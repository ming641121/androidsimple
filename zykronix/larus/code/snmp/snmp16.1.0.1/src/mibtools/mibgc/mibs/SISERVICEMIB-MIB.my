--
-- Copyright (C) 1992-2003 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--
 
--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--
--
SISERVICEMIB-MIB DEFINITIONS ::= BEGIN

IMPORTS
    snmpResearchMIBs
        FROM SNMP-RESEARCH-MIB

    DisplayString, RowStatus, TruthValue, DateAndTime
        FROM SNMPv2-TC

    MODULE-IDENTITY, OBJECT-TYPE, NOTIFICATION-TYPE,
    Integer32, Counter32
        FROM SNMPv2-SMI;


siServiceMIB MODULE-IDENTITY
    LAST-UPDATED "200203201101Z"
    ORGANIZATION "SNMP Research"
    CONTACT-INFO "Postal:  SNMP Research
                           3001 Kimberlin Heights Rd.
                           Knoxville, TN 37920-9716
                           USA

                  Tel:     +1 865 579 3311
                  Fax:     +1 865 579 6565
                  E-mail:  info@snmp.com
                  WWW:     http://www.snmp.com"
    DESCRIPTION  " "
    ::= { snmpResearchMIBs 38 }


siServiceObjects     OBJECT IDENTIFIER ::= { siServiceMIB 1 }
siServiceNotifications OBJECT IDENTIFIER ::= { siServiceMIB 2 }

-- The siDns Group

siDns OBJECT IDENTIFIER ::= { siServiceObjects 1 }
 
siDnsTable OBJECT-TYPE
    SYNTAX     SEQUENCE OF SiDnsEntry
    MAX-ACCESS not-accessible
    STATUS     current
    DESCRIPTION " "
    ::= { siDns 1 }

siDnsEntry OBJECT-TYPE
    SYNTAX     SiDnsEntry
    MAX-ACCESS not-accessible
    STATUS     current
    DESCRIPTION " "
    INDEX { siDnsIndex }
    ::= { siDnsTable 1 }

SiDnsEntry ::= SEQUENCE {
    siDnsIndex             Integer32,
    siDnsServerName        DisplayString,
    siDnsLookupAddress     DisplayString,
    siDnsTimeout           Integer32,
    siDnsRetries           Integer32,
    siDnsErrcode           INTEGER,
    siDnsErrstring         DisplayString,
    siDnsNameResolutionTime Integer32,
    siDnsResponseTime      Integer32,
    siDnsPollInterval      Integer32,
    siDnsPollNow           TruthValue,
    siDnsMaxRows           Integer32,
    siDnsTrapOnFailure     TruthValue,
    siDnsThreshold         Integer32,
    siDnsRowStatus         RowStatus
}

siDnsIndex OBJECT-TYPE
    SYNTAX     Integer32 (1..2147483647)
    MAX-ACCESS not-accessible
    STATUS     current
    DESCRIPTION " "
    ::= { siDnsEntry 1 }

siDnsServerName OBJECT-TYPE
    SYNTAX     DisplayString 
    MAX-ACCESS read-create
    STATUS     current
    DESCRIPTION " "
    ::= { siDnsEntry 3 }

siDnsLookupAddress OBJECT-TYPE
    SYNTAX     DisplayString 
    MAX-ACCESS read-create
    STATUS     current
    DESCRIPTION " "
    ::= { siDnsEntry 4 }

siDnsTimeout OBJECT-TYPE
    SYNTAX     Integer32 (0..2147483647)
    MAX-ACCESS read-create
    STATUS     current
    DESCRIPTION " "
    ::= { siDnsEntry 5 }

siDnsRetries OBJECT-TYPE
    SYNTAX     Integer32 (0..2147483647)
    MAX-ACCESS read-create
    STATUS     current
    DESCRIPTION " "
    ::= { siDnsEntry 6 }

siDnsErrcode OBJECT-TYPE
    SYNTAX     INTEGER{inProgress(-1),noError(0),resMakeQueryError(1),gethostbynameError(2),notAnInternetHost(3),errorTimerTimedOut(4),serverDown(5),unknownError(6),noDnsMatch(7),recvFromError(8)} 
    MAX-ACCESS read-only
    STATUS     current
    DESCRIPTION " "
    ::= { siDnsEntry 7 }

siDnsErrstring OBJECT-TYPE
    SYNTAX     DisplayString 
    MAX-ACCESS read-only
    STATUS     current
    DESCRIPTION " "
    ::= { siDnsEntry 8 }

siDnsNameResolutionTime OBJECT-TYPE
    SYNTAX     Integer32 (0..2147483647)
    MAX-ACCESS read-only
    STATUS     current
    DESCRIPTION " "
    ::= { siDnsEntry 9 }

siDnsResponseTime OBJECT-TYPE
    SYNTAX     Integer32 (0..2147483647)
    MAX-ACCESS read-only
    STATUS     current
    DESCRIPTION " "
    ::= { siDnsEntry 10 }

siDnsPollInterval OBJECT-TYPE
    SYNTAX     Integer32 (0..2147483647)
    MAX-ACCESS read-create
    STATUS     current
    DESCRIPTION " "
    ::= { siDnsEntry 11 }

siDnsPollNow OBJECT-TYPE
    SYNTAX     TruthValue 
    MAX-ACCESS read-create
    STATUS     current
    DESCRIPTION " "
    ::= { siDnsEntry 12 }

siDnsMaxRows OBJECT-TYPE
    SYNTAX     Integer32 (0..2147483647)
    MAX-ACCESS read-create
    STATUS     current
    DESCRIPTION " "
    ::= { siDnsEntry 13 }

siDnsTrapOnFailure OBJECT-TYPE
    SYNTAX     TruthValue 
    MAX-ACCESS read-create
    STATUS     current
    DESCRIPTION " "
    ::= { siDnsEntry 14 }

siDnsThreshold OBJECT-TYPE
    SYNTAX     Integer32 (0..2147483647)
    MAX-ACCESS read-create
    STATUS     current
    DESCRIPTION " "
    ::= { siDnsEntry 15 }

siDnsRowStatus OBJECT-TYPE
    SYNTAX     RowStatus 
    MAX-ACCESS read-create
    STATUS     current
    DESCRIPTION " "
    ::= { siDnsEntry 16 }

siDnsHistoryTable OBJECT-TYPE
    SYNTAX     SEQUENCE OF SiDnsHistoryEntry
    MAX-ACCESS not-accessible
    STATUS     current
    DESCRIPTION " "
    ::= { siDns 2 }

siDnsHistoryEntry OBJECT-TYPE
    SYNTAX     SiDnsHistoryEntry
    MAX-ACCESS not-accessible
    STATUS     current
    DESCRIPTION " "
    INDEX { siDnsIndex, siDnsHistoryIndex }
    ::= { siDnsHistoryTable 1 }

SiDnsHistoryEntry ::= SEQUENCE {
    siDnsHistoryIndex      Integer32,
    siDnsHistoryNameResolutionTime Integer32,
    siDnsHistoryResponseTime Integer32,
    siDnsHistoryErrcode    INTEGER,
    siDnsHistoryErrstring  DisplayString,
    siDnsHistoryDateAndTime DateAndTime,
    siDnsHistoryNumRetries Integer32
}

siDnsHistoryIndex OBJECT-TYPE
    SYNTAX     Integer32 (1..2147483647)
    MAX-ACCESS not-accessible
    STATUS     current
    DESCRIPTION " "
    ::= { siDnsHistoryEntry 1 }

siDnsHistoryNameResolutionTime OBJECT-TYPE
    SYNTAX     Integer32 (0..2147483647)
    MAX-ACCESS read-only
    STATUS     current
    DESCRIPTION " "
    ::= { siDnsHistoryEntry 2 }

siDnsHistoryResponseTime OBJECT-TYPE
    SYNTAX     Integer32 (0..2147483647)
    MAX-ACCESS read-only
    STATUS     current
    DESCRIPTION " "
    ::= { siDnsHistoryEntry 3 }

siDnsHistoryErrcode OBJECT-TYPE
    SYNTAX     INTEGER{noError(0),resMakeQueryError(1),gethostbynameError(2),notAnInternetHost(3),errorTimerTimedOut(4),serverDown(5),unknownError(6),noDnsMatch(7),recvFromError(8)} 
    MAX-ACCESS read-only
    STATUS     current
    DESCRIPTION " "
    ::= { siDnsHistoryEntry 4 }

siDnsHistoryErrstring OBJECT-TYPE
    SYNTAX     DisplayString 
    MAX-ACCESS read-only
    STATUS     current
    DESCRIPTION " "
    ::= { siDnsHistoryEntry 5 }

siDnsHistoryDateAndTime OBJECT-TYPE
    SYNTAX     DateAndTime 
    MAX-ACCESS read-only
    STATUS     current
    DESCRIPTION " "
    ::= { siDnsHistoryEntry 6 }

siDnsHistoryNumRetries OBJECT-TYPE
    SYNTAX     Integer32 (0..2147483647)
    MAX-ACCESS read-only
    STATUS     current
    DESCRIPTION " "
    ::= { siDnsHistoryEntry 7 }


-- The siFtp Group

siFtp OBJECT IDENTIFIER ::= { siServiceObjects 2 }
 
siFtpTable OBJECT-TYPE
    SYNTAX     SEQUENCE OF SiFtpEntry
    MAX-ACCESS not-accessible
    STATUS     current
    DESCRIPTION " "
    ::= { siFtp 1 }

siFtpEntry OBJECT-TYPE
    SYNTAX     SiFtpEntry
    MAX-ACCESS not-accessible
    STATUS     current
    DESCRIPTION " "
    INDEX { siFtpIndex }
    ::= { siFtpTable 1 }

SiFtpEntry ::= SEQUENCE {
    siFtpIndex             Integer32,
    siFtpServerName        DisplayString,
    siFtpUserName          DisplayString,
    siFtpPassword          DisplayString,
    siFtpLocalFileName     DisplayString,
    siFtpRemoteFileName    DisplayString,
    siFtpCommand           INTEGER,
    siFtpTimeout           Integer32,
    siFtpErrcode           Integer32,
    siFtpErrstring         DisplayString,
    siFtpNameResolutionTime Integer32,
    siFtpConnectTime       Integer32,
    siFtpResponseTime      Integer32,
    siFtpPollInterval      Integer32,
    siFtpPollNow           TruthValue,
    siFtpMaxRows           Integer32,
    siFtpTrapOnFailure     TruthValue,
    siFtpThreshold         Integer32,
    siFtpRowStatus         RowStatus
}

siFtpIndex OBJECT-TYPE
    SYNTAX     Integer32 (1..2147483647)
    MAX-ACCESS not-accessible
    STATUS     current
    DESCRIPTION " "
    ::= { siFtpEntry 1 }

siFtpServerName OBJECT-TYPE
    SYNTAX     DisplayString 
    MAX-ACCESS read-create
    STATUS     current
    DESCRIPTION " "
    ::= { siFtpEntry 3 }

siFtpUserName OBJECT-TYPE
    SYNTAX     DisplayString 
    MAX-ACCESS read-create
    STATUS     current
    DESCRIPTION " "
    ::= { siFtpEntry 4 }

siFtpPassword OBJECT-TYPE
    SYNTAX     DisplayString 
    MAX-ACCESS read-create
    STATUS     current
    DESCRIPTION " "
    ::= { siFtpEntry 5 }

siFtpLocalFileName OBJECT-TYPE
    SYNTAX     DisplayString 
    MAX-ACCESS read-create
    STATUS     current
    DESCRIPTION " "
    ::= { siFtpEntry 6 }

siFtpRemoteFileName OBJECT-TYPE
    SYNTAX     DisplayString 
    MAX-ACCESS read-create
    STATUS     current
    DESCRIPTION " "
    ::= { siFtpEntry 7 }

siFtpCommand OBJECT-TYPE
    SYNTAX     INTEGER{put(1),get(2)} 
    MAX-ACCESS read-create
    STATUS     current
    DESCRIPTION " "
    ::= { siFtpEntry 8 }

siFtpTimeout OBJECT-TYPE
    SYNTAX     Integer32 (0..2147483647)
    MAX-ACCESS read-create
    STATUS     current
    DESCRIPTION " "
    ::= { siFtpEntry 9 }

siFtpErrcode OBJECT-TYPE
    SYNTAX     Integer32 
    MAX-ACCESS read-only
    STATUS     current
    DESCRIPTION " "
    ::= { siFtpEntry 10 }

siFtpErrstring OBJECT-TYPE
    SYNTAX     DisplayString 
    MAX-ACCESS read-only
    STATUS     current
    DESCRIPTION " "
    ::= { siFtpEntry 11 }

siFtpNameResolutionTime OBJECT-TYPE
    SYNTAX     Integer32 (0..2147483647)
    MAX-ACCESS read-only
    STATUS     current
    DESCRIPTION " "
    ::= { siFtpEntry 12 }

siFtpConnectTime OBJECT-TYPE
    SYNTAX     Integer32 (0..2147483647)
    MAX-ACCESS read-only
    STATUS     current
    DESCRIPTION " "
    ::= { siFtpEntry 13 }

siFtpResponseTime OBJECT-TYPE
    SYNTAX     Integer32 (0..2147483647)
    MAX-ACCESS read-only
    STATUS     current
    DESCRIPTION " "
    ::= { siFtpEntry 14 }

siFtpPollInterval OBJECT-TYPE
    SYNTAX     Integer32 (0..2147483647)
    MAX-ACCESS read-create
    STATUS     current
    DESCRIPTION " "
    ::= { siFtpEntry 15 }

siFtpPollNow OBJECT-TYPE
    SYNTAX     TruthValue 
    MAX-ACCESS read-create
    STATUS     current
    DESCRIPTION " "
    ::= { siFtpEntry 16 }

siFtpMaxRows OBJECT-TYPE
    SYNTAX     Integer32 (0..2147483647)
    MAX-ACCESS read-create
    STATUS     current
    DESCRIPTION " "
    ::= { siFtpEntry 17 }

siFtpTrapOnFailure OBJECT-TYPE
    SYNTAX     TruthValue 
    MAX-ACCESS read-create
    STATUS     current
    DESCRIPTION " "
    ::= { siFtpEntry 18 }

siFtpThreshold OBJECT-TYPE
    SYNTAX     Integer32 (0..2147483647)
    MAX-ACCESS read-create
    STATUS     current
    DESCRIPTION " "
    ::= { siFtpEntry 19 }

siFtpRowStatus OBJECT-TYPE
    SYNTAX     RowStatus 
    MAX-ACCESS read-create
    STATUS     current
    DESCRIPTION " "
    ::= { siFtpEntry 20 }

siFtpHistoryTable OBJECT-TYPE
    SYNTAX     SEQUENCE OF SiFtpHistoryEntry
    MAX-ACCESS not-accessible
    STATUS     current
    DESCRIPTION " "
    ::= { siFtp 2 }

siFtpHistoryEntry OBJECT-TYPE
    SYNTAX     SiFtpHistoryEntry
    MAX-ACCESS not-accessible
    STATUS     current
    DESCRIPTION " "
    INDEX { siFtpIndex, siFtpHistoryIndex }
    ::= { siFtpHistoryTable 1 }

SiFtpHistoryEntry ::= SEQUENCE {
    siFtpHistoryIndex      Integer32,
    siFtpHistoryNameResolutionTime Integer32,
    siFtpHistoryResponseTime Integer32,
    siFtpHistoryConnectTime Integer32,
    siFtpHistoryErrcode    Integer32,
    siFtpHistoryErrstring  DisplayString,
    siFtpHistoryDateAndTime DateAndTime
}

siFtpHistoryIndex OBJECT-TYPE
    SYNTAX     Integer32 (1..2147483647)
    MAX-ACCESS not-accessible
    STATUS     current
    DESCRIPTION " "
    ::= { siFtpHistoryEntry 1 }

siFtpHistoryNameResolutionTime OBJECT-TYPE
    SYNTAX     Integer32 (0..2147483647)
    MAX-ACCESS read-only
    STATUS     current
    DESCRIPTION " "
    ::= { siFtpHistoryEntry 2 }

siFtpHistoryResponseTime OBJECT-TYPE
    SYNTAX     Integer32 (0..2147483647)
    MAX-ACCESS read-only
    STATUS     current
    DESCRIPTION " "
    ::= { siFtpHistoryEntry 3 }

siFtpHistoryConnectTime OBJECT-TYPE
    SYNTAX     Integer32 (0..2147483647)
    MAX-ACCESS read-only
    STATUS     current
    DESCRIPTION " "
    ::= { siFtpHistoryEntry 4 }

siFtpHistoryErrcode OBJECT-TYPE
    SYNTAX     Integer32 
    MAX-ACCESS read-only
    STATUS     current
    DESCRIPTION " "
    ::= { siFtpHistoryEntry 5 }

siFtpHistoryErrstring OBJECT-TYPE
    SYNTAX     DisplayString 
    MAX-ACCESS read-only
    STATUS     current
    DESCRIPTION " "
    ::= { siFtpHistoryEntry 6 }

siFtpHistoryDateAndTime OBJECT-TYPE
    SYNTAX     DateAndTime 
    MAX-ACCESS read-only
    STATUS     current
    DESCRIPTION " "
    ::= { siFtpHistoryEntry 7 }


-- The siHttp Group

siHttp OBJECT IDENTIFIER ::= { siServiceObjects 3 }
 
siHttpTable OBJECT-TYPE
    SYNTAX     SEQUENCE OF SiHttpEntry
    MAX-ACCESS not-accessible
    STATUS     current
    DESCRIPTION " "
    ::= { siHttp 1 }

siHttpEntry OBJECT-TYPE
    SYNTAX     SiHttpEntry
    MAX-ACCESS not-accessible
    STATUS     current
    DESCRIPTION " "
    INDEX { siHttpIndex }
    ::= { siHttpTable 1 }

SiHttpEntry ::= SEQUENCE {
    siHttpIndex            Integer32,
    siHttpServerName       DisplayString,
    siHttpPageUrl          DisplayString,
    siHttpPort             Integer32,
    siHttpPageTimeout      Integer32,
    siHttpCommand          INTEGER,
    siHttpUserName         DisplayString,
    siHttpPassword         DisplayString,
    siHttpPostName         DisplayString,
    siHttpPostValue        DisplayString,
    siHttpErrcode          Integer32,
    siHttpErrstring        DisplayString,
    siHttpNameResolutionTime Integer32,
    siHttpConnectTime      Integer32,
    siHttpResponseTime     Integer32,
    siHttpPollInterval     Integer32,
    siHttpPollNow          TruthValue,
    siHttpMaxRows          Integer32,
    siHttpTrapOnFailure    TruthValue,
    siHttpThreshold        Integer32,
    siHttpRowStatus        RowStatus
}

siHttpIndex OBJECT-TYPE
    SYNTAX     Integer32 (1..2147483647)
    MAX-ACCESS not-accessible
    STATUS     current
    DESCRIPTION " "
    ::= { siHttpEntry 1 }

siHttpServerName OBJECT-TYPE
    SYNTAX     DisplayString 
    MAX-ACCESS read-create
    STATUS     current
    DESCRIPTION " "
    ::= { siHttpEntry 3 }

siHttpPageUrl OBJECT-TYPE
    SYNTAX     DisplayString 
    MAX-ACCESS read-create
    STATUS     current
    DESCRIPTION " "
    ::= { siHttpEntry 4 }

siHttpPort OBJECT-TYPE
    SYNTAX     Integer32 (1..2147483647)
    MAX-ACCESS read-create
    STATUS     current
    DESCRIPTION " "
    ::= { siHttpEntry 5 }

siHttpPageTimeout OBJECT-TYPE
    SYNTAX     Integer32 (0..2147483647)
    MAX-ACCESS read-create
    STATUS     current
    DESCRIPTION " "
    ::= { siHttpEntry 6 }

siHttpCommand OBJECT-TYPE
    SYNTAX     INTEGER{put(1),get(2)} 
    MAX-ACCESS read-create
    STATUS     current
    DESCRIPTION " "
    ::= { siHttpEntry 7 }

siHttpUserName OBJECT-TYPE
    SYNTAX     DisplayString 
    MAX-ACCESS read-create
    STATUS     current
    DESCRIPTION " "
    ::= { siHttpEntry 8 }

siHttpPassword OBJECT-TYPE
    SYNTAX     DisplayString 
    MAX-ACCESS read-create
    STATUS     current
    DESCRIPTION " "
    ::= { siHttpEntry 9 }

siHttpPostName OBJECT-TYPE
    SYNTAX     DisplayString 
    MAX-ACCESS read-create
    STATUS     current
    DESCRIPTION " "
    ::= { siHttpEntry 10 }

siHttpPostValue OBJECT-TYPE
    SYNTAX     DisplayString 
    MAX-ACCESS read-create
    STATUS     current
    DESCRIPTION " "
    ::= { siHttpEntry 11 }

siHttpErrcode OBJECT-TYPE
    SYNTAX     Integer32 
    MAX-ACCESS read-only
    STATUS     current
    DESCRIPTION " "
    ::= { siHttpEntry 12 }

siHttpErrstring OBJECT-TYPE
    SYNTAX     DisplayString 
    MAX-ACCESS read-only
    STATUS     current
    DESCRIPTION " "
    ::= { siHttpEntry 13 }

siHttpNameResolutionTime OBJECT-TYPE
    SYNTAX     Integer32 (0..2147483647)
    MAX-ACCESS read-only
    STATUS     current
    DESCRIPTION " "
    ::= { siHttpEntry 14 }

siHttpConnectTime OBJECT-TYPE
    SYNTAX     Integer32 (0..2147483647)
    MAX-ACCESS read-only
    STATUS     current
    DESCRIPTION " "
    ::= { siHttpEntry 15 }

siHttpResponseTime OBJECT-TYPE
    SYNTAX     Integer32 (0..2147483647)
    MAX-ACCESS read-only
    STATUS     current
    DESCRIPTION " "
    ::= { siHttpEntry 16 }

siHttpPollInterval OBJECT-TYPE
    SYNTAX     Integer32 (0..2147483647)
    MAX-ACCESS read-create
    STATUS     current
    DESCRIPTION " "
    ::= { siHttpEntry 17 }

siHttpPollNow OBJECT-TYPE
    SYNTAX     TruthValue 
    MAX-ACCESS read-create
    STATUS     current
    DESCRIPTION " "
    ::= { siHttpEntry 18 }

siHttpMaxRows OBJECT-TYPE
    SYNTAX     Integer32 (0..2147483647)
    MAX-ACCESS read-create
    STATUS     current
    DESCRIPTION " "
    ::= { siHttpEntry 19 }

siHttpTrapOnFailure OBJECT-TYPE
    SYNTAX     TruthValue 
    MAX-ACCESS read-create
    STATUS     current
    DESCRIPTION " "
    ::= { siHttpEntry 20 }

siHttpThreshold OBJECT-TYPE
    SYNTAX     Integer32 (0..2147483647)
    MAX-ACCESS read-create
    STATUS     current
    DESCRIPTION " "
    ::= { siHttpEntry 21 }

siHttpRowStatus OBJECT-TYPE
    SYNTAX     RowStatus 
    MAX-ACCESS read-create
    STATUS     current
    DESCRIPTION " "
    ::= { siHttpEntry 22 }

siHttpHistoryTable OBJECT-TYPE
    SYNTAX     SEQUENCE OF SiHttpHistoryEntry
    MAX-ACCESS not-accessible
    STATUS     current
    DESCRIPTION " "
    ::= { siHttp 2 }

siHttpHistoryEntry OBJECT-TYPE
    SYNTAX     SiHttpHistoryEntry
    MAX-ACCESS not-accessible
    STATUS     current
    DESCRIPTION " "
    INDEX { siHttpIndex, siHttpHistoryIndex }
    ::= { siHttpHistoryTable 1 }

SiHttpHistoryEntry ::= SEQUENCE {
    siHttpHistoryIndex     Integer32,
    siHttpHistoryNameResolutionTime Integer32,
    siHttpHistoryConnectTime Integer32,
    siHttpHistoryResponseTime Integer32,
    siHttpHistoryErrcode   Integer32,
    siHttpHistoryErrstring DisplayString,
    siHttpHistoryDateAndTime DateAndTime
}

siHttpHistoryIndex OBJECT-TYPE
    SYNTAX     Integer32 (1..2147483647)
    MAX-ACCESS not-accessible
    STATUS     current
    DESCRIPTION " "
    ::= { siHttpHistoryEntry 1 }

siHttpHistoryNameResolutionTime OBJECT-TYPE
    SYNTAX     Integer32 (0..2147483647)
    MAX-ACCESS read-only
    STATUS     current
    DESCRIPTION " "
    ::= { siHttpHistoryEntry 2 }

siHttpHistoryConnectTime OBJECT-TYPE
    SYNTAX     Integer32 (0..2147483647)
    MAX-ACCESS read-only
    STATUS     current
    DESCRIPTION " "
    ::= { siHttpHistoryEntry 3 }

siHttpHistoryResponseTime OBJECT-TYPE
    SYNTAX     Integer32 (0..2147483647)
    MAX-ACCESS read-only
    STATUS     current
    DESCRIPTION " "
    ::= { siHttpHistoryEntry 4 }

siHttpHistoryErrcode OBJECT-TYPE
    SYNTAX     Integer32 
    MAX-ACCESS read-only
    STATUS     current
    DESCRIPTION " "
    ::= { siHttpHistoryEntry 5 }

siHttpHistoryErrstring OBJECT-TYPE
    SYNTAX     DisplayString 
    MAX-ACCESS read-only
    STATUS     current
    DESCRIPTION " "
    ::= { siHttpHistoryEntry 6 }

siHttpHistoryDateAndTime OBJECT-TYPE
    SYNTAX     DateAndTime 
    MAX-ACCESS read-only
    STATUS     current
    DESCRIPTION " "
    ::= { siHttpHistoryEntry 7 }


-- The siNntp Group

siNntp OBJECT IDENTIFIER ::= { siServiceObjects 4 }
 
siNntpTable OBJECT-TYPE
    SYNTAX     SEQUENCE OF SiNntpEntry
    MAX-ACCESS not-accessible
    STATUS     current
    DESCRIPTION " "
    ::= { siNntp 1 }

siNntpEntry OBJECT-TYPE
    SYNTAX     SiNntpEntry
    MAX-ACCESS not-accessible
    STATUS     current
    DESCRIPTION " "
    INDEX { siNntpIndex }
    ::= { siNntpTable 1 }

SiNntpEntry ::= SEQUENCE {
    siNntpIndex            Integer32,
    siNntpServerName       DisplayString,
    siNntpNewsgroup        DisplayString,
    siNntpTimeout          Integer32,
    siNntpRetries          Integer32,
    siNntpErrcode          Integer32,
    siNntpErrstring        DisplayString,
    siNntpNameResolutionTime Integer32,
    siNntpConnectTime      Integer32,
    siNntpResponseTime     Integer32,
    siNntpPollInterval     Integer32,
    siNntpPollNow          TruthValue,
    siNntpMaxRows          Integer32,
    siNntpTrapOnFailure    TruthValue,
    siNntpThreshold        Integer32,
    siNntpRowStatus        RowStatus
}

siNntpIndex OBJECT-TYPE
    SYNTAX     Integer32 (1..2147483647)
    MAX-ACCESS not-accessible
    STATUS     current
    DESCRIPTION " "
    ::= { siNntpEntry 1 }

siNntpServerName OBJECT-TYPE
    SYNTAX     DisplayString 
    MAX-ACCESS read-create
    STATUS     current
    DESCRIPTION " "
    ::= { siNntpEntry 3 }

siNntpNewsgroup OBJECT-TYPE
    SYNTAX     DisplayString 
    MAX-ACCESS read-create
    STATUS     current
    DESCRIPTION " "
    ::= { siNntpEntry 4 }

siNntpTimeout OBJECT-TYPE
    SYNTAX     Integer32 (0..2147483647)
    MAX-ACCESS read-create
    STATUS     current
    DESCRIPTION " "
    ::= { siNntpEntry 5 }

siNntpRetries OBJECT-TYPE
    SYNTAX     Integer32 (0..2147483647)
    MAX-ACCESS read-create
    STATUS     current
    DESCRIPTION " "
    ::= { siNntpEntry 6 }

siNntpErrcode OBJECT-TYPE
    SYNTAX     Integer32 
    MAX-ACCESS read-only
    STATUS     current
    DESCRIPTION " "
    ::= { siNntpEntry 7 }

siNntpErrstring OBJECT-TYPE
    SYNTAX     DisplayString 
    MAX-ACCESS read-only
    STATUS     current
    DESCRIPTION " "
    ::= { siNntpEntry 8 }

siNntpNameResolutionTime OBJECT-TYPE
    SYNTAX     Integer32 (0..2147483647)
    MAX-ACCESS read-only
    STATUS     current
    DESCRIPTION " "
    ::= { siNntpEntry 9 }

siNntpConnectTime OBJECT-TYPE
    SYNTAX     Integer32 (0..2147483647)
    MAX-ACCESS read-only
    STATUS     current
    DESCRIPTION " "
    ::= { siNntpEntry 10 }

siNntpResponseTime OBJECT-TYPE
    SYNTAX     Integer32 (0..2147483647)
    MAX-ACCESS read-only
    STATUS     current
    DESCRIPTION " "
    ::= { siNntpEntry 11 }

siNntpPollInterval OBJECT-TYPE
    SYNTAX     Integer32 (0..2147483647)
    MAX-ACCESS read-create
    STATUS     current
    DESCRIPTION " "
    ::= { siNntpEntry 12 }

siNntpPollNow OBJECT-TYPE
    SYNTAX     TruthValue 
    MAX-ACCESS read-create
    STATUS     current
    DESCRIPTION " "
    ::= { siNntpEntry 13 }

siNntpMaxRows OBJECT-TYPE
    SYNTAX     Integer32 (0..2147483647)
    MAX-ACCESS read-create
    STATUS     current
    DESCRIPTION " "
    ::= { siNntpEntry 14 }

siNntpTrapOnFailure OBJECT-TYPE
    SYNTAX     TruthValue 
    MAX-ACCESS read-create
    STATUS     current
    DESCRIPTION " "
    ::= { siNntpEntry 15 }

siNntpThreshold OBJECT-TYPE
    SYNTAX     Integer32 (0..2147483647)
    MAX-ACCESS read-create
    STATUS     current
    DESCRIPTION " "
    ::= { siNntpEntry 16 }

siNntpRowStatus OBJECT-TYPE
    SYNTAX     RowStatus 
    MAX-ACCESS read-create
    STATUS     current
    DESCRIPTION " "
    ::= { siNntpEntry 17 }

siNntpHistoryTable OBJECT-TYPE
    SYNTAX     SEQUENCE OF SiNntpHistoryEntry
    MAX-ACCESS not-accessible
    STATUS     current
    DESCRIPTION " "
    ::= { siNntp 2 }

siNntpHistoryEntry OBJECT-TYPE
    SYNTAX     SiNntpHistoryEntry
    MAX-ACCESS not-accessible
    STATUS     current
    DESCRIPTION " "
    INDEX { siNntpIndex, siNntpHistoryIndex }
    ::= { siNntpHistoryTable 1 }

SiNntpHistoryEntry ::= SEQUENCE {
    siNntpHistoryIndex     Integer32,
    siNntpHistoryNameResolutionTime Integer32,
    siNntpHistoryConnectTime Integer32,
    siNntpHistoryResponseTime Integer32,
    siNntpHistoryErrcode   Integer32,
    siNntpHistoryErrstring DisplayString,
    siNntpHistoryDateAndTime DateAndTime
}

siNntpHistoryIndex OBJECT-TYPE
    SYNTAX     Integer32 (1..2147483647)
    MAX-ACCESS not-accessible
    STATUS     current
    DESCRIPTION " "
    ::= { siNntpHistoryEntry 1 }

siNntpHistoryNameResolutionTime OBJECT-TYPE
    SYNTAX     Integer32 (0..2147483647)
    MAX-ACCESS read-only
    STATUS     current
    DESCRIPTION " "
    ::= { siNntpHistoryEntry 2 }

siNntpHistoryConnectTime OBJECT-TYPE
    SYNTAX     Integer32 (0..2147483647)
    MAX-ACCESS read-only
    STATUS     current
    DESCRIPTION " "
    ::= { siNntpHistoryEntry 3 }

siNntpHistoryResponseTime OBJECT-TYPE
    SYNTAX     Integer32 (0..2147483647)
    MAX-ACCESS read-only
    STATUS     current
    DESCRIPTION " "
    ::= { siNntpHistoryEntry 4 }

siNntpHistoryErrcode OBJECT-TYPE
    SYNTAX     Integer32 
    MAX-ACCESS read-only
    STATUS     current
    DESCRIPTION " "
    ::= { siNntpHistoryEntry 5 }

siNntpHistoryErrstring OBJECT-TYPE
    SYNTAX     DisplayString 
    MAX-ACCESS read-only
    STATUS     current
    DESCRIPTION " "
    ::= { siNntpHistoryEntry 6 }

siNntpHistoryDateAndTime OBJECT-TYPE
    SYNTAX     DateAndTime 
    MAX-ACCESS read-only
    STATUS     current
    DESCRIPTION " "
    ::= { siNntpHistoryEntry 7 }


-- The siPop3 Group

siPop3 OBJECT IDENTIFIER ::= { siServiceObjects 5 }
 
siPop3Table OBJECT-TYPE
    SYNTAX     SEQUENCE OF SiPop3Entry
    MAX-ACCESS not-accessible
    STATUS     current
    DESCRIPTION " "
    ::= { siPop3 1 }

siPop3Entry OBJECT-TYPE
    SYNTAX     SiPop3Entry
    MAX-ACCESS not-accessible
    STATUS     current
    DESCRIPTION " "
    INDEX { siPop3Index }
    ::= { siPop3Table 1 }

SiPop3Entry ::= SEQUENCE {
    siPop3Index            Integer32,
    siPop3ServerName       DisplayString,
    siPop3UserName         DisplayString,
    siPop3Password         DisplayString,
    siPop3Timeout          Integer32,
    siPop3Errcode          Integer32,
    siPop3Errstring        DisplayString,
    siPop3NameResolutionTime Integer32,
    siPop3ConnectTime      Integer32,
    siPop3ResponseTime     Integer32,
    siPop3PollInterval     Integer32,
    siPop3PollNow          TruthValue,
    siPop3MaxRows          Integer32,
    siPop3TrapOnFailure    TruthValue,
    siPop3Threshold        Integer32,
    siPop3RowStatus        RowStatus
}

siPop3Index OBJECT-TYPE
    SYNTAX     Integer32 (1..2147483647)
    MAX-ACCESS not-accessible
    STATUS     current
    DESCRIPTION " "
    ::= { siPop3Entry 1 }

siPop3ServerName OBJECT-TYPE
    SYNTAX     DisplayString 
    MAX-ACCESS read-create
    STATUS     current
    DESCRIPTION " "
    ::= { siPop3Entry 3 }

siPop3UserName OBJECT-TYPE
    SYNTAX     DisplayString 
    MAX-ACCESS read-create
    STATUS     current
    DESCRIPTION " "
    ::= { siPop3Entry 4 }

siPop3Password OBJECT-TYPE
    SYNTAX     DisplayString 
    MAX-ACCESS read-create
    STATUS     current
    DESCRIPTION " "
    ::= { siPop3Entry 5 }

siPop3Timeout OBJECT-TYPE
    SYNTAX     Integer32 (0..2147483647)
    MAX-ACCESS read-create
    STATUS     current
    DESCRIPTION " "
    ::= { siPop3Entry 6 }

siPop3Errcode OBJECT-TYPE
    SYNTAX     Integer32 
    MAX-ACCESS read-only
    STATUS     current
    DESCRIPTION " "
    ::= { siPop3Entry 7 }

siPop3Errstring OBJECT-TYPE
    SYNTAX     DisplayString 
    MAX-ACCESS read-only
    STATUS     current
    DESCRIPTION " "
    ::= { siPop3Entry 8 }

siPop3NameResolutionTime OBJECT-TYPE
    SYNTAX     Integer32 (0..2147483647)
    MAX-ACCESS read-only
    STATUS     current
    DESCRIPTION " "
    ::= { siPop3Entry 9 }

siPop3ConnectTime OBJECT-TYPE
    SYNTAX     Integer32 (0..2147483647)
    MAX-ACCESS read-only
    STATUS     current
    DESCRIPTION " "
    ::= { siPop3Entry 10 }

siPop3ResponseTime OBJECT-TYPE
    SYNTAX     Integer32 (0..2147483647)
    MAX-ACCESS read-only
    STATUS     current
    DESCRIPTION " "
    ::= { siPop3Entry 11 }

siPop3PollInterval OBJECT-TYPE
    SYNTAX     Integer32 (0..2147483647)
    MAX-ACCESS read-create
    STATUS     current
    DESCRIPTION " "
    ::= { siPop3Entry 12 }

siPop3PollNow OBJECT-TYPE
    SYNTAX     TruthValue 
    MAX-ACCESS read-create
    STATUS     current
    DESCRIPTION " "
    ::= { siPop3Entry 13 }

siPop3MaxRows OBJECT-TYPE
    SYNTAX     Integer32 (0..2147483647)
    MAX-ACCESS read-create
    STATUS     current
    DESCRIPTION " "
    ::= { siPop3Entry 14 }

siPop3TrapOnFailure OBJECT-TYPE
    SYNTAX     TruthValue 
    MAX-ACCESS read-create
    STATUS     current
    DESCRIPTION " "
    ::= { siPop3Entry 15 }

siPop3Threshold OBJECT-TYPE
    SYNTAX     Integer32 (0..2147483647)
    MAX-ACCESS read-create
    STATUS     current
    DESCRIPTION " "
    ::= { siPop3Entry 16 }

siPop3RowStatus OBJECT-TYPE
    SYNTAX     RowStatus 
    MAX-ACCESS read-create
    STATUS     current
    DESCRIPTION " "
    ::= { siPop3Entry 17 }

siPop3HistoryTable OBJECT-TYPE
    SYNTAX     SEQUENCE OF SiPop3HistoryEntry
    MAX-ACCESS not-accessible
    STATUS     current
    DESCRIPTION " "
    ::= { siPop3 2 }

siPop3HistoryEntry OBJECT-TYPE
    SYNTAX     SiPop3HistoryEntry
    MAX-ACCESS not-accessible
    STATUS     current
    DESCRIPTION " "
    INDEX { siPop3Index, siPop3HistoryIndex }
    ::= { siPop3HistoryTable 1 }

SiPop3HistoryEntry ::= SEQUENCE {
    siPop3HistoryIndex     Integer32,
    siPop3HistoryNameResolutionTime Integer32,
    siPop3HistoryConnectTime Integer32,
    siPop3HistoryResponseTime Integer32,
    siPop3HistoryErrcode   Integer32,
    siPop3HistoryErrstring DisplayString,
    siPop3HistoryDateAndTime DateAndTime
}

siPop3HistoryIndex OBJECT-TYPE
    SYNTAX     Integer32 (1..2147483647)
    MAX-ACCESS not-accessible
    STATUS     current
    DESCRIPTION " "
    ::= { siPop3HistoryEntry 1 }

siPop3HistoryNameResolutionTime OBJECT-TYPE
    SYNTAX     Integer32 (0..2147483647)
    MAX-ACCESS read-only
    STATUS     current
    DESCRIPTION " "
    ::= { siPop3HistoryEntry 2 }

siPop3HistoryConnectTime OBJECT-TYPE
    SYNTAX     Integer32 (0..2147483647)
    MAX-ACCESS read-only
    STATUS     current
    DESCRIPTION " "
    ::= { siPop3HistoryEntry 3 }

siPop3HistoryResponseTime OBJECT-TYPE
    SYNTAX     Integer32 (0..2147483647)
    MAX-ACCESS read-only
    STATUS     current
    DESCRIPTION " "
    ::= { siPop3HistoryEntry 4 }

siPop3HistoryErrcode OBJECT-TYPE
    SYNTAX     Integer32 
    MAX-ACCESS read-only
    STATUS     current
    DESCRIPTION " "
    ::= { siPop3HistoryEntry 5 }

siPop3HistoryErrstring OBJECT-TYPE
    SYNTAX     DisplayString 
    MAX-ACCESS read-only
    STATUS     current
    DESCRIPTION " "
    ::= { siPop3HistoryEntry 6 }

siPop3HistoryDateAndTime OBJECT-TYPE
    SYNTAX     DateAndTime 
    MAX-ACCESS read-only
    STATUS     current
    DESCRIPTION " "
    ::= { siPop3HistoryEntry 7 }


-- The siSmtp Group

siSmtp OBJECT IDENTIFIER ::= { siServiceObjects 6 }
 
siSmtpTable OBJECT-TYPE
    SYNTAX     SEQUENCE OF SiSmtpEntry
    MAX-ACCESS not-accessible
    STATUS     current
    DESCRIPTION " "
    ::= { siSmtp 1 }

siSmtpEntry OBJECT-TYPE
    SYNTAX     SiSmtpEntry
    MAX-ACCESS not-accessible
    STATUS     current
    DESCRIPTION " "
    INDEX { siSmtpIndex }
    ::= { siSmtpTable 1 }

SiSmtpEntry ::= SEQUENCE {
    siSmtpIndex            Integer32,
    siSmtpServerName       DisplayString,
    siSmtpTimeout          Integer32,
    siSmtpPollInterval     Integer32,
    siSmtpPollNow          TruthValue,
    siSmtpMaxRows          Integer32,
    siSmtpTestUser         DisplayString,
    siSmtpErrcode          Integer32,
    siSmtpErrstring        DisplayString,
    siSmtpNameResolutionTime Integer32,
    siSmtpConnectTime      Integer32,
    siSmtpResponseTime     Integer32,
    siSmtpTrapOnFailure    TruthValue,
    siSmtpThreshold        Integer32,
    siSmtpRowStatus        RowStatus
}

siSmtpIndex OBJECT-TYPE
    SYNTAX     Integer32 (1..2147483647)
    MAX-ACCESS not-accessible
    STATUS     current
    DESCRIPTION " "
    ::= { siSmtpEntry 1 }

siSmtpServerName OBJECT-TYPE
    SYNTAX     DisplayString 
    MAX-ACCESS read-create
    STATUS     current
    DESCRIPTION " "
    ::= { siSmtpEntry 3 }

siSmtpTimeout OBJECT-TYPE
    SYNTAX     Integer32 (0..2147483647)
    MAX-ACCESS read-create
    STATUS     current
    DESCRIPTION " "
    ::= { siSmtpEntry 4 }

siSmtpPollInterval OBJECT-TYPE
    SYNTAX     Integer32 (0..2147483647)
    MAX-ACCESS read-create
    STATUS     current
    DESCRIPTION " "
    ::= { siSmtpEntry 5 }

siSmtpPollNow OBJECT-TYPE
    SYNTAX     TruthValue 
    MAX-ACCESS read-create
    STATUS     current
    DESCRIPTION " "
    ::= { siSmtpEntry 6 }

siSmtpMaxRows OBJECT-TYPE
    SYNTAX     Integer32 (0..2147483647)
    MAX-ACCESS read-create
    STATUS     current
    DESCRIPTION " "
    ::= { siSmtpEntry 7 }

siSmtpTestUser OBJECT-TYPE
    SYNTAX     DisplayString 
    MAX-ACCESS read-create
    STATUS     current
    DESCRIPTION " "
    ::= { siSmtpEntry 8 }

siSmtpErrcode OBJECT-TYPE
    SYNTAX     Integer32 
    MAX-ACCESS read-only
    STATUS     current
    DESCRIPTION " "
    ::= { siSmtpEntry 9 }

siSmtpErrstring OBJECT-TYPE
    SYNTAX     DisplayString 
    MAX-ACCESS read-only
    STATUS     current
    DESCRIPTION " "
    ::= { siSmtpEntry 10 }

siSmtpNameResolutionTime OBJECT-TYPE
    SYNTAX     Integer32 (0..2147483647)
    MAX-ACCESS read-only
    STATUS     current
    DESCRIPTION " "
    ::= { siSmtpEntry 11 }

siSmtpConnectTime OBJECT-TYPE
    SYNTAX     Integer32 (0..2147483647)
    MAX-ACCESS read-only
    STATUS     current
    DESCRIPTION " "
    ::= { siSmtpEntry 12 }

siSmtpResponseTime OBJECT-TYPE
    SYNTAX     Integer32 (0..2147483647)
    MAX-ACCESS read-only
    STATUS     current
    DESCRIPTION " "
    ::= { siSmtpEntry 13 }

siSmtpTrapOnFailure OBJECT-TYPE
    SYNTAX     TruthValue 
    MAX-ACCESS read-create
    STATUS     current
    DESCRIPTION " "
    ::= { siSmtpEntry 14 }

siSmtpThreshold OBJECT-TYPE
    SYNTAX     Integer32 (0..2147483647)
    MAX-ACCESS read-create
    STATUS     current
    DESCRIPTION " "
    ::= { siSmtpEntry 15 }

siSmtpRowStatus OBJECT-TYPE
    SYNTAX     RowStatus 
    MAX-ACCESS read-create
    STATUS     current
    DESCRIPTION " "
    ::= { siSmtpEntry 16 }

siSmtpHistoryTable OBJECT-TYPE
    SYNTAX     SEQUENCE OF SiSmtpHistoryEntry
    MAX-ACCESS not-accessible
    STATUS     current
    DESCRIPTION " "
    ::= { siSmtp 2 }

siSmtpHistoryEntry OBJECT-TYPE
    SYNTAX     SiSmtpHistoryEntry
    MAX-ACCESS not-accessible
    STATUS     current
    DESCRIPTION " "
    INDEX { siSmtpIndex, siSmtpHistoryIndex }
    ::= { siSmtpHistoryTable 1 }

SiSmtpHistoryEntry ::= SEQUENCE {
    siSmtpHistoryIndex     Integer32,
    siSmtpHistoryNameResolutionTime Integer32,
    siSmtpHistoryConnectTime Integer32,
    siSmtpHistoryResponseTime Integer32,
    siSmtpHistoryErrcode   Integer32,
    siSmtpHistoryErrstring DisplayString,
    siSmtpHistoryDateAndTime DateAndTime
}

siSmtpHistoryIndex OBJECT-TYPE
    SYNTAX     Integer32 (1..2147483647)
    MAX-ACCESS not-accessible
    STATUS     current
    DESCRIPTION " "
    ::= { siSmtpHistoryEntry 1 }

siSmtpHistoryNameResolutionTime OBJECT-TYPE
    SYNTAX     Integer32 (0..2147483647)
    MAX-ACCESS read-only
    STATUS     current
    DESCRIPTION " "
    ::= { siSmtpHistoryEntry 2 }

siSmtpHistoryConnectTime OBJECT-TYPE
    SYNTAX     Integer32 (0..2147483647)
    MAX-ACCESS read-only
    STATUS     current
    DESCRIPTION " "
    ::= { siSmtpHistoryEntry 3 }

siSmtpHistoryResponseTime OBJECT-TYPE
    SYNTAX     Integer32 (0..2147483647)
    MAX-ACCESS read-only
    STATUS     current
    DESCRIPTION " "
    ::= { siSmtpHistoryEntry 4 }

siSmtpHistoryErrcode OBJECT-TYPE
    SYNTAX     Integer32 
    MAX-ACCESS read-only
    STATUS     current
    DESCRIPTION " "
    ::= { siSmtpHistoryEntry 5 }

siSmtpHistoryErrstring OBJECT-TYPE
    SYNTAX     DisplayString 
    MAX-ACCESS read-only
    STATUS     current
    DESCRIPTION " "
    ::= { siSmtpHistoryEntry 6 }

siSmtpHistoryDateAndTime OBJECT-TYPE
    SYNTAX     DateAndTime 
    MAX-ACCESS read-only
    STATUS     current
    DESCRIPTION " "
    ::= { siSmtpHistoryEntry 7 }


-- The siSnmp Group

siSnmp OBJECT IDENTIFIER ::= { siServiceObjects 7 }
 
siSnmpTable OBJECT-TYPE
    SYNTAX     SEQUENCE OF SiSnmpEntry
    MAX-ACCESS not-accessible
    STATUS     current
    DESCRIPTION " "
    ::= { siSnmp 1 }

siSnmpEntry OBJECT-TYPE
    SYNTAX     SiSnmpEntry
    MAX-ACCESS not-accessible
    STATUS     current
    DESCRIPTION " "
    INDEX { siSnmpIndex }
    ::= { siSnmpTable 1 }

SiSnmpEntry ::= SEQUENCE {
    siSnmpIndex            Integer32,
    siSnmpServerName       DisplayString,
    siSnmpVersion          INTEGER,
    siSnmpMibVariable      OBJECT IDENTIFIER,
    siSnmpCommand          INTEGER,
    siSnmpTimeout          Integer32,
    siSnmpRetries          Integer32,
    siSnmpAuthInfo         DisplayString,
    siSnmpErrcode          Integer32,
    siSnmpErrstring        DisplayString,
    siSnmpNameResolutionTime Integer32,
    siSnmpResponseTime     Integer32,
    siSnmpPollInterval     Integer32,
    siSnmpPollNow          TruthValue,
    siSnmpMaxRows          Integer32,
    siSnmpTrapOnFailure    TruthValue,
    siSnmpThreshold        Integer32,
    siSnmpRowStatus        RowStatus
}

siSnmpIndex OBJECT-TYPE
    SYNTAX     Integer32 (1..2147483647)
    MAX-ACCESS not-accessible
    STATUS     current
    DESCRIPTION " "
    ::= { siSnmpEntry 1 }

siSnmpServerName OBJECT-TYPE
    SYNTAX     DisplayString 
    MAX-ACCESS read-create
    STATUS     current
    DESCRIPTION " "
    ::= { siSnmpEntry 3 }

siSnmpVersion OBJECT-TYPE
    SYNTAX     INTEGER{snmpv1(1),snmpv2(2),snmpv3(3)} 
    MAX-ACCESS read-create
    STATUS     current
    DESCRIPTION " "
    ::= { siSnmpEntry 4 }

siSnmpMibVariable OBJECT-TYPE
    SYNTAX     OBJECT IDENTIFIER
    MAX-ACCESS read-create
    STATUS     current
    DESCRIPTION " "
    ::= { siSnmpEntry 5 }

siSnmpCommand OBJECT-TYPE
    SYNTAX     INTEGER{set(1),get(2)} 
    MAX-ACCESS read-create
    STATUS     current
    DESCRIPTION " "
    ::= { siSnmpEntry 6 }

siSnmpTimeout OBJECT-TYPE
    SYNTAX     Integer32 (0..2147483647)
    MAX-ACCESS read-create
    STATUS     current
    DESCRIPTION " "
    ::= { siSnmpEntry 7 }

siSnmpRetries OBJECT-TYPE
    SYNTAX     Integer32 (0..2147483647)
    MAX-ACCESS read-create
    STATUS     current
    DESCRIPTION " "
    ::= { siSnmpEntry 8 }

siSnmpAuthInfo OBJECT-TYPE
    SYNTAX     DisplayString 
    MAX-ACCESS read-create
    STATUS     current
    DESCRIPTION " "
    ::= { siSnmpEntry 9 }

siSnmpErrcode OBJECT-TYPE
    SYNTAX     Integer32 
    MAX-ACCESS read-only
    STATUS     current
    DESCRIPTION " "
    ::= { siSnmpEntry 10 }

siSnmpErrstring OBJECT-TYPE
    SYNTAX     DisplayString 
    MAX-ACCESS read-only
    STATUS     current
    DESCRIPTION " "
    ::= { siSnmpEntry 11 }

siSnmpNameResolutionTime OBJECT-TYPE
    SYNTAX     Integer32 (0..2147483647)
    MAX-ACCESS read-only
    STATUS     current
    DESCRIPTION " "
    ::= { siSnmpEntry 12 }

siSnmpResponseTime OBJECT-TYPE
    SYNTAX     Integer32 (0..2147483647)
    MAX-ACCESS read-only
    STATUS     current
    DESCRIPTION " "
    ::= { siSnmpEntry 13 }

siSnmpPollInterval OBJECT-TYPE
    SYNTAX     Integer32 (0..2147483647)
    MAX-ACCESS read-create
    STATUS     current
    DESCRIPTION " "
    ::= { siSnmpEntry 14 }

siSnmpPollNow OBJECT-TYPE
    SYNTAX     TruthValue 
    MAX-ACCESS read-create
    STATUS     current
    DESCRIPTION " "
    ::= { siSnmpEntry 15 }

siSnmpMaxRows OBJECT-TYPE
    SYNTAX     Integer32 (0..2147483647)
    MAX-ACCESS read-create
    STATUS     current
    DESCRIPTION " "
    ::= { siSnmpEntry 16 }

siSnmpTrapOnFailure OBJECT-TYPE
    SYNTAX     TruthValue 
    MAX-ACCESS read-create
    STATUS     current
    DESCRIPTION " "
    ::= { siSnmpEntry 17 }

siSnmpThreshold OBJECT-TYPE
    SYNTAX     Integer32 (0..2147483647)
    MAX-ACCESS read-create
    STATUS     current
    DESCRIPTION " "
    ::= { siSnmpEntry 18 }

siSnmpRowStatus OBJECT-TYPE
    SYNTAX     RowStatus 
    MAX-ACCESS read-create
    STATUS     current
    DESCRIPTION " "
    ::= { siSnmpEntry 19 }

siSnmpHistoryTable OBJECT-TYPE
    SYNTAX     SEQUENCE OF SiSnmpHistoryEntry
    MAX-ACCESS not-accessible
    STATUS     current
    DESCRIPTION " "
    ::= { siSnmp 2 }

siSnmpHistoryEntry OBJECT-TYPE
    SYNTAX     SiSnmpHistoryEntry
    MAX-ACCESS not-accessible
    STATUS     current
    DESCRIPTION " "
    INDEX { siSnmpIndex, siSnmpHistoryIndex }
    ::= { siSnmpHistoryTable 1 }

SiSnmpHistoryEntry ::= SEQUENCE {
    siSnmpHistoryIndex     Integer32,
    siSnmpHistoryNameResolutionTime Integer32,
    siSnmpHistoryResponseTime Integer32,
    siSnmpHistoryErrcode   Integer32,
    siSnmpHistoryErrstring DisplayString,
    siSnmpHistoryDateAndTime DateAndTime,
    siSnmpHistoryNumRetries Integer32
}

siSnmpHistoryIndex OBJECT-TYPE
    SYNTAX     Integer32 (1..2147483647)
    MAX-ACCESS not-accessible
    STATUS     current
    DESCRIPTION " "
    ::= { siSnmpHistoryEntry 1 }

siSnmpHistoryNameResolutionTime OBJECT-TYPE
    SYNTAX     Integer32 (0..2147483647)
    MAX-ACCESS read-only
    STATUS     current
    DESCRIPTION " "
    ::= { siSnmpHistoryEntry 2 }

siSnmpHistoryResponseTime OBJECT-TYPE
    SYNTAX     Integer32 (0..2147483647)
    MAX-ACCESS read-only
    STATUS     current
    DESCRIPTION " "
    ::= { siSnmpHistoryEntry 3 }

siSnmpHistoryErrcode OBJECT-TYPE
    SYNTAX     Integer32 
    MAX-ACCESS read-only
    STATUS     current
    DESCRIPTION " "
    ::= { siSnmpHistoryEntry 4 }

siSnmpHistoryErrstring OBJECT-TYPE
    SYNTAX     DisplayString 
    MAX-ACCESS read-only
    STATUS     current
    DESCRIPTION " "
    ::= { siSnmpHistoryEntry 5 }

siSnmpHistoryDateAndTime OBJECT-TYPE
    SYNTAX     DateAndTime 
    MAX-ACCESS read-only
    STATUS     current
    DESCRIPTION " "
    ::= { siSnmpHistoryEntry 6 }

siSnmpHistoryNumRetries OBJECT-TYPE
    SYNTAX     Integer32 (0..2147483647)
    MAX-ACCESS read-only
    STATUS     current
    DESCRIPTION " "
    ::= { siSnmpHistoryEntry 7 }


-- The siNfs Group

siNfs OBJECT IDENTIFIER ::= { siServiceObjects 8 }
 
siNfsTable OBJECT-TYPE
    SYNTAX     SEQUENCE OF SiNfsEntry
    MAX-ACCESS not-accessible
    STATUS     current
    DESCRIPTION " "
    ::= { siNfs 1 }

siNfsEntry OBJECT-TYPE
    SYNTAX     SiNfsEntry
    MAX-ACCESS not-accessible
    STATUS     current
    DESCRIPTION " "
    INDEX { siNfsIndex }
    ::= { siNfsTable 1 }

SiNfsEntry ::= SEQUENCE {
    siNfsIndex             Integer32,
    siNfsServerName        DisplayString,
    siNfsTimeout           Integer32,
    siNfsPollInterval      Integer32,
    siNfsPollNow           TruthValue,
    siNfsMaxRows           Integer32,
    siNfsErrcode           Integer32,
    siNfsErrstring         DisplayString,
    siNfsNameResolutionTime Integer32,
    siNfsResponseTime      Integer32,
    siNfsTrapOnFailure     TruthValue,
    siNfsThreshold         Integer32,
    siNfsRowStatus         RowStatus
}

siNfsIndex OBJECT-TYPE
    SYNTAX     Integer32 (1..2147483647)
    MAX-ACCESS not-accessible
    STATUS     current
    DESCRIPTION " "
    ::= { siNfsEntry 1 }

siNfsServerName OBJECT-TYPE
    SYNTAX     DisplayString 
    MAX-ACCESS read-create
    STATUS     current
    DESCRIPTION " "
    ::= { siNfsEntry 3 }

siNfsTimeout OBJECT-TYPE
    SYNTAX     Integer32 (0..2147483647)
    MAX-ACCESS read-create
    STATUS     current
    DESCRIPTION " "
    ::= { siNfsEntry 4 }

siNfsPollInterval OBJECT-TYPE
    SYNTAX     Integer32 (0..2147483647)
    MAX-ACCESS read-create
    STATUS     current
    DESCRIPTION " "
    ::= { siNfsEntry 5 }

siNfsPollNow OBJECT-TYPE
    SYNTAX     TruthValue 
    MAX-ACCESS read-create
    STATUS     current
    DESCRIPTION " "
    ::= { siNfsEntry 6 }

siNfsMaxRows OBJECT-TYPE
    SYNTAX     Integer32 (0..2147483647)
    MAX-ACCESS read-create
    STATUS     current
    DESCRIPTION " "
    ::= { siNfsEntry 7 }

siNfsErrcode OBJECT-TYPE
    SYNTAX     Integer32 
    MAX-ACCESS read-only
    STATUS     current
    DESCRIPTION " "
    ::= { siNfsEntry 8 }

siNfsErrstring OBJECT-TYPE
    SYNTAX     DisplayString 
    MAX-ACCESS read-only
    STATUS     current
    DESCRIPTION " "
    ::= { siNfsEntry 9 }

siNfsNameResolutionTime OBJECT-TYPE
    SYNTAX     Integer32 (0..2147483647)
    MAX-ACCESS read-only
    STATUS     current
    DESCRIPTION " "
    ::= { siNfsEntry 10 }

siNfsResponseTime OBJECT-TYPE
    SYNTAX     Integer32 (0..2147483647)
    MAX-ACCESS read-only
    STATUS     current
    DESCRIPTION " "
    ::= { siNfsEntry 11 }

siNfsTrapOnFailure OBJECT-TYPE
    SYNTAX     TruthValue 
    MAX-ACCESS read-create
    STATUS     current
    DESCRIPTION " "
    ::= { siNfsEntry 12 }

siNfsThreshold OBJECT-TYPE
    SYNTAX     Integer32 (0..2147483647)
    MAX-ACCESS read-create
    STATUS     current
    DESCRIPTION " "
    ::= { siNfsEntry 13 }

siNfsRowStatus OBJECT-TYPE
    SYNTAX     RowStatus 
    MAX-ACCESS read-create
    STATUS     current
    DESCRIPTION " "
    ::= { siNfsEntry 14 }

siNfsHistoryTable OBJECT-TYPE
    SYNTAX     SEQUENCE OF SiNfsHistoryEntry
    MAX-ACCESS not-accessible
    STATUS     current
    DESCRIPTION " "
    ::= { siNfs 2 }

siNfsHistoryEntry OBJECT-TYPE
    SYNTAX     SiNfsHistoryEntry
    MAX-ACCESS not-accessible
    STATUS     current
    DESCRIPTION " "
    INDEX { siNfsIndex, siNfsHistoryIndex }
    ::= { siNfsHistoryTable 1 }

SiNfsHistoryEntry ::= SEQUENCE {
    siNfsHistoryIndex      Integer32,
    siNfsHistoryNameResolutionTime Integer32,
    siNfsHistoryResponseTime Integer32,
    siNfsHistoryErrcode    Integer32,
    siNfsHistoryErrstring  DisplayString,
    siNfsHistoryDateAndTime DateAndTime
}

siNfsHistoryIndex OBJECT-TYPE
    SYNTAX     Integer32 (1..2147483647)
    MAX-ACCESS not-accessible
    STATUS     current
    DESCRIPTION " "
    ::= { siNfsHistoryEntry 1 }

siNfsHistoryNameResolutionTime OBJECT-TYPE
    SYNTAX     Integer32 (0..2147483647)
    MAX-ACCESS read-only
    STATUS     current
    DESCRIPTION " "
    ::= { siNfsHistoryEntry 2 }

siNfsHistoryResponseTime OBJECT-TYPE
    SYNTAX     Integer32 (0..2147483647)
    MAX-ACCESS read-only
    STATUS     current
    DESCRIPTION " "
    ::= { siNfsHistoryEntry 3 }

siNfsHistoryErrcode OBJECT-TYPE
    SYNTAX     Integer32 
    MAX-ACCESS read-only
    STATUS     current
    DESCRIPTION " "
    ::= { siNfsHistoryEntry 4 }

siNfsHistoryErrstring OBJECT-TYPE
    SYNTAX     DisplayString 
    MAX-ACCESS read-only
    STATUS     current
    DESCRIPTION " "
    ::= { siNfsHistoryEntry 5 }

siNfsHistoryDateAndTime OBJECT-TYPE
    SYNTAX     DateAndTime 
    MAX-ACCESS read-only
    STATUS     current
    DESCRIPTION " "
    ::= { siNfsHistoryEntry 6 }


-- The siDhcp Group

siDhcp OBJECT IDENTIFIER ::= { siServiceObjects 9 }
 
siDhcpTable OBJECT-TYPE
    SYNTAX     SEQUENCE OF SiDhcpEntry
    MAX-ACCESS not-accessible
    STATUS     current
    DESCRIPTION " "
    ::= { siDhcp 1 }

siDhcpEntry OBJECT-TYPE
    SYNTAX     SiDhcpEntry
    MAX-ACCESS not-accessible
    STATUS     current
    DESCRIPTION " "
    INDEX { siDhcpIndex }
    ::= { siDhcpTable 1 }

SiDhcpEntry ::= SEQUENCE {
    siDhcpIndex            Integer32,
    siDhcpServerName       DisplayString,
    siDhcpTimeout          Integer32,
    siDhcpPollInterval     Integer32,
    siDhcpPollNow          TruthValue,
    siDhcpMaxRows          Integer32,
    siDhcpErrcode          Integer32,
    siDhcpErrstring        DisplayString,
    siDhcpNameResolutionTime Integer32,
    siDhcpResponseTime     Integer32,
    siDhcpTrapOnFailure    TruthValue,
    siDhcpThreshold        Integer32,
    siDhcpRowStatus        RowStatus
}

siDhcpIndex OBJECT-TYPE
    SYNTAX     Integer32 (1..2147483647)
    MAX-ACCESS not-accessible
    STATUS     current
    DESCRIPTION " "
    ::= { siDhcpEntry 1 }

siDhcpServerName OBJECT-TYPE
    SYNTAX     DisplayString 
    MAX-ACCESS read-create
    STATUS     current
    DESCRIPTION " "
    ::= { siDhcpEntry 3 }

siDhcpTimeout OBJECT-TYPE
    SYNTAX     Integer32 (0..2147483647)
    MAX-ACCESS read-create
    STATUS     current
    DESCRIPTION " "
    ::= { siDhcpEntry 4 }

siDhcpPollInterval OBJECT-TYPE
    SYNTAX     Integer32 (0..2147483647)
    MAX-ACCESS read-create
    STATUS     current
    DESCRIPTION " "
    ::= { siDhcpEntry 5 }

siDhcpPollNow OBJECT-TYPE
    SYNTAX     TruthValue 
    MAX-ACCESS read-create
    STATUS     current
    DESCRIPTION " "
    ::= { siDhcpEntry 6 }

siDhcpMaxRows OBJECT-TYPE
    SYNTAX     Integer32 (0..2147483647)
    MAX-ACCESS read-create
    STATUS     current
    DESCRIPTION " "
    ::= { siDhcpEntry 7 }

siDhcpErrcode OBJECT-TYPE
    SYNTAX     Integer32 
    MAX-ACCESS read-only
    STATUS     current
    DESCRIPTION " "
    ::= { siDhcpEntry 8 }

siDhcpErrstring OBJECT-TYPE
    SYNTAX     DisplayString 
    MAX-ACCESS read-only
    STATUS     current
    DESCRIPTION " "
    ::= { siDhcpEntry 9 }

siDhcpNameResolutionTime OBJECT-TYPE
    SYNTAX     Integer32 (0..2147483647)
    MAX-ACCESS read-only
    STATUS     current
    DESCRIPTION " "
    ::= { siDhcpEntry 10 }

siDhcpResponseTime OBJECT-TYPE
    SYNTAX     Integer32 (0..2147483647)
    MAX-ACCESS read-only
    STATUS     current
    DESCRIPTION " "
    ::= { siDhcpEntry 11 }

siDhcpTrapOnFailure OBJECT-TYPE
    SYNTAX     TruthValue 
    MAX-ACCESS read-create
    STATUS     current
    DESCRIPTION " "
    ::= { siDhcpEntry 12 }

siDhcpThreshold OBJECT-TYPE
    SYNTAX     Integer32 (0..2147483647)
    MAX-ACCESS read-create
    STATUS     current
    DESCRIPTION " "
    ::= { siDhcpEntry 13 }

siDhcpRowStatus OBJECT-TYPE
    SYNTAX     RowStatus 
    MAX-ACCESS read-create
    STATUS     current
    DESCRIPTION " "
    ::= { siDhcpEntry 14 }

siDhcpHistoryTable OBJECT-TYPE
    SYNTAX     SEQUENCE OF SiDhcpHistoryEntry
    MAX-ACCESS not-accessible
    STATUS     current
    DESCRIPTION " "
    ::= { siDhcp 2 }

siDhcpHistoryEntry OBJECT-TYPE
    SYNTAX     SiDhcpHistoryEntry
    MAX-ACCESS not-accessible
    STATUS     current
    DESCRIPTION " "
    INDEX { siDhcpIndex, siDhcpHistoryIndex }
    ::= { siDhcpHistoryTable 1 }

SiDhcpHistoryEntry ::= SEQUENCE {
    siDhcpHistoryIndex     Integer32,
    siDhcpHistoryNameResolutionTime Integer32,
    siDhcpHistoryResponseTime Integer32,
    siDhcpHistoryErrcode   Integer32,
    siDhcpHistoryErrstring DisplayString,
    siDhcpHistoryDateAndTime DateAndTime
}

siDhcpHistoryIndex OBJECT-TYPE
    SYNTAX     Integer32 (1..2147483647)
    MAX-ACCESS not-accessible
    STATUS     current
    DESCRIPTION " "
    ::= { siDhcpHistoryEntry 1 }

siDhcpHistoryNameResolutionTime OBJECT-TYPE
    SYNTAX     Integer32 (0..2147483647)
    MAX-ACCESS read-only
    STATUS     current
    DESCRIPTION " "
    ::= { siDhcpHistoryEntry 2 }

siDhcpHistoryResponseTime OBJECT-TYPE
    SYNTAX     Integer32 (0..2147483647)
    MAX-ACCESS read-only
    STATUS     current
    DESCRIPTION " "
    ::= { siDhcpHistoryEntry 3 }

siDhcpHistoryErrcode OBJECT-TYPE
    SYNTAX     Integer32 
    MAX-ACCESS read-only
    STATUS     current
    DESCRIPTION " "
    ::= { siDhcpHistoryEntry 4 }

siDhcpHistoryErrstring OBJECT-TYPE
    SYNTAX     DisplayString 
    MAX-ACCESS read-only
    STATUS     current
    DESCRIPTION " "
    ::= { siDhcpHistoryEntry 5 }

siDhcpHistoryDateAndTime OBJECT-TYPE
    SYNTAX     DateAndTime 
    MAX-ACCESS read-only
    STATUS     current
    DESCRIPTION " "
    ::= { siDhcpHistoryEntry 6 }


-- The siIcmp Group

siIcmp OBJECT IDENTIFIER ::= { siServiceObjects 10 }
 
siIcmpTable OBJECT-TYPE
    SYNTAX     SEQUENCE OF SiIcmpEntry
    MAX-ACCESS not-accessible
    STATUS     current
    DESCRIPTION " "
    ::= { siIcmp 1 }

siIcmpEntry OBJECT-TYPE
    SYNTAX     SiIcmpEntry
    MAX-ACCESS not-accessible
    STATUS     current
    DESCRIPTION " "
    INDEX { siIcmpIndex }
    ::= { siIcmpTable 1 }

SiIcmpEntry ::= SEQUENCE {
    siIcmpIndex            Integer32,
    siIcmpServerName       DisplayString,
    siIcmpTimeout          Integer32,
    siIcmpRetries          Integer32,
    siIcmpErrcode          INTEGER,
    siIcmpErrstring        DisplayString,
    siIcmpNameResolutionTime Integer32,
    siIcmpResponseTime     Integer32,
    siIcmpPollInterval     Integer32,
    siIcmpPollNow          TruthValue,
    siIcmpMaxRows          Integer32,
    siIcmpTrapOnFailure    TruthValue,
    siIcmpThreshold        Integer32,
    siIcmpRowStatus        RowStatus
}

siIcmpIndex OBJECT-TYPE
    SYNTAX     Integer32 (1..2147483647)
    MAX-ACCESS not-accessible
    STATUS     current
    DESCRIPTION " "
    ::= { siIcmpEntry 1 }

siIcmpServerName OBJECT-TYPE
    SYNTAX     DisplayString 
    MAX-ACCESS read-create
    STATUS     current
    DESCRIPTION " "
    ::= { siIcmpEntry 3 }

siIcmpTimeout OBJECT-TYPE
    SYNTAX     Integer32 (0..2147483647)
    MAX-ACCESS read-create
    STATUS     current
    DESCRIPTION " "
    ::= { siIcmpEntry 4 }

siIcmpRetries OBJECT-TYPE
    SYNTAX     Integer32 (0..2147483647)
    MAX-ACCESS read-create
    STATUS     current
    DESCRIPTION " "
    ::= { siIcmpEntry 5 }

siIcmpErrcode OBJECT-TYPE
    SYNTAX     INTEGER{inProgress(-1),noError(0),socketError(1),sendToError(2),recvFromError(3)} 
    MAX-ACCESS read-only
    STATUS     current
    DESCRIPTION " "
    ::= { siIcmpEntry 6 }

siIcmpErrstring OBJECT-TYPE
    SYNTAX     DisplayString 
    MAX-ACCESS read-only
    STATUS     current
    DESCRIPTION " "
    ::= { siIcmpEntry 7 }

siIcmpNameResolutionTime OBJECT-TYPE
    SYNTAX     Integer32 (0..2147483647)
    MAX-ACCESS read-only
    STATUS     current
    DESCRIPTION " "
    ::= { siIcmpEntry 8 }

siIcmpResponseTime OBJECT-TYPE
    SYNTAX     Integer32 (0..2147483647)
    MAX-ACCESS read-only
    STATUS     current
    DESCRIPTION " "
    ::= { siIcmpEntry 9 }

siIcmpPollInterval OBJECT-TYPE
    SYNTAX     Integer32 (0..2147483647)
    MAX-ACCESS read-create
    STATUS     current
    DESCRIPTION " "
    ::= { siIcmpEntry 10 }

siIcmpPollNow OBJECT-TYPE
    SYNTAX     TruthValue 
    MAX-ACCESS read-create
    STATUS     current
    DESCRIPTION " "
    ::= { siIcmpEntry 11 }

siIcmpMaxRows OBJECT-TYPE
    SYNTAX     Integer32 (0..2147483647)
    MAX-ACCESS read-create
    STATUS     current
    DESCRIPTION " "
    ::= { siIcmpEntry 12 }

siIcmpTrapOnFailure OBJECT-TYPE
    SYNTAX     TruthValue 
    MAX-ACCESS read-create
    STATUS     current
    DESCRIPTION " "
    ::= { siIcmpEntry 13 }

siIcmpThreshold OBJECT-TYPE
    SYNTAX     Integer32 (0..2147483647)
    MAX-ACCESS read-create
    STATUS     current
    DESCRIPTION " "
    ::= { siIcmpEntry 14 }

siIcmpRowStatus OBJECT-TYPE
    SYNTAX     RowStatus 
    MAX-ACCESS read-create
    STATUS     current
    DESCRIPTION " "
    ::= { siIcmpEntry 15 }

siIcmpHistoryTable OBJECT-TYPE
    SYNTAX     SEQUENCE OF SiIcmpHistoryEntry
    MAX-ACCESS not-accessible
    STATUS     current
    DESCRIPTION " "
    ::= { siIcmp 2 }

siIcmpHistoryEntry OBJECT-TYPE
    SYNTAX     SiIcmpHistoryEntry
    MAX-ACCESS not-accessible
    STATUS     current
    DESCRIPTION " "
    INDEX { siIcmpIndex, siIcmpHistoryIndex }
    ::= { siIcmpHistoryTable 1 }

SiIcmpHistoryEntry ::= SEQUENCE {
    siIcmpHistoryIndex     Integer32,
    siIcmpHistoryNameResolutionTime Integer32,
    siIcmpHistoryResponseTime Integer32,
    siIcmpHistoryErrcode   Integer32,
    siIcmpHistoryErrstring DisplayString,
    siIcmpHistoryDateAndTime DateAndTime,
    siIcmpHistoryNumRetries Integer32
}

siIcmpHistoryIndex OBJECT-TYPE
    SYNTAX     Integer32 (1..2147483647)
    MAX-ACCESS not-accessible
    STATUS     current
    DESCRIPTION " "
    ::= { siIcmpHistoryEntry 1 }

siIcmpHistoryNameResolutionTime OBJECT-TYPE
    SYNTAX     Integer32 (0..2147483647)
    MAX-ACCESS read-only
    STATUS     current
    DESCRIPTION " "
    ::= { siIcmpHistoryEntry 2 }

siIcmpHistoryResponseTime OBJECT-TYPE
    SYNTAX     Integer32 (0..2147483647)
    MAX-ACCESS read-only
    STATUS     current
    DESCRIPTION " "
    ::= { siIcmpHistoryEntry 3 }

siIcmpHistoryErrcode OBJECT-TYPE
    SYNTAX     Integer32 
    MAX-ACCESS read-only
    STATUS     current
    DESCRIPTION " "
    ::= { siIcmpHistoryEntry 4 }

siIcmpHistoryErrstring OBJECT-TYPE
    SYNTAX     DisplayString 
    MAX-ACCESS read-only
    STATUS     current
    DESCRIPTION " "
    ::= { siIcmpHistoryEntry 5 }

siIcmpHistoryDateAndTime OBJECT-TYPE
    SYNTAX     DateAndTime 
    MAX-ACCESS read-only
    STATUS     current
    DESCRIPTION " "
    ::= { siIcmpHistoryEntry 6 }

siIcmpHistoryNumRetries OBJECT-TYPE
    SYNTAX     Integer32 (0..2147483647)
    MAX-ACCESS read-only
    STATUS     current
    DESCRIPTION " "
    ::= { siIcmpHistoryEntry 7 }


-- The siUser Group

siUser OBJECT IDENTIFIER ::= { siServiceObjects 11 }
 
siUserTable OBJECT-TYPE
    SYNTAX     SEQUENCE OF SiUserEntry
    MAX-ACCESS not-accessible
    STATUS     current
    DESCRIPTION " "
    ::= { siUser 1 }

siUserEntry OBJECT-TYPE
    SYNTAX     SiUserEntry
    MAX-ACCESS not-accessible
    STATUS     current
    DESCRIPTION " "
    INDEX { siUserIndex }
    ::= { siUserTable 1 }

SiUserEntry ::= SEQUENCE {
    siUserIndex            Integer32,
    siUserServerName       DisplayString,
    siUserProtocol         INTEGER,
    siUserPort             Integer32,
    siUserTimeout          Integer32,
    siUserRetries          Integer32,
    siUserScriptName       DisplayString,
    siUserErrcode          Integer32,
    siUserErrstring        DisplayString,
    siUserNameResolutionTime Integer32,
    siUserConnectTime      Integer32,
    siUserResponseTime     Integer32,
    siUserPollInterval     Integer32,
    siUserPollNow          TruthValue,
    siUserMaxRows          Integer32,
    siUserTrapOnFailure    TruthValue,
    siUserThreshold        Integer32,
    siUserRowStatus        RowStatus
}

siUserIndex OBJECT-TYPE
    SYNTAX     Integer32 (1..2147483647)
    MAX-ACCESS not-accessible
    STATUS     current
    DESCRIPTION " "
    ::= { siUserEntry 1 }

siUserServerName OBJECT-TYPE
    SYNTAX     DisplayString 
    MAX-ACCESS read-create
    STATUS     current
    DESCRIPTION " "
    ::= { siUserEntry 3 }

siUserProtocol OBJECT-TYPE
    SYNTAX     INTEGER{tcp(1),udp(2)} 
    MAX-ACCESS read-create
    STATUS     current
    DESCRIPTION " "
    ::= { siUserEntry 4 }

siUserPort OBJECT-TYPE
    SYNTAX     Integer32 (0..2147483647)
    MAX-ACCESS read-create
    STATUS     current
    DESCRIPTION " "
    ::= { siUserEntry 5 }

siUserTimeout OBJECT-TYPE
    SYNTAX     Integer32 (0..2147483647)
    MAX-ACCESS read-create
    STATUS     current
    DESCRIPTION " "
    ::= { siUserEntry 6 }

siUserRetries OBJECT-TYPE
    SYNTAX     Integer32 (0..2147483647)
    MAX-ACCESS read-create
    STATUS     current
    DESCRIPTION " "
    ::= { siUserEntry 7 }

siUserScriptName OBJECT-TYPE
    SYNTAX     DisplayString 
    MAX-ACCESS read-create
    STATUS     current
    DESCRIPTION " "
    ::= { siUserEntry 8 }

siUserErrcode OBJECT-TYPE
    SYNTAX     Integer32 
    MAX-ACCESS read-only
    STATUS     current
    DESCRIPTION " "
    ::= { siUserEntry 9 }

siUserErrstring OBJECT-TYPE
    SYNTAX     DisplayString 
    MAX-ACCESS read-only
    STATUS     current
    DESCRIPTION " "
    ::= { siUserEntry 10 }

siUserNameResolutionTime OBJECT-TYPE
    SYNTAX     Integer32 (0..2147483647)
    MAX-ACCESS read-only
    STATUS     current
    DESCRIPTION " "
    ::= { siUserEntry 11 }

siUserConnectTime OBJECT-TYPE
    SYNTAX     Integer32 (0..2147483647)
    MAX-ACCESS read-only
    STATUS     current
    DESCRIPTION " "
    ::= { siUserEntry 12 }

siUserResponseTime OBJECT-TYPE
    SYNTAX     Integer32 (0..2147483647)
    MAX-ACCESS read-only
    STATUS     current
    DESCRIPTION " "
    ::= { siUserEntry 13 }

siUserPollInterval OBJECT-TYPE
    SYNTAX     Integer32 (0..2147483647)
    MAX-ACCESS read-create
    STATUS     current
    DESCRIPTION " "
    ::= { siUserEntry 14 }

siUserPollNow OBJECT-TYPE
    SYNTAX     TruthValue 
    MAX-ACCESS read-create
    STATUS     current
    DESCRIPTION " "
    ::= { siUserEntry 15 }

siUserMaxRows OBJECT-TYPE
    SYNTAX     Integer32 (0..2147483647)
    MAX-ACCESS read-create
    STATUS     current
    DESCRIPTION " "
    ::= { siUserEntry 16 }

siUserTrapOnFailure OBJECT-TYPE
    SYNTAX     TruthValue 
    MAX-ACCESS read-create
    STATUS     current
    DESCRIPTION " "
    ::= { siUserEntry 17 }

siUserThreshold OBJECT-TYPE
    SYNTAX     Integer32 (0..2147483647)
    MAX-ACCESS read-create
    STATUS     current
    DESCRIPTION " "
    ::= { siUserEntry 18 }

siUserRowStatus OBJECT-TYPE
    SYNTAX     RowStatus 
    MAX-ACCESS read-create
    STATUS     current
    DESCRIPTION " "
    ::= { siUserEntry 19 }

siUserHistoryTable OBJECT-TYPE
    SYNTAX     SEQUENCE OF SiUserHistoryEntry
    MAX-ACCESS not-accessible
    STATUS     current
    DESCRIPTION " "
    ::= { siUser 2 }

siUserHistoryEntry OBJECT-TYPE
    SYNTAX     SiUserHistoryEntry
    MAX-ACCESS not-accessible
    STATUS     current
    DESCRIPTION " "
    INDEX { siUserIndex, siUserHistoryIndex }
    ::= { siUserHistoryTable 1 }

SiUserHistoryEntry ::= SEQUENCE {
    siUserHistoryIndex     Integer32,
    siUserHistoryNameResolutionTime Integer32,
    siUserHistoryConnectTime Integer32,
    siUserHistoryResponseTime Integer32,
    siUserHistoryErrcode   Integer32,
    siUserHistoryErrstring DisplayString,
    siUserHistoryDateAndTime DateAndTime,
    siUserHistoryNumRetries Integer32
}

siUserHistoryIndex OBJECT-TYPE
    SYNTAX     Integer32 (1..2147483647)
    MAX-ACCESS not-accessible
    STATUS     current
    DESCRIPTION " "
    ::= { siUserHistoryEntry 1 }

siUserHistoryNameResolutionTime OBJECT-TYPE
    SYNTAX     Integer32 (0..2147483647)
    MAX-ACCESS read-only
    STATUS     current
    DESCRIPTION " "
    ::= { siUserHistoryEntry 2 }

siUserHistoryConnectTime OBJECT-TYPE
    SYNTAX     Integer32 (0..2147483647)
    MAX-ACCESS read-only
    STATUS     current
    DESCRIPTION " "
    ::= { siUserHistoryEntry 3 }

siUserHistoryResponseTime OBJECT-TYPE
    SYNTAX     Integer32 (0..2147483647)
    MAX-ACCESS read-only
    STATUS     current
    DESCRIPTION " "
    ::= { siUserHistoryEntry 4 }

siUserHistoryErrcode OBJECT-TYPE
    SYNTAX     Integer32 
    MAX-ACCESS read-only
    STATUS     current
    DESCRIPTION " "
    ::= { siUserHistoryEntry 5 }

siUserHistoryErrstring OBJECT-TYPE
    SYNTAX     DisplayString 
    MAX-ACCESS read-only
    STATUS     current
    DESCRIPTION " "
    ::= { siUserHistoryEntry 6 }

siUserHistoryDateAndTime OBJECT-TYPE
    SYNTAX     DateAndTime 
    MAX-ACCESS read-only
    STATUS     current
    DESCRIPTION " "
    ::= { siUserHistoryEntry 7 }

siUserHistoryNumRetries OBJECT-TYPE
    SYNTAX     Integer32 (0..2147483647)
    MAX-ACCESS read-only
    STATUS     current
    DESCRIPTION " "
    ::= { siUserHistoryEntry 8 }


-- The siServiceNotifications Group

siDnsFailure NOTIFICATION-TYPE
    OBJECTS     { siDnsServerName, siDnsErrcode, siDnsErrstring }
    STATUS      current
    DESCRIPTION " "
    ::= { siServiceNotifications 1 }

siFtpFailure NOTIFICATION-TYPE
    OBJECTS     { siFtpServerName, siFtpErrcode, siFtpErrstring }
    STATUS      current
    DESCRIPTION " "
    ::= { siServiceNotifications 2 }

siHttpFailure NOTIFICATION-TYPE
    OBJECTS     { siHttpServerName, siHttpErrcode, siHttpErrstring }
    STATUS      current
    DESCRIPTION " "
    ::= { siServiceNotifications 3 }

siNntpFailure NOTIFICATION-TYPE
    OBJECTS     { siNntpServerName, siNntpErrcode, siNntpErrstring }
    STATUS      current
    DESCRIPTION " "
    ::= { siServiceNotifications 4 }

siPop3Failure NOTIFICATION-TYPE
    OBJECTS     { siPop3ServerName, siPop3Errcode, siPop3Errstring }
    STATUS      current
    DESCRIPTION " "
    ::= { siServiceNotifications 5 }

siSmtpFailure NOTIFICATION-TYPE
    OBJECTS     { siSmtpServerName, siSmtpErrcode, siSmtpErrstring }
    STATUS      current
    DESCRIPTION " "
    ::= { siServiceNotifications 6 }

siSnmpFailure NOTIFICATION-TYPE
    OBJECTS     { siSnmpServerName, siSnmpErrcode, siSnmpErrstring }
    STATUS      current
    DESCRIPTION " "
    ::= { siServiceNotifications 7 }

siNfsFailure NOTIFICATION-TYPE
    OBJECTS     { siNfsServerName, siNfsErrcode, siNfsErrstring }
    STATUS      current
    DESCRIPTION " "
    ::= { siServiceNotifications 8 }

siDhcpFailure NOTIFICATION-TYPE
    OBJECTS     { siDhcpServerName, siDhcpErrcode, siDhcpErrstring }
    STATUS      current
    DESCRIPTION " "
    ::= { siServiceNotifications 9 }

siIcmpFailure NOTIFICATION-TYPE
    OBJECTS     { siIcmpServerName, siIcmpErrcode, siIcmpErrstring }
    STATUS      current
    DESCRIPTION " "
    ::= { siServiceNotifications 10 }

siUserFailure NOTIFICATION-TYPE
    OBJECTS     { siUserServerName, siUserErrcode, siUserErrstring }
    STATUS      current
    DESCRIPTION " "
    ::= { siServiceNotifications 11 }

siDnsAboveThreshold NOTIFICATION-TYPE
    OBJECTS     { siDnsServerName, siDnsResponseTime }
    STATUS      current
    DESCRIPTION " "
    ::= { siServiceNotifications 12 }

siFtpAboveThreshold NOTIFICATION-TYPE
    OBJECTS     { siFtpServerName, siFtpResponseTime }
    STATUS      current
    DESCRIPTION " "
    ::= { siServiceNotifications 13 }

siHttpAboveThreshold NOTIFICATION-TYPE
    OBJECTS     { siHttpServerName, siHttpResponseTime }
    STATUS      current
    DESCRIPTION " "
    ::= { siServiceNotifications 14 }

siNntpAboveThreshold NOTIFICATION-TYPE
    OBJECTS     { siNntpServerName, siNntpResponseTime }
    STATUS      current
    DESCRIPTION " "
    ::= { siServiceNotifications 15 }

siPop3AboveThreshold NOTIFICATION-TYPE
    OBJECTS     { siPop3ServerName, siPop3ResponseTime }
    STATUS      current
    DESCRIPTION " "
    ::= { siServiceNotifications 16 }

siSmtpAboveThreshold NOTIFICATION-TYPE
    OBJECTS     { siSmtpServerName, siSmtpResponseTime }
    STATUS      current
    DESCRIPTION " "
    ::= { siServiceNotifications 17 }

siSnmpAboveThreshold NOTIFICATION-TYPE
    OBJECTS     { siSnmpServerName, siSnmpResponseTime }
    STATUS      current
    DESCRIPTION " "
    ::= { siServiceNotifications 18 }

siNfsAboveThreshold NOTIFICATION-TYPE
    OBJECTS     { siNfsServerName, siNfsResponseTime }
    STATUS      current
    DESCRIPTION " "
    ::= { siServiceNotifications 19 }

siDhcpAboveThreshold NOTIFICATION-TYPE
    OBJECTS     { siDhcpServerName, siDhcpResponseTime }
    STATUS      current
    DESCRIPTION " "
    ::= { siServiceNotifications 20 }

siIcmpAboveThreshold NOTIFICATION-TYPE
    OBJECTS     { siIcmpServerName, siIcmpResponseTime }
    STATUS      current
    DESCRIPTION " "
    ::= { siServiceNotifications 21 }

siUserAboveThreshold NOTIFICATION-TYPE
    OBJECTS     { siUserServerName, siUserResponseTime }
    STATUS      current
    DESCRIPTION " "
    ::= { siServiceNotifications 22 }


END
