--
--
-- Copyright (C) 1996-2003 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--

--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--
--
-- SNMP Research, Inc. grants permission to load this MIB onto your SNMP
-- management stations for use in configuring and managing LT-301 devices
-- and LATIN agents from SNMP Research.  SNMP Research, Inc. does not grant
-- permission to make additional copies, or distribute these MIBs to others
-- without written permission from SNMP Research, Inc.
--
--

LT-HARDWARE-MIB DEFINITIONS ::= BEGIN

IMPORTS
    MODULE-IDENTITY, OBJECT-TYPE, NOTIFICATION-TYPE,
    ObjectName, Integer32, Counter32
        FROM SNMPv2-SMI;

ltHardware MODULE-IDENTITY
    LAST-UPDATED "9716191725"
    ORGANIZATION "SNMP Research, Inc."
    CONTACT-INFO "SNMP Research, Inc.
                  3001 Kimberlin Heights Road
                  Knoxville, TN  37920-9716   U.S.A.
                  Voice:   +1-865-573-1434
                  FAX:     +1-865-573-9197
                  E-mail:  support@snmp.com"
    DESCRIPTION  "This MIB specifies objects that provide information
                  about the LT-xxx hardware."
::= { snmpResearchMIBs 25}

snmpResearch                OBJECT IDENTIFIER ::= { enterprises 99 }
snmpResearchMIBs            OBJECT IDENTIFIER ::= { snmpResearch 12 }



--  Scalar objects.


 
ltHardwareModel OBJECT-TYPE
    SYNTAX     DisplayString 
    MAX-ACCESS read-only
    STATUS     current
    DESCRIPTION "Specifies the model number of the LT-xxx product."
::= { ltHardware 1 }
 
ltHardwareSerialNumber OBJECT-TYPE
    SYNTAX     Integer32
    MAX-ACCESS read-only
    STATUS     current
    DESCRIPTION "Specifies the serial number of the LT-xxx product."
::= { ltHardware 2 }
 
ltHardwareBoardRevision OBJECT-TYPE
    SYNTAX     Integer32
    MAX-ACCESS read-only
    STATUS     current
    DESCRIPTION "Specifies the circuit board revision number."
::= { ltHardware 3 }

ltHardwareProcessorRevision OBJECT-TYPE
    SYNTAX     Integer32
    MAX-ACCESS read-only
    STATUS     current
    DESCRIPTION "Specifies the CPU revision number."
::= { ltHardware 4 }
 
ltHardwareAgentRevision OBJECT-TYPE
    SYNTAX     DisplayString 
    MAX-ACCESS read-only
    STATUS     current
    DESCRIPTION "Specifies the agent software revision number."
::= { ltHardware 5 }
 
ltHardwareStrapSettings OBJECT-TYPE
    SYNTAX     Integer32
    MAX-ACCESS read-only
    STATUS     current
    DESCRIPTION "Retrieves the current settings of the option strapping
                 pins on the circuit board."
::= { ltHardware 6 }
 
ltHardwareSwitchSettings OBJECT-TYPE
    SYNTAX     Integer32
    MAX-ACCESS read-only
    STATUS     current
    DESCRIPTION "Retrieves the current settings of the DIP switches
                 on the circuit board."
::= { ltHardware 7 }
 
ltHardwareDisplaySettings OBJECT-TYPE
    SYNTAX     Integer32
    MAX-ACCESS read-write
    STATUS     current
    DESCRIPTION "When read, retrieves the value currently displayed on
                 the unit's display.  When written, the value written is
                 displayed on the unit's display."
::= { ltHardware 8 }
 
ltHardwareSerialEEPROMSize OBJECT-TYPE
    SYNTAX     Integer32
    MAX-ACCESS read-only
    STATUS     current
    DESCRIPTION "Specifies the number of bytes contained in the serial
                 EEPROM on the circuit board."
::= { ltHardware 9 }
 
ltHardwareSerialEEPROMFormat OBJECT-TYPE
    SYNTAX     Integer32
    MAX-ACCESS read-only
    STATUS     current
    DESCRIPTION "Specifies the format of the data contained in the serial
                 EEPROM on the circuit board."
::= { ltHardware 10 }



--  Information about the installed DRAM.



ltHardwareDRAMTable OBJECT-TYPE
    SYNTAX     SEQUENCE OF LTHardwareDRAMEntry
    MAX-ACCESS not-accessible
    STATUS     current
    DESCRIPTION "Provides information about the banks of dynamic RAM
                 (DRAM) installed."
::= { ltHardware 11 }

ltHardwareDRAMEntry OBJECT-TYPE
    SYNTAX     LTHardwareDRAMEntry
    MAX-ACCESS not-accessible
    STATUS     current
    DESCRIPTION "A row of the ltHardwareDRAMTable"
    INDEX { ltHardwareDRAMIndex }
::= { ltHardwareDRAMTable 1 }

LTHardwareDRAMEntry ::= SEQUENCE {
    ltHardwareDRAMIndex     Integer32,
    ltHardwareDRAMAmount    Integer32
}

ltHardwareDRAMIndex OBJECT-TYPE
    SYNTAX     Integer32 
    MAX-ACCESS not-accessible
    STATUS     current
    DESCRIPTION "Specifies the dynamic RAM (DRAM) bank number."
::= { ltHardwareDRAMEntry 1 }

ltHardwareDRAMAmount OBJECT-TYPE
    SYNTAX     Integer32 
    UNITS      "1024 bytes (kilobytes)"
    MAX-ACCESS read-only
    STATUS     current
    DESCRIPTION "Specifies the amount of dynamic RAM (DRAM) installed
                 in that DRAM bank."
::= { ltHardwareDRAMEntry 2 }



--  Information about the FLASH integrated circuits installed.



ltHardwareFLASHTable OBJECT-TYPE
    SYNTAX     SEQUENCE OF LTHardwareFLASHEntry
    MAX-ACCESS not-accessible
    STATUS     current
    DESCRIPTION "Provides information about the FLASH memory integrated
                 circuits (IC) installed." 
::= { ltHardware 12 }

ltHardwareFLASHEntry OBJECT-TYPE
    SYNTAX     LTHardwareFLASHEntry
    MAX-ACCESS not-accessible
    STATUS     current
    DESCRIPTION "A row of the ltHardwareFLASHTable"
    INDEX { ltHardwareFLASHIndex }
::= { ltHardwareFLASHTable 1 }

LTHardwareFLASHEntry ::= SEQUENCE {
    ltHardwareFLASHIndex    Integer32,
    ltHardwareFLASHType     OCTET STRING
}

ltHardwareFLASHIndex OBJECT-TYPE
    SYNTAX     Integer32 
    MAX-ACCESS not-accessible
    STATUS     current
    DESCRIPTION "Specifies the FLASH IC number."
::= { ltHardwareFLASHEntry 1 }

ltHardwareFLASHType OBJECT-TYPE
    SYNTAX     OCTET STRING (SIZE(0..255))
    MAX-ACCESS read-only
    STATUS     current
    DESCRIPTION "Returns the product ID bytes from the installed FLASH memory 
                 integrated circuits (ICs).  If FLASH memory is not installed,
                 this returns the first two bytes read from the installed 
                 memory IC.  If a memory IC is not installed, this returns
                 meaningless octets.  It is the user's responsibility to
                 interpret these octets and determine their validity."
::= { ltHardwareFLASHEntry 2 }


END
