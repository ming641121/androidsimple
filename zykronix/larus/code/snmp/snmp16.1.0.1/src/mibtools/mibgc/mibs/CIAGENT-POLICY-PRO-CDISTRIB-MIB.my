--
--
-- Copyright (C) 1999-2003 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--

--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--

   CIAGENT-POLICY-PRO-CDISTRIB-MIB DEFINITIONS ::= BEGIN

   IMPORTS
       MODULE-IDENTITY, NOTIFICATION-TYPE
           FROM SNMPv2-SMI;

   snmpResearch                OBJECT IDENTIFIER ::= { enterprises 99 }

   secureIntelligence          OBJECT IDENTIFIER ::= { snmpResearch 16 }

   enterpol                    OBJECT IDENTIFIER ::= { secureIntelligence 1 }

   enterpolEvents              OBJECT IDENTIFIER ::= { enterpol 1 }

   enterpolCdistribEvents      OBJECT IDENTIFIER ::= { enterpolEvents 2 }

   enterpolCIAgentPolicyProCdistribEvents MODULE-IDENTITY
       LAST-UPDATED "200206201532Z"
       ORGANIZATION "SNMP Research"
       CONTACT-INFO
              " Postal: SNMP Research
                        3001 Kimberlin Heights Road
                        Knoxville, TN  37920-9716

                   Tel: +1 865 573 1434
                   Fax: +1 865 573 9197

                E-mail: info@snmp.com"

       DESCRIPTION
               "Events of the Configuration Distributor Subsystem
               of EnterPol related to CIAgent PolicyPro."
       ::= { enterpolCdistribEvents 2 }

   ciaCdReasonCode NOTIFICATION-TYPE
       STATUS        current
       DESCRIPTION
               "ARL reason code indicates the error condition (if any)"
       ::= { enterpolCIAgentPolicyProCdistribEvents 1 }

   ciaCdNoResponseVarbindList NOTIFICATION-TYPE
       STATUS        current
       DESCRIPTION
               "No response VarBind list"
       ::= { enterpolCIAgentPolicyProCdistribEvents 2 }

   ciaCdNoAuthinfo NOTIFICATION-TYPE
       STATUS        current
       DESCRIPTION
               "No authentication information available for host"
       ::= { enterpolCIAgentPolicyProCdistribEvents 21 }

   ciaCdResourceUnavailable NOTIFICATION-TYPE
       STATUS        current
       DESCRIPTION
               "A failure occurred because a system resource was unavailable"
       ::= { enterpolCIAgentPolicyProCdistribEvents 22 }

   ciaCdPolicyFileVarbind NOTIFICATION-TYPE
       STATUS        current
       DESCRIPTION
               "An error occured while parsing VarBinds in the policy file"
       ::= { enterpolCIAgentPolicyProCdistribEvents 23 }

   ciaCdValueSubstitution NOTIFICATION-TYPE
       STATUS        current
       DESCRIPTION
               "An error occured during object value substitution"
       ::= { enterpolCIAgentPolicyProCdistribEvents 24 }

   ciaCdOidTree NOTIFICATION-TYPE
       STATUS        current
       DESCRIPTION
               "Some information is not unknown about a MIB object"
       ::= { enterpolCIAgentPolicyProCdistribEvents 25 }

   ciaCdInvalidConflictResolution NOTIFICATION-TYPE
       STATUS        current
       DESCRIPTION
               "Invalid conflict resolution"
       ::= { enterpolCIAgentPolicyProCdistribEvents 26 }

   ciaCdCantOpenIplistFile NOTIFICATION-TYPE
       STATUS        current
       DESCRIPTION
               "Could not open the IP address list file"
       ::= { enterpolCIAgentPolicyProCdistribEvents 27 }

   ciaCdCantOpenPolicyFile NOTIFICATION-TYPE
       STATUS        current
       DESCRIPTION
               "Could not open the policy file"
       ::= { enterpolCIAgentPolicyProCdistribEvents 28 }

   ciaCdCantAddSubstValue NOTIFICATION-TYPE
       STATUS        current
       DESCRIPTION
               "Error occurred while adding a value to the substitution list"
       ::= { enterpolCIAgentPolicyProCdistribEvents 29 }

   ciaCdIplistFileChangedAgents NOTIFICATION-TYPE
       STATUS        current
       DESCRIPTION
               "Since retry was scheduled, the list of agents changed"
       ::= { enterpolCIAgentPolicyProCdistribEvents 30 }

   ciaCdPolicyFileChangedRowstatus NOTIFICATION-TYPE
       STATUS        current
       DESCRIPTION
               "Since retry was scheduled, the list of RowStatus objects changed"
       ::= { enterpolCIAgentPolicyProCdistribEvents 31 }

   ciaCdPolicyFileChangedVblists NOTIFICATION-TYPE
       STATUS        current
       DESCRIPTION
               "Since retry was scheduled, the VarBinds in the policy changed"
       ::= { enterpolCIAgentPolicyProCdistribEvents 32 }

   ciaCdNothingToDistribute NOTIFICATION-TYPE
       STATUS        current
       DESCRIPTION
               "Nothing in the policy to distribute"
       ::= { enterpolCIAgentPolicyProCdistribEvents 33 }

   ciaCdCreateChangeqFailed NOTIFICATION-TYPE
       STATUS        current
       DESCRIPTION
               "Failed to create a change queue"
       ::= { enterpolCIAgentPolicyProCdistribEvents 34 }

   ciaCdRespDu NOTIFICATION-TYPE
       STATUS        current
       DESCRIPTION
               "Destination unreachable"
       ::= { enterpolCIAgentPolicyProCdistribEvents 128 }

   ciaCdRespDuNet NOTIFICATION-TYPE
       STATUS        current
       DESCRIPTION
               "Net unreachable"
       ::= { enterpolCIAgentPolicyProCdistribEvents 129 }

   ciaCdRespDuHost NOTIFICATION-TYPE
       STATUS        current
       DESCRIPTION
               "Host unreachable"
       ::= { enterpolCIAgentPolicyProCdistribEvents 130 }

   ciaCdRespDuProto NOTIFICATION-TYPE
       STATUS        current
       DESCRIPTION
               "Protocol unreachable"
       ::= { enterpolCIAgentPolicyProCdistribEvents 131 }

   ciaCdRespDuPort NOTIFICATION-TYPE
       STATUS        current
       DESCRIPTION
               "Port unreachable"
       ::= { enterpolCIAgentPolicyProCdistribEvents 132 }

   ciaCdRespDuFrag NOTIFICATION-TYPE
       STATUS        current
       DESCRIPTION
               "Fragmentation needed, don't fragment was set"
       ::= { enterpolCIAgentPolicyProCdistribEvents 133 }

   ciaCdRespDuSrcRt NOTIFICATION-TYPE
       STATUS        current
       DESCRIPTION
               "Source route failed"
       ::= { enterpolCIAgentPolicyProCdistribEvents 134 }

   ciaCdRespDuNetUnk NOTIFICATION-TYPE
       STATUS        current
       DESCRIPTION
               "Destination network unknown"
       ::= { enterpolCIAgentPolicyProCdistribEvents 135 }

   ciaCdRespDuHostUnk NOTIFICATION-TYPE
       STATUS        current
       DESCRIPTION
               "Destination host unknown"
       ::= { enterpolCIAgentPolicyProCdistribEvents 136 }

   ciaCdRespDuHostIso NOTIFICATION-TYPE
       STATUS        current
       DESCRIPTION
               "Source host isolated"
       ::= { enterpolCIAgentPolicyProCdistribEvents 137 }

   ciaCdRespDuNetAdmPro NOTIFICATION-TYPE
       STATUS        current
       DESCRIPTION
               "Communication w/ dest network administratively prohibited"
       ::= { enterpolCIAgentPolicyProCdistribEvents 138 }

   ciaCdRespDuHostAdmPro NOTIFICATION-TYPE
       STATUS        current
       DESCRIPTION
               "Communication w/ dest host administratively prohibited"
       ::= { enterpolCIAgentPolicyProCdistribEvents 139 }

   ciaCdRespDuNuTos NOTIFICATION-TYPE
       STATUS        current
       DESCRIPTION
               "Dest network unreachable for type of service"
       ::= { enterpolCIAgentPolicyProCdistribEvents 140 }

   ciaCdRespDuHuTos NOTIFICATION-TYPE
       STATUS        current
       DESCRIPTION
               "Dest host unreachable for type of service"
       ::= { enterpolCIAgentPolicyProCdistribEvents 141 }

   ciaCdRespDuComAdmPro NOTIFICATION-TYPE
       STATUS        current
       DESCRIPTION
               "Communication administratively prohibited"
       ::= { enterpolCIAgentPolicyProCdistribEvents 142 }

   ciaCdRespDuHostPrec NOTIFICATION-TYPE
       STATUS        current
       DESCRIPTION
               "Host precedence violation"
       ::= { enterpolCIAgentPolicyProCdistribEvents 143 }

   ciaCdRespDuPrecCutoff NOTIFICATION-TYPE
       STATUS        current
       DESCRIPTION
               "Precedence cutoff in effect"
       ::= { enterpolCIAgentPolicyProCdistribEvents 144 }

END
