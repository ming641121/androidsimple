--
--
-- Copyright (C) 1992-2003 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--

--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--
--


   --
   -- This MIB defines the organization of SNMP Research examples, present
   -- and future, covering the basics of SNMP in the area of scalar objects.
   --

   SCALAR-MIB DEFINITIONS ::= BEGIN

   snmpResearch                OBJECT IDENTIFIER ::= { enterprises 99 }

   snmpResearchMIBs            OBJECT IDENTIFIER ::= { snmpResearch 12 }

   srExamples                  OBJECT IDENTIFIER ::= { snmpResearchMIBs 19 }

   srBasics                    OBJECT IDENTIFIER ::= { srExamples 1 }

   srScalars                   OBJECT IDENTIFIER ::= { srBasics 1 }

   srScalarGet                 OBJECT IDENTIFIER ::= { srScalars 1 }

   srInteger                   OBJECT IDENTIFIER ::= { srScalarGet 1 }

   srOctetString               OBJECT IDENTIFIER ::= { srScalarGet 2 }

   srOID                       OBJECT IDENTIFIER ::= { srScalarGet 3 }

   srBITS                      OBJECT IDENTIFIER ::= { srScalarGet 4 }

   srIpAddress                 OBJECT IDENTIFIER ::= { srScalarGet 5 }

   srCounter32                 OBJECT IDENTIFIER ::= { srScalarGet 6 }

   srGauge32                   OBJECT IDENTIFIER ::= { srScalarGet 7 }

   srTimeTicks                 OBJECT IDENTIFIER ::= { srScalarGet 8 }

   srOpaque                    OBJECT IDENTIFIER ::= { srScalarGet 9 }

   srCounter64                 OBJECT IDENTIFIER ::= { srScalarGet 10 }

   srUnsigned32                OBJECT IDENTIFIER ::= { srScalarGet 11 }

   srDisplayString             OBJECT IDENTIFIER ::= { srScalarGet 12 }

   srPhysAddress               OBJECT IDENTIFIER ::= { srScalarGet 13 }

   srMacAddress                OBJECT IDENTIFIER ::= { srScalarGet 14 }

   srTruthValue                OBJECT IDENTIFIER ::= { srScalarGet 15 }

   srTestAndIncr               OBJECT IDENTIFIER ::= { srScalarGet 16 }

   srAutonomousType            OBJECT IDENTIFIER ::= { srScalarGet 17 }

   srVariablePointer           OBJECT IDENTIFIER ::= { srScalarGet 18 }

   srRowPointer                OBJECT IDENTIFIER ::= { srScalarGet 19 }

-- srRowStatus                 OBJECT IDENTIFIER ::= { srScalarGet 20 }

   srTimeStamp                 OBJECT IDENTIFIER ::= { srScalarGet 21 }

   srTimeInterval              OBJECT IDENTIFIER ::= { srScalarGet 22 }

   srDateAndTime               OBJECT IDENTIFIER ::= { srScalarGet 23 }

   srStorageType               OBJECT IDENTIFIER ::= { srScalarGet 24 }

   srTDomain                   OBJECT IDENTIFIER ::= { srScalarGet 25 }

   srTAddress                  OBJECT IDENTIFIER ::= { srScalarGet 26 }

   END
