--
--
-- Copyright (C) 1992-2003 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--

--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--
--


   TYPESETTER-MIB DEFINITIONS ::= BEGIN

   IMPORTS
       MODULE-IDENTITY, OBJECT-TYPE
           FROM SNMPv2-SMI;

   snmpResearch                OBJECT IDENTIFIER ::= { enterprises 99 }

   snmpResearchMIBs            OBJECT IDENTIFIER ::= { snmpResearch 12 }

   srExamples                  OBJECT IDENTIFIER ::= { snmpResearchMIBs 19 }

   srBasics                    OBJECT IDENTIFIER ::= { srExamples 1 }

   srScalars                   OBJECT IDENTIFIER ::= { srBasics 1 }

   srScalarGet                 OBJECT IDENTIFIER ::= { srScalars 1 }

   srOctetString               OBJECT IDENTIFIER ::= { srScalarGet 2 }

   typesetter MODULE-IDENTITY
       LAST-UPDATED "9501010000Z"
       ORGANIZATION "SNMP Research"
       CONTACT-INFO
              "         Technical Support

                Postal: SNMP Research
                        3001 Kimberlin Heights Road
                        Knoxville, TN  37920-9716

                   Tel: +1 865 573 1434
                   Fax: +1 865 573 9197

                E-mail: support@snmp.com
                   WWW: http://www.snmp.com"
       DESCRIPTION
               "An example MIB module to demonstrate the SNMP
               Research get method routine and the internal
	       representation of OctetString MIB objects."
       ::= { srOctetString 1 }


   tsBoldfaceBegin OBJECT-TYPE
       SYNTAX  OCTET STRING (SIZE (0..16))
       MAX-ACCESS  read-only
       STATUS  current
       DESCRIPTION
               "The ascii sequence which activates boldface type."
       ::= { typesetter 1 }

   tsBoldfaceEnd OBJECT-TYPE
       SYNTAX  OCTET STRING (SIZE (0..16))
       MAX-ACCESS  read-only
       STATUS  current
       DESCRIPTION
               "The ascii sequence which deactivates boldface type."
       ::= { typesetter 2 }

   tsNegativeBegin OBJECT-TYPE
       SYNTAX  OCTET STRING (SIZE (0..16))
       MAX-ACCESS  read-only
       STATUS  current
       DESCRIPTION
               "The ascii sequence which activates negative (reverse) type."
       ::= { typesetter 3 }

   tsNegativeEnd OBJECT-TYPE
       SYNTAX  OCTET STRING (SIZE (0..16))
       MAX-ACCESS  read-only
       STATUS  current
       DESCRIPTION
               "The ascii sequence which deactivates negative (reverse) type."
       ::= { typesetter 4 }

   tsUnderlineBegin OBJECT-TYPE
       SYNTAX  OCTET STRING (SIZE (0..16))
       MAX-ACCESS  read-only
       STATUS  current
       DESCRIPTION
               "The ascii sequence which activates underlined type."
       ::= { typesetter 5 }

   tsUnderlineEnd OBJECT-TYPE
       SYNTAX  OCTET STRING (SIZE (0..16))
       MAX-ACCESS  read-only
       STATUS  current
       DESCRIPTION
               "The ascii sequence which deactivates underlined type."
       ::= { typesetter 6 }

END
