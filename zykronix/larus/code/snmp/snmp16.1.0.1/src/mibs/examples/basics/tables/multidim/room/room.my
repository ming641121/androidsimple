--
--
-- Copyright (C) 1992-2003 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--

--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--
--


   ROOM-MIB DEFINITIONS ::= BEGIN

   IMPORTS
       MODULE-IDENTITY, OBJECT-TYPE, NOTIFICATION-TYPE,
       ObjectName, Integer32
           FROM SNMPv2-SMI
       DisplayString
           FROM SNMPv2-TC;

   snmpResearch                OBJECT IDENTIFIER ::= { enterprises 99 }

   snmpResearchMIBs            OBJECT IDENTIFIER ::= { snmpResearch 12 }

   srExamples                  OBJECT IDENTIFIER ::= { snmpResearchMIBs 19 }

   srBasics                    OBJECT IDENTIFIER ::= { srExamples 1 }

   srTables                    OBJECT IDENTIFIER ::= { srBasics 2 }

   srTableMultiDimensional     OBJECT IDENTIFIER ::= { srTables 2 }

   room MODULE-IDENTITY
       LAST-UPDATED "9603050000Z"
       ORGANIZATION "SNMP Research"
       CONTACT-INFO
              "         Technical Support

                Postal: SNMP Research
                        3001 Kimberlin Heights Road
                        Knoxville, TN  37920-9716

                   Tel: +1 865 573 1434
                   Fax: +1 865 573 9197

                E-mail: support@snmp.com
                   WWW: http://www.snmp.com" 
       DESCRIPTION
               "An example MIB module to demonstrate the SNMP
               Research method routines for conceptual tables
	       having more than one index."
       ::= { srTableMultiDimensional 1 }


-- The roomDetector Group

   roomDetector OBJECT IDENTIFIER ::= { room 1 }

   roomDetectorTable OBJECT-TYPE
       SYNTAX     SEQUENCE OF RoomDetectorEntry
       MAX-ACCESS not-accessible
       STATUS     current
       DESCRIPTION
	       "The table of detectors to monitor."
       ::= { roomDetector 1 }
   
   roomDetectorEntry OBJECT-TYPE
       SYNTAX     RoomDetectorEntry
       MAX-ACCESS not-accessible
       STATUS     current
       DESCRIPTION
	       "The information about the detectors in one room."
       INDEX { roomDetectorFloorIndex,
               roomDetectorHallIndex,
	       roomDetectorRoomIndex }
       ::= { roomDetectorTable 1 }
   
   RoomDetectorEntry ::= SEQUENCE {
       roomDetectorFloorIndex Integer32,
       roomDetectorHallIndex  Integer32,
       roomDetectorRoomIndex  Integer32,
       roomDetectorRoomName   DisplayString,
       roomDetectorMotion     INTEGER,
       roomDetectorSmoke      INTEGER,
       roomDetectorGas        Integer32
   }
   
   roomDetectorFloorIndex OBJECT-TYPE
       SYNTAX     Integer32 
       MAX-ACCESS not-accessible
       STATUS     current
       DESCRIPTION
	       "The building floor number."
       ::= { roomDetectorEntry 1 }
   
   roomDetectorHallIndex OBJECT-TYPE
       SYNTAX     Integer32 
       MAX-ACCESS not-accessible
       STATUS     current
       DESCRIPTION
	       "The hall number on a particular floor."
       ::= { roomDetectorEntry 2 }
   
   roomDetectorRoomIndex OBJECT-TYPE
       SYNTAX     Integer32 
       MAX-ACCESS not-accessible
       STATUS     current
       DESCRIPTION
	       "The room number in a particular hall."
       ::= { roomDetectorEntry 3 }
   
   roomDetectorRoomName OBJECT-TYPE
       SYNTAX     DisplayString (SIZE (1..255))
       MAX-ACCESS read-only
       STATUS     current
       DESCRIPTION
	       "The name of the room."
       ::= { roomDetectorEntry 4 }
   
   roomDetectorMotion OBJECT-TYPE
       SYNTAX     INTEGER { no-movement(1), movement(2) }
       MAX-ACCESS read-only
       STATUS     current
       DESCRIPTION
	       "The presence of motion within range of the detector."
       ::= { roomDetectorEntry 5 }
   
   roomDetectorSmoke OBJECT-TYPE
       SYNTAX     INTEGER { no-smoke(1), smoke(2) }
       MAX-ACCESS read-only
       STATUS     current
       DESCRIPTION
	       "The presence of smoke within range of the detector."
       ::= { roomDetectorEntry 6 }
   
   roomDetectorGas OBJECT-TYPE
       SYNTAX     Integer32 
       MAX-ACCESS read-only
       STATUS     current
       DESCRIPTION
	       "The amount of gas present in the air (parts per million)."
       ::= { roomDetectorEntry 7 }
   
END
