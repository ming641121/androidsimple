--
--
-- Copyright (C) 1992-2003 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--

--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--
--


   SURGE-PROTECTOR-MIB DEFINITIONS ::= BEGIN

   IMPORTS
       MODULE-IDENTITY, OBJECT-TYPE
           FROM SNMPv2-SMI;

   snmpResearch                OBJECT IDENTIFIER ::= { enterprises 99 }

   snmpResearchMIBs            OBJECT IDENTIFIER ::= { snmpResearch 12 }

   srExamples                  OBJECT IDENTIFIER ::= { snmpResearchMIBs 19 }

   srBasics                    OBJECT IDENTIFIER ::= { srExamples 1 }

   srTraps                     OBJECT IDENTIFIER ::= { srBasics 3 }

   surgeProtector MODULE-IDENTITY
       LAST-UPDATED "9502160000Z"
       ORGANIZATION "SNMP Research"
       CONTACT-INFO
              "         Technical Support

                Postal: SNMP Research
                        3001 Kimberlin Heights Road
                        Knoxville, TN  37920-9716

                   Tel: +1 865 573 1434
                   Fax: +1 865 573 9197

                E-mail: support@snmp.com
                   WWW: http://www.snmp.com"
       DESCRIPTION
               "An example MIB module to demonstrate the SNMP
               Research interface for sending traps."
       ::= { srTraps 1 }


   surgeSpikeCount OBJECT-TYPE
       SYNTAX  Counter32
       MAX-ACCESS  read-only
       STATUS  current
       DESCRIPTION
               "The number of recorded spikes since the surge protector
	       was connected to power."
       ::= { surgeProtector 1 }

   surgeSpikeVoltageLast OBJECT-TYPE
       SYNTAX  INTEGER (-2147483648..2147483647)
       UNITS   "milliVolts"
       MAX-ACCESS  read-only
       STATUS  current
       DESCRIPTION
               "The recorded voltage of the last power spike."
       ::= { surgeProtector 2 }

   surgeBreakerStatus OBJECT-TYPE
       SYNTAX  INTEGER { closed(1), open(2), unknown(3) }
       MAX-ACCESS  read-only
       STATUS  current
       DESCRIPTION
               "The position of the circuit breaker.  A value of
	       unknown(3) indicates potential damange to the circuit
	       breaker and that the surge protector should be replaced."
       ::= { surgeProtector 3 }


   -- surgeProtector Traps

   surgeSpikeAlarm NOTIFICATION-TYPE
       STATUS  current
       DESCRIPTION
	       "An event that is generated when the circuit breaker
	       detects a power spike."
       ::= { surgeProtector 4 }

   surgeBreakerAlarm NOTIFICATION-TYPE
       OBJECTS { surgeBreakerStatus }
       STATUS  current
       DESCRIPTION
	       "An event that is generated when the state of the
	       circuit breaker changes."
       ::= { surgeProtector 5 }

END
