VENDORS-MIB DEFINITIONS ::= BEGIN

proteon                           OBJECT IDENTIFIER ::= { enterprises 1 }
ibm                               OBJECT IDENTIFIER ::= { enterprises 2 }
cmu                               OBJECT IDENTIFIER ::= { enterprises 3 }
unix                              OBJECT IDENTIFIER ::= { enterprises 4 }
acc                               OBJECT IDENTIFIER ::= { enterprises 5 }
twg                               OBJECT IDENTIFIER ::= { enterprises 6 }
cayman                            OBJECT IDENTIFIER ::= { enterprises 7 }
psi                               OBJECT IDENTIFIER ::= { enterprises 8 }
cisco                             OBJECT IDENTIFIER ::= { enterprises 9 }
nsc                               OBJECT IDENTIFIER ::= { enterprises 10 }
hewlettPackard                    OBJECT IDENTIFIER ::= { enterprises 11 }
epilogue                          OBJECT IDENTIFIER ::= { enterprises 12 }
uOfTennessee                      OBJECT IDENTIFIER ::= { enterprises 13 }
bbn                               OBJECT IDENTIFIER ::= { enterprises 14 }
xylogics                          OBJECT IDENTIFIER ::= { enterprises 15 }
timeplex                          OBJECT IDENTIFIER ::= { enterprises 16 }
canstar                           OBJECT IDENTIFIER ::= { enterprises 17 }
wellfleet                         OBJECT IDENTIFIER ::= { enterprises 18 }
trw                               OBJECT IDENTIFIER ::= { enterprises 19 }
mit                               OBJECT IDENTIFIER ::= { enterprises 20 }
eon                               OBJECT IDENTIFIER ::= { enterprises 21 }
spartacus                         OBJECT IDENTIFIER ::= { enterprises 22 }
novell                            OBJECT IDENTIFIER ::= { enterprises 23 }
spiderSystems                     OBJECT IDENTIFIER ::= { enterprises 24 }
nsfnet                            OBJECT IDENTIFIER ::= { enterprises 25 }
hughesLANSystems                  OBJECT IDENTIFIER ::= { enterprises 26 }
intergraph                        OBJECT IDENTIFIER ::= { enterprises 27 }
interlan                          OBJECT IDENTIFIER ::= { enterprises 28 }
vitalinkCommunications            OBJECT IDENTIFIER ::= { enterprises 29 }
ulana                             OBJECT IDENTIFIER ::= { enterprises 30 }
nswc                              OBJECT IDENTIFIER ::= { enterprises 31 }
santaCruzOperation                OBJECT IDENTIFIER ::= { enterprises 32 }
xyplex                            OBJECT IDENTIFIER ::= { enterprises 33 }
cray                              OBJECT IDENTIFIER ::= { enterprises 34 }
bellNorthernResearch              OBJECT IDENTIFIER ::= { enterprises 35 }
dec                               OBJECT IDENTIFIER ::= { enterprises 36 }
touch                             OBJECT IDENTIFIER ::= { enterprises 37 }
networkResearchCorp               OBJECT IDENTIFIER ::= { enterprises 38 }
baylorCollegeOfMedicine           OBJECT IDENTIFIER ::= { enterprises 39 }
nmfeccLLNL                        OBJECT IDENTIFIER ::= { enterprises 40 }
sri                               OBJECT IDENTIFIER ::= { enterprises 41 }
sunMicrosystems                   OBJECT IDENTIFIER ::= { enterprises 42 }
threeCom                          OBJECT IDENTIFIER ::= { enterprises 43 }
cmc                               OBJECT IDENTIFIER ::= { enterprises 44 }
synoptics                         OBJECT IDENTIFIER ::= { enterprises 45 }
cheyenneSoftware                  OBJECT IDENTIFIER ::= { enterprises 46 }
primeComputer                     OBJECT IDENTIFIER ::= { enterprises 47 }
mcncNorthCarolina                 OBJECT IDENTIFIER ::= { enterprises 48 }
chipcom                           OBJECT IDENTIFIER ::= { enterprises 49 }
opticalDataSystems                OBJECT IDENTIFIER ::= { enterprises 50 }
gated                             OBJECT IDENTIFIER ::= { enterprises 51 }
cabletronSystems                  OBJECT IDENTIFIER ::= { enterprises 52 }
apolloComputers                   OBJECT IDENTIFIER ::= { enterprises 53 }
desktalkSystems                   OBJECT IDENTIFIER ::= { enterprises 54 }
ssds                              OBJECT IDENTIFIER ::= { enterprises 55 }
castleRockComputing               OBJECT IDENTIFIER ::= { enterprises 56 }
mipsComputerSystems               OBJECT IDENTIFIER ::= { enterprises 57 }
tgv                               OBJECT IDENTIFIER ::= { enterprises 58 }
siliconGraphics                   OBJECT IDENTIFIER ::= { enterprises 59 }
universityOfBritishColumbia       OBJECT IDENTIFIER ::= { enterprises 60 }
merit                             OBJECT IDENTIFIER ::= { enterprises 61 }
netedge                           OBJECT IDENTIFIER ::= { enterprises 62 }
appleComputer                     OBJECT IDENTIFIER ::= { enterprises 63 }
gandalf                           OBJECT IDENTIFIER ::= { enterprises 64 }
dartmouth                         OBJECT IDENTIFIER ::= { enterprises 65 }
davidSystems                      OBJECT IDENTIFIER ::= { enterprises 66 }
reuter                            OBJECT IDENTIFIER ::= { enterprises 67 }
cornell                           OBJECT IDENTIFIER ::= { enterprises 68 }
lms                               OBJECT IDENTIFIER ::= { enterprises 69 }
locusComputingCorp                OBJECT IDENTIFIER ::= { enterprises 70 }
nasa                              OBJECT IDENTIFIER ::= { enterprises 71 }
retix                             OBJECT IDENTIFIER ::= { enterprises 72 }
boeing                            OBJECT IDENTIFIER ::= { enterprises 73 }
atAndt                            OBJECT IDENTIFIER ::= { enterprises 74 }
ungermannBass                     OBJECT IDENTIFIER ::= { enterprises 75 }
digitalAnalysisCorporation        OBJECT IDENTIFIER ::= { enterprises 76 }
lanManager                        OBJECT IDENTIFIER ::= { enterprises 77 }
netlabs                           OBJECT IDENTIFIER ::= { enterprises 78 }
icl                               OBJECT IDENTIFIER ::= { enterprises 79 }
auspexSystems                     OBJECT IDENTIFIER ::= { enterprises 80 }
lannetCompany                     OBJECT IDENTIFIER ::= { enterprises 81 }
networkComputingDevices           OBJECT IDENTIFIER ::= { enterprises 82 }
raycomSystems                     OBJECT IDENTIFIER ::= { enterprises 83 }
pirelliFocom                      OBJECT IDENTIFIER ::= { enterprises 84 }
databilitySoftwareSystems         OBJECT IDENTIFIER ::= { enterprises 85 }
networkApplicationTechnology      OBJECT IDENTIFIER ::= { enterprises 86 }
link                              OBJECT IDENTIFIER ::= { enterprises 87 }
nyu                               OBJECT IDENTIFIER ::= { enterprises 88 }
rnd                               OBJECT IDENTIFIER ::= { enterprises 89 }
interconSystemsCorporation        OBJECT IDENTIFIER ::= { enterprises 90 }
coralNetworkCorporation           OBJECT IDENTIFIER ::= { enterprises 91 }
websterComputerCorporation        OBJECT IDENTIFIER ::= { enterprises 92 }
frontierTechnologiesCorporation   OBJECT IDENTIFIER ::= { enterprises 93 }
nokiaDataCommunications           OBJECT IDENTIFIER ::= { enterprises 94 }
allenBradelyCompany               OBJECT IDENTIFIER ::= { enterprises 95 }
cern                              OBJECT IDENTIFIER ::= { enterprises 96 }
sigmaNetworkSystems               OBJECT IDENTIFIER ::= { enterprises 97 }
emergingTechnologies              OBJECT IDENTIFIER ::= { enterprises 98 }
snmpResearch                      OBJECT IDENTIFIER ::= { enterprises 99 }
ohioStateUniversity               OBJECT IDENTIFIER ::= { enterprises 100 }
ultraNetworkTechnologies          OBJECT IDENTIFIER ::= { enterprises 101 }
microcom                          OBJECT IDENTIFIER ::= { enterprises 102 }
lockheedMartin                    OBJECT IDENTIFIER ::= { enterprises 103 }
microTechnology                   OBJECT IDENTIFIER ::= { enterprises 104 }
processSoftwareCorporation        OBJECT IDENTIFIER ::= { enterprises 105 }
dataGeneralCorporation            OBJECT IDENTIFIER ::= { enterprises 106 }
bullCompany                       OBJECT IDENTIFIER ::= { enterprises 107 }
emulexCorporation                 OBJECT IDENTIFIER ::= { enterprises 108 }
warwickUniversityComputingServices OBJECT IDENTIFIER ::= { enterprises 109 }
networkGeneralCorporation         OBJECT IDENTIFIER ::= { enterprises 110 }
oracle                            OBJECT IDENTIFIER ::= { enterprises 111 }
controlDataCorporation            OBJECT IDENTIFIER ::= { enterprises 112 }
hughesAircraftCompany             OBJECT IDENTIFIER ::= { enterprises 113 }
synernetics                       OBJECT IDENTIFIER ::= { enterprises 114 }
mitre                             OBJECT IDENTIFIER ::= { enterprises 115 }
hitachi                           OBJECT IDENTIFIER ::= { enterprises 116 }
telebit                           OBJECT IDENTIFIER ::= { enterprises 117 }
salomonTechnologyServices         OBJECT IDENTIFIER ::= { enterprises 118 }
necCorporation                    OBJECT IDENTIFIER ::= { enterprises 119 }
fibermux                          OBJECT IDENTIFIER ::= { enterprises 120 }
ftpSoftware                       OBJECT IDENTIFIER ::= { enterprises 121 }
sony                              OBJECT IDENTIFIER ::= { enterprises 122 }
newbridgeNetworksCorporation      OBJECT IDENTIFIER ::= { enterprises 123 }
racalMilgoInformationSystems      OBJECT IDENTIFIER ::= { enterprises 124 }
crSYSTEMS                         OBJECT IDENTIFIER ::= { enterprises 125 }
dsetCorporation                   OBJECT IDENTIFIER ::= { enterprises 126 }
computone                         OBJECT IDENTIFIER ::= { enterprises 127 }
tektronix                         OBJECT IDENTIFIER ::= { enterprises 128 }
interactiveSystemsCorporation     OBJECT IDENTIFIER ::= { enterprises 129 }
banyanSystems                     OBJECT IDENTIFIER ::= { enterprises 130 }
sintromDatanetLimited             OBJECT IDENTIFIER ::= { enterprises 131 }
bellCanada                        OBJECT IDENTIFIER ::= { enterprises 132 }
crosscommCorporation              OBJECT IDENTIFIER ::= { enterprises 133 }
riceUniversity                    OBJECT IDENTIFIER ::= { enterprises 134 }
t3plusNetworking                  OBJECT IDENTIFIER ::= { enterprises 135 }
concurrentComputerCorporation     OBJECT IDENTIFIER ::= { enterprises 136 }
basser                            OBJECT IDENTIFIER ::= { enterprises 137 }
luxcom                            OBJECT IDENTIFIER ::= { enterprises 138 }
artel                             OBJECT IDENTIFIER ::= { enterprises 139 }
independenceTechnologies          OBJECT IDENTIFIER ::= { enterprises 140 }
frontierSoftwareDevelopment       OBJECT IDENTIFIER ::= { enterprises 141 }
digitalComputerLimited            OBJECT IDENTIFIER ::= { enterprises 142 }
eyring                            OBJECT IDENTIFIER ::= { enterprises 143 }
caseCommunications                OBJECT IDENTIFIER ::= { enterprises 144 }
penrilDataComm                    OBJECT IDENTIFIER ::= { enterprises 145 }
americanAirlines                  OBJECT IDENTIFIER ::= { enterprises 146 }
sequentComputerSystems            OBJECT IDENTIFIER ::= { enterprises 147 }
bellcore                          OBJECT IDENTIFIER ::= { enterprises 148 }
konkordCommunications             OBJECT IDENTIFIER ::= { enterprises 149 }
universityOfWashington            OBJECT IDENTIFIER ::= { enterprises 150 }
develcon                          OBJECT IDENTIFIER ::= { enterprises 151 }
solarixSystems                    OBJECT IDENTIFIER ::= { enterprises 152 }
unifiCommunicationsCorp           OBJECT IDENTIFIER ::= { enterprises 153 }
roadnet                           OBJECT IDENTIFIER ::= { enterprises 154 }
networkSystemsCorp                OBJECT IDENTIFIER ::= { enterprises 155 }
ene                               OBJECT IDENTIFIER ::= { enterprises 156 }
danskDataElektronikAS             OBJECT IDENTIFIER ::= { enterprises 157 }
morningStarTechnologies           OBJECT IDENTIFIER ::= { enterprises 158 }
dupontEOP                         OBJECT IDENTIFIER ::= { enterprises 159 }
legatoSystems                     OBJECT IDENTIFIER ::= { enterprises 160 }
motorola                          OBJECT IDENTIFIER ::= { enterprises 161 }
europeanSpaceAgency               OBJECT IDENTIFIER ::= { enterprises 162 }
bim                               OBJECT IDENTIFIER ::= { enterprises 163 }
radDataCommunications             OBJECT IDENTIFIER ::= { enterprises 164 }
intellicom                        OBJECT IDENTIFIER ::= { enterprises 165 }
shivaCorporation                  OBJECT IDENTIFIER ::= { enterprises 166 }
fujikuraAmerica                   OBJECT IDENTIFIER ::= { enterprises 167 }
xlntDesignsINC                    OBJECT IDENTIFIER ::= { enterprises 168 }
tandemComputers                   OBJECT IDENTIFIER ::= { enterprises 169 }
bicc                              OBJECT IDENTIFIER ::= { enterprises 170 }
dLinkSystems                      OBJECT IDENTIFIER ::= { enterprises 171 }
amp                               OBJECT IDENTIFIER ::= { enterprises 172 }
netlink                           OBJECT IDENTIFIER ::= { enterprises 173 }
cItohElectronics                  OBJECT IDENTIFIER ::= { enterprises 174 }
sumitomoElectricIndustries        OBJECT IDENTIFIER ::= { enterprises 175 }
dhlSystems                        OBJECT IDENTIFIER ::= { enterprises 176 }
networkEquipmentTechnologies      OBJECT IDENTIFIER ::= { enterprises 177 }
aptecComputerSystems              OBJECT IDENTIFIER ::= { enterprises 178 }
schneiderAndKochAndCo             OBJECT IDENTIFIER ::= { enterprises 179 }
hillAirForceBase                  OBJECT IDENTIFIER ::= { enterprises 180 }
adcKentrox                        OBJECT IDENTIFIER ::= { enterprises 181 }
japanRadioCo                      OBJECT IDENTIFIER ::= { enterprises 182 }
versitron                         OBJECT IDENTIFIER ::= { enterprises 183 }
telecommunicationSystems          OBJECT IDENTIFIER ::= { enterprises 184 }
interphase                        OBJECT IDENTIFIER ::= { enterprises 185 }
toshibaCorporation                OBJECT IDENTIFIER ::= { enterprises 186 }
clearpointResearchCorp            OBJECT IDENTIFIER ::= { enterprises 187 }
ascom                             OBJECT IDENTIFIER ::= { enterprises 188 }
fujitsuAmerica                    OBJECT IDENTIFIER ::= { enterprises 189 }
netcomSolutions                   OBJECT IDENTIFIER ::= { enterprises 190 }
ncr                               OBJECT IDENTIFIER ::= { enterprises 191 }
drMaternaGmbH                     OBJECT IDENTIFIER ::= { enterprises 192 }
ericssonBusinessCommunications    OBJECT IDENTIFIER ::= { enterprises 193 }
metaphorComputerSystems           OBJECT IDENTIFIER ::= { enterprises 194 }
patriotPartners                   OBJECT IDENTIFIER ::= { enterprises 195 }
theSoftwareGroupLimited           OBJECT IDENTIFIER ::= { enterprises 196 }
kalpana                           OBJECT IDENTIFIER ::= { enterprises 197 }
universityOfWaterloo              OBJECT IDENTIFIER ::= { enterprises 198 }
cclITRI                           OBJECT IDENTIFIER ::= { enterprises 199 }
coeurPostel                       OBJECT IDENTIFIER ::= { enterprises 200 }
mitsubishCableIndustries          OBJECT IDENTIFIER ::= { enterprises 201 }
smc                               OBJECT IDENTIFIER ::= { enterprises 202 }
crescendoCommunication            OBJECT IDENTIFIER ::= { enterprises 203 }
goodallSoftwareEngineering        OBJECT IDENTIFIER ::= { enterprises 204 }
intecom                           OBJECT IDENTIFIER ::= { enterprises 205 }
victoriaUniversityOfWellington    OBJECT IDENTIFIER ::= { enterprises 206 }
alliedTelesis                     OBJECT IDENTIFIER ::= { enterprises 207 }
crayCommunicationsAS              OBJECT IDENTIFIER ::= { enterprises 208 }
protools                          OBJECT IDENTIFIER ::= { enterprises 209 }
nipponTelegraphAndTelephoneCorp   OBJECT IDENTIFIER ::= { enterprises 210 }
fujitsuLimited                    OBJECT IDENTIFIER ::= { enterprises 211 }
networkPeripherals                OBJECT IDENTIFIER ::= { enterprises 212 }
netronix                          OBJECT IDENTIFIER ::= { enterprises 213 }
universityOfWisconsinMadison      OBJECT IDENTIFIER ::= { enterprises 214 }
networth                          OBJECT IDENTIFIER ::= { enterprises 215 }
tandbergDataAS                    OBJECT IDENTIFIER ::= { enterprises 216 }
technicallyEliteConcepts          OBJECT IDENTIFIER ::= { enterprises 217 }
labtamAustraliaPty                OBJECT IDENTIFIER ::= { enterprises 218 }
republicTelcomSystems             OBJECT IDENTIFIER ::= { enterprises 219 }
adiSystems                        OBJECT IDENTIFIER ::= { enterprises 220 }
microwaveBypassSystems            OBJECT IDENTIFIER ::= { enterprises 221 }
pyramidTechnologyCorp             OBJECT IDENTIFIER ::= { enterprises 222 }
unisysCorp                        OBJECT IDENTIFIER ::= { enterprises 223 }
lanopticsLTD                      OBJECT IDENTIFIER ::= { enterprises 224 }
nkkCorporation                    OBJECT IDENTIFIER ::= { enterprises 225 }
mtradeUK                          OBJECT IDENTIFIER ::= { enterprises 226 }
acals                             OBJECT IDENTIFIER ::= { enterprises 227 }
astec                             OBJECT IDENTIFIER ::= { enterprises 228 }
delmarvaPower                     OBJECT IDENTIFIER ::= { enterprises 229 }
telematicsInternational           OBJECT IDENTIFIER ::= { enterprises 230 }
siemensNixdorf                    OBJECT IDENTIFIER ::= { enterprises 231 }
compaq                            OBJECT IDENTIFIER ::= { enterprises 232 }
netmanage                         OBJECT IDENTIFIER ::= { enterprises 233 }
ncsuComputingCenter               OBJECT IDENTIFIER ::= { enterprises 234 }
empiricalToolsAndTechnologies     OBJECT IDENTIFIER ::= { enterprises 235 }
samsungGroup                      OBJECT IDENTIFIER ::= { enterprises 236 }
takaokaElectricMfgCo              OBJECT IDENTIFIER ::= { enterprises 237 }
netrixSystemsCorporation          OBJECT IDENTIFIER ::= { enterprises 238 }
windata                           OBJECT IDENTIFIER ::= { enterprises 239 }
rcInternationalAS                 OBJECT IDENTIFIER ::= { enterprises 240 }
netexpResearch                    OBJECT IDENTIFIER ::= { enterprises 241 }
internodeSystemsPty               OBJECT IDENTIFIER ::= { enterprises 242 }
netcsInformationstechnikGmbH      OBJECT IDENTIFIER ::= { enterprises 243 }
lantronix                         OBJECT IDENTIFIER ::= { enterprises 244 }
avatarConsultants                 OBJECT IDENTIFIER ::= { enterprises 245 }
furukawaElectoricCo               OBJECT IDENTIFIER ::= { enterprises 246 }
nortelDasaNetworkSystems          OBJECT IDENTIFIER ::= { enterprises 247 }
richardHirschmannGmbHAndCo        OBJECT IDENTIFIER ::= { enterprises 248 }
g2r                               OBJECT IDENTIFIER ::= { enterprises 249 }
universityOfMichigan              OBJECT IDENTIFIER ::= { enterprises 250 }
netcomm                           OBJECT IDENTIFIER ::= { enterprises 251 }
sableTechnologyCorporation        OBJECT IDENTIFIER ::= { enterprises 252 }
xerox                             OBJECT IDENTIFIER ::= { enterprises 253 }
conwareComputerConsultingGmbH     OBJECT IDENTIFIER ::= { enterprises 254 }
compatibleSystemsCorp             OBJECT IDENTIFIER ::= { enterprises 255 }
scitecCommunicationsSystems       OBJECT IDENTIFIER ::= { enterprises 256 }
transarcCorporation               OBJECT IDENTIFIER ::= { enterprises 257 }
matsushitaElectricIndustrialCo    OBJECT IDENTIFIER ::= { enterprises 258 }
acctonTechnology                  OBJECT IDENTIFIER ::= { enterprises 259 }
starTek                           OBJECT IDENTIFIER ::= { enterprises 260 }
codenollTechCorp                  OBJECT IDENTIFIER ::= { enterprises 261 }
formation                         OBJECT IDENTIFIER ::= { enterprises 262 }
seikoInstruments                  OBJECT IDENTIFIER ::= { enterprises 263 }
rce                               OBJECT IDENTIFIER ::= { enterprises 264 }
xenocom                           OBJECT IDENTIFIER ::= { enterprises 265 }
kabelrheydt                       OBJECT IDENTIFIER ::= { enterprises 266 }
systechComputerCorporation        OBJECT IDENTIFIER ::= { enterprises 267 }
visual                            OBJECT IDENTIFIER ::= { enterprises 268 }
sdd                               OBJECT IDENTIFIER ::= { enterprises 269 }
zenithElectronicsCorporation      OBJECT IDENTIFIER ::= { enterprises 270 }
telecomFINLAND                    OBJECT IDENTIFIER ::= { enterprises 271 }
bintecComputersystems             OBJECT IDENTIFIER ::= { enterprises 272 }
eunetGermany                      OBJECT IDENTIFIER ::= { enterprises 273 }
picturetelCorporation             OBJECT IDENTIFIER ::= { enterprises 274 }
michiganStateUniversity           OBJECT IDENTIFIER ::= { enterprises 275 }
gteTelecom                        OBJECT IDENTIFIER ::= { enterprises 276 }
cascadeCommunicationsCorp         OBJECT IDENTIFIER ::= { enterprises 277 }
hitachiCable                      OBJECT IDENTIFIER ::= { enterprises 278 }
olivetti                          OBJECT IDENTIFIER ::= { enterprises 279 }
vitacomCorporation                OBJECT IDENTIFIER ::= { enterprises 280 }
inmos                             OBJECT IDENTIFIER ::= { enterprises 281 }
aicSystemsLaboratories            OBJECT IDENTIFIER ::= { enterprises 282 }
cameoCommunications               OBJECT IDENTIFIER ::= { enterprises 283 }
diabDataAB                        OBJECT IDENTIFIER ::= { enterprises 284 }
olicomAS                          OBJECT IDENTIFIER ::= { enterprises 285 }
digitalKienzleComputersystems     OBJECT IDENTIFIER ::= { enterprises 286 }
cselt                             OBJECT IDENTIFIER ::= { enterprises 287 }
electronicDataSystems             OBJECT IDENTIFIER ::= { enterprises 288 }
mcdataCorporation                 OBJECT IDENTIFIER ::= { enterprises 289 }
harrisCorporation                 OBJECT IDENTIFIER ::= { enterprises 290 }
technologyDynamics                OBJECT IDENTIFIER ::= { enterprises 291 }
datahouseInformationSystems       OBJECT IDENTIFIER ::= { enterprises 292 }
dsirNetworkGroup                  OBJECT IDENTIFIER ::= { enterprises 293 }
texasInstruments                  OBJECT IDENTIFIER ::= { enterprises 294 }
plaintreeSystems                  OBJECT IDENTIFIER ::= { enterprises 295 }
hedemannSoftwareDevelopment       OBJECT IDENTIFIER ::= { enterprises 296 }
fujiXeroxCo                       OBJECT IDENTIFIER ::= { enterprises 297 }
asanteTechnology                  OBJECT IDENTIFIER ::= { enterprises 298 }
stanfordUniversity                OBJECT IDENTIFIER ::= { enterprises 299 }
digitalLink                       OBJECT IDENTIFIER ::= { enterprises 300 }
raylanCorporation                 OBJECT IDENTIFIER ::= { enterprises 301 }
datacraft                         OBJECT IDENTIFIER ::= { enterprises 302 }
hughes                            OBJECT IDENTIFIER ::= { enterprises 303 }
farallonComputing                 OBJECT IDENTIFIER ::= { enterprises 304 }
geInformationServices             OBJECT IDENTIFIER ::= { enterprises 305 }
gambitComputerCommunications      OBJECT IDENTIFIER ::= { enterprises 306 }
livingstonEnterprises             OBJECT IDENTIFIER ::= { enterprises 307 }
starTechnologies                  OBJECT IDENTIFIER ::= { enterprises 308 }
micronicsComputers                OBJECT IDENTIFIER ::= { enterprises 309 }
basis                             OBJECT IDENTIFIER ::= { enterprises 310 }
microsoft                         OBJECT IDENTIFIER ::= { enterprises 311 }
usWestAdvanceTechnologies         OBJECT IDENTIFIER ::= { enterprises 312 }
universityCollegeLondon           OBJECT IDENTIFIER ::= { enterprises 313 }
eastmanKodakCompany               OBJECT IDENTIFIER ::= { enterprises 314 }
networkResourcesCorporation       OBJECT IDENTIFIER ::= { enterprises 315 }
atlasTelecom                      OBJECT IDENTIFIER ::= { enterprises 316 }
bridgeway                         OBJECT IDENTIFIER ::= { enterprises 317 }
americanPowerConversionCorp       OBJECT IDENTIFIER ::= { enterprises 318 }
doeAtmosphericRadiationMeasurementProject OBJECT IDENTIFIER ::= { enterprises 319 }
versteegCodeWorks                 OBJECT IDENTIFIER ::= { enterprises 320 }
verilinkCorp                      OBJECT IDENTIFIER ::= { enterprises 321 }
sybusCorportation                 OBJECT IDENTIFIER ::= { enterprises 322 }
tekelec                           OBJECT IDENTIFIER ::= { enterprises 323 }
nasaAmesResearchCente             OBJECT IDENTIFIER ::= { enterprises 324 }
simonFraserUniversity             OBJECT IDENTIFIER ::= { enterprises 325 }
foreSystems                       OBJECT IDENTIFIER ::= { enterprises 326 }
centrumCommunications             OBJECT IDENTIFIER ::= { enterprises 327 }
nextComputer                      OBJECT IDENTIFIER ::= { enterprises 328 }
netcore                           OBJECT IDENTIFIER ::= { enterprises 329 }
northwestDigitalSystems           OBJECT IDENTIFIER ::= { enterprises 330 }
andrewCorporation                 OBJECT IDENTIFIER ::= { enterprises 331 }
digiboard                         OBJECT IDENTIFIER ::= { enterprises 332 }
computerNetworkTechnologyCorp     OBJECT IDENTIFIER ::= { enterprises 333 }
lotusDevelopmentCorp              OBJECT IDENTIFIER ::= { enterprises 334 }
micomCommunicationCorporation     OBJECT IDENTIFIER ::= { enterprises 335 }
asciiCorporation                  OBJECT IDENTIFIER ::= { enterprises 336 }
puredataResearch                  OBJECT IDENTIFIER ::= { enterprises 337 }
nttDATA                           OBJECT IDENTIFIER ::= { enterprises 338 }
emprosSystemsInternational        OBJECT IDENTIFIER ::= { enterprises 339 }
kendallSquareResearch             OBJECT IDENTIFIER ::= { enterprises 340 }
ornl                              OBJECT IDENTIFIER ::= { enterprises 341 }
networkInnovations                OBJECT IDENTIFIER ::= { enterprises 342 }
intelCorporation                  OBJECT IDENTIFIER ::= { enterprises 343 }
proxar                            OBJECT IDENTIFIER ::= { enterprises 344 }
epsonResearchCenter               OBJECT IDENTIFIER ::= { enterprises 345 }
fibernet                          OBJECT IDENTIFIER ::= { enterprises 346 }
boxHillSystemsCorporation         OBJECT IDENTIFIER ::= { enterprises 347 }
americanExpressTravelRelatedServices OBJECT IDENTIFIER ::= { enterprises 348 }
compuShack                        OBJECT IDENTIFIER ::= { enterprises 349 }
parallanComputer                  OBJECT IDENTIFIER ::= { enterprises 350 }
stratacom                         OBJECT IDENTIFIER ::= { enterprises 351 }
openNetworksEngineering           OBJECT IDENTIFIER ::= { enterprises 352 }
atmForum                          OBJECT IDENTIFIER ::= { enterprises 353 }
ssdManagement                     OBJECT IDENTIFIER ::= { enterprises 354 }
automatedNetworkManagement        OBJECT IDENTIFIER ::= { enterprises 355 }
magnalinkCommunicationsCorporation OBJECT IDENTIFIER ::= { enterprises 356 }
kastenChaseAppliedResearch        OBJECT IDENTIFIER ::= { enterprises 357 }
skylineTechnology                 OBJECT IDENTIFIER ::= { enterprises 358 }
nuMegaTechnologies                OBJECT IDENTIFIER ::= { enterprises 359 }
morganStanleyAndCo                OBJECT IDENTIFIER ::= { enterprises 360 }
integratedBusinessNetwork         OBJECT IDENTIFIER ::= { enterprises 361 }
lAndNTechnologies                 OBJECT IDENTIFIER ::= { enterprises 362 }
cincinnatiBellInformationSystems  OBJECT IDENTIFIER ::= { enterprises 363 }
oscomInternational                OBJECT IDENTIFIER ::= { enterprises 364 }
micrognosis                       OBJECT IDENTIFIER ::= { enterprises 365 }
datapointCorporation              OBJECT IDENTIFIER ::= { enterprises 366 }
ricohCo                           OBJECT IDENTIFIER ::= { enterprises 367 }
axisCommunicationsAB              OBJECT IDENTIFIER ::= { enterprises 368 }
pacerSoftware                     OBJECT IDENTIFIER ::= { enterprises 369 }
axonNetworks                      OBJECT IDENTIFIER ::= { enterprises 370 }
brixtonSystems                    OBJECT IDENTIFIER ::= { enterprises 371 }
gsi                               OBJECT IDENTIFIER ::= { enterprises 372 }
tatungCo                          OBJECT IDENTIFIER ::= { enterprises 373 }
disResearchLTD                    OBJECT IDENTIFIER ::= { enterprises 374 }
quotronSystems                    OBJECT IDENTIFIER ::= { enterprises 375 }
dassaultElectronique              OBJECT IDENTIFIER ::= { enterprises 376 }
corollary                         OBJECT IDENTIFIER ::= { enterprises 377 }
seel                              OBJECT IDENTIFIER ::= { enterprises 378 }
lexcel                            OBJECT IDENTIFIER ::= { enterprises 379 }
sophisticatedTechnologies         OBJECT IDENTIFIER ::= { enterprises 380 }
ost                               OBJECT IDENTIFIER ::= { enterprises 381 }
megadataPty                       OBJECT IDENTIFIER ::= { enterprises 382 }
llnlLivermoreComputerCenter       OBJECT IDENTIFIER ::= { enterprises 383 }
dynatechCommunications            OBJECT IDENTIFIER ::= { enterprises 384 }
symplexCommunicationsCorp         OBJECT IDENTIFIER ::= { enterprises 385 }
tribeComputerWorks                OBJECT IDENTIFIER ::= { enterprises 386 }
taligent                          OBJECT IDENTIFIER ::= { enterprises 387 }
symbolTechnologies                OBJECT IDENTIFIER ::= { enterprises 388 }
lancert                           OBJECT IDENTIFIER ::= { enterprises 389 }
alantec                           OBJECT IDENTIFIER ::= { enterprises 390 }
ridgebackSolutions                OBJECT IDENTIFIER ::= { enterprises 391 }
metrix                            OBJECT IDENTIFIER ::= { enterprises 392 }
symantecCorporation               OBJECT IDENTIFIER ::= { enterprises 393 }
nrlCommunicationSystemsBranch     OBJECT IDENTIFIER ::= { enterprises 394 }
ideCorporation                    OBJECT IDENTIFIER ::= { enterprises 395 }
matsushitaElectricWorks           OBJECT IDENTIFIER ::= { enterprises 396 }
megapac                           OBJECT IDENTIFIER ::= { enterprises 397 }
pinaclCommunicationSystems        OBJECT IDENTIFIER ::= { enterprises 398 }
hitachiComputerProducts           OBJECT IDENTIFIER ::= { enterprises 399 }
meteoFRANCE                       OBJECT IDENTIFIER ::= { enterprises 400 }
prc                               OBJECT IDENTIFIER ::= { enterprises 401 }
walMartStores                     OBJECT IDENTIFIER ::= { enterprises 402 }
nissinElectricCompany             OBJECT IDENTIFIER ::= { enterprises 403 }
distributedSupportInformationStandard OBJECT IDENTIFIER ::= { enterprises 404 }
smdsInterestGroup                 OBJECT IDENTIFIER ::= { enterprises 405 }
solcomSystems                     OBJECT IDENTIFIER ::= { enterprises 406 }
bellAtlantic                      OBJECT IDENTIFIER ::= { enterprises 407 }
advancedMultiuserTechnologiesCorporation OBJECT IDENTIFIER ::= { enterprises 408 }
mitsubishiElectricCorporation     OBJECT IDENTIFIER ::= { enterprises 409 }
colSystems                        OBJECT IDENTIFIER ::= { enterprises 410 }
universityOfAuckland              OBJECT IDENTIFIER ::= { enterprises 411 }
desktopManagementTaskForce        OBJECT IDENTIFIER ::= { enterprises 412 }
kleverComputers                   OBJECT IDENTIFIER ::= { enterprises 413 }
amdahlCorporation                 OBJECT IDENTIFIER ::= { enterprises 414 }
jtecPty                           OBJECT IDENTIFIER ::= { enterprises 415 }
matraCommuncation                 OBJECT IDENTIFIER ::= { enterprises 416 }
halComputerSystems                OBJECT IDENTIFIER ::= { enterprises 417 }
lawrenceBerkeleyLaboratory        OBJECT IDENTIFIER ::= { enterprises 418 }
daleComputerCorporation           OBJECT IDENTIFIER ::= { enterprises 419 }
iptc                              OBJECT IDENTIFIER ::= { enterprises 420 }
bytexCorporation                  OBJECT IDENTIFIER ::= { enterprises 421 }
cogwheel                          OBJECT IDENTIFIER ::= { enterprises 422 }
lanwanTechnologies                OBJECT IDENTIFIER ::= { enterprises 423 }
thomasConradCorporation           OBJECT IDENTIFIER ::= { enterprises 424 }
txport                            OBJECT IDENTIFIER ::= { enterprises 425 }
compex                            OBJECT IDENTIFIER ::= { enterprises 426 }
evergreenSystems                  OBJECT IDENTIFIER ::= { enterprises 427 }
hnv                               OBJECT IDENTIFIER ::= { enterprises 428 }
usRobotics                        OBJECT IDENTIFIER ::= { enterprises 429 }
canadaPostCorporation             OBJECT IDENTIFIER ::= { enterprises 430 }
openSystemsSolutions              OBJECT IDENTIFIER ::= { enterprises 431 }
torontoStockExchange              OBJECT IDENTIFIER ::= { enterprises 432 }
mamakosTransSysConsulting         OBJECT IDENTIFIER ::= { enterprises 433 }
eicon                             OBJECT IDENTIFIER ::= { enterprises 434 }
jupiterSystems                    OBJECT IDENTIFIER ::= { enterprises 435 }
ssti                              OBJECT IDENTIFIER ::= { enterprises 436 }
grandJunctionNetworks             OBJECT IDENTIFIER ::= { enterprises 437 }
anasazi                           OBJECT IDENTIFIER ::= { enterprises 438 }
edwardDJonesAndCompany            OBJECT IDENTIFIER ::= { enterprises 439 }
amnet                             OBJECT IDENTIFIER ::= { enterprises 440 }
chaseResearch                     OBJECT IDENTIFIER ::= { enterprises 441 }
peerNetworks                      OBJECT IDENTIFIER ::= { enterprises 442 }
gatewayCommunications             OBJECT IDENTIFIER ::= { enterprises 443 }
peregrineSystems                  OBJECT IDENTIFIER ::= { enterprises 444 }
daewooTelecom                     OBJECT IDENTIFIER ::= { enterprises 445 }
norwegianTelecomResearch          OBJECT IDENTIFIER ::= { enterprises 446 }
wiltel                            OBJECT IDENTIFIER ::= { enterprises 447 }
ericssonCamtec                    OBJECT IDENTIFIER ::= { enterprises 448 }
codex                             OBJECT IDENTIFIER ::= { enterprises 449 }
basis2                            OBJECT IDENTIFIER ::= { enterprises 450 }
ageLogic                          OBJECT IDENTIFIER ::= { enterprises 451 }
indeElectronics                   OBJECT IDENTIFIER ::= { enterprises 452 }
isodeConsortium                   OBJECT IDENTIFIER ::= { enterprises 453 }
jiCase                            OBJECT IDENTIFIER ::= { enterprises 454 }
trillium                          OBJECT IDENTIFIER ::= { enterprises 455 }
bacchus                           OBJECT IDENTIFIER ::= { enterprises 456 }
mcc                               OBJECT IDENTIFIER ::= { enterprises 457 }
stratusComputer                   OBJECT IDENTIFIER ::= { enterprises 458 }
quotron                           OBJECT IDENTIFIER ::= { enterprises 459 }
beameAndWhiteside                 OBJECT IDENTIFIER ::= { enterprises 460 }
cellularTechnicalServices         OBJECT IDENTIFIER ::= { enterprises 461 }
shoreMicrosystems                 OBJECT IDENTIFIER ::= { enterprises 462 }
telecommunicationsTechniquesCorp  OBJECT IDENTIFIER ::= { enterprises 463 }
dnpap                             OBJECT IDENTIFIER ::= { enterprises 464 }
plexcom                           OBJECT IDENTIFIER ::= { enterprises 465 }
tylink                            OBJECT IDENTIFIER ::= { enterprises 466 }
brookhavenNationalLaboratory      OBJECT IDENTIFIER ::= { enterprises 467 }
computerCommunicationSystems      OBJECT IDENTIFIER ::= { enterprises 468 }
norandCorp                        OBJECT IDENTIFIER ::= { enterprises 469 }
muxLAP                            OBJECT IDENTIFIER ::= { enterprises 470 }
premisysCommunications            OBJECT IDENTIFIER ::= { enterprises 471 }
bellSouthTelecommunications       OBJECT IDENTIFIER ::= { enterprises 472 }
jStainsburyPLC                    OBJECT IDENTIFIER ::= { enterprises 473 }
kiResearch                        OBJECT IDENTIFIER ::= { enterprises 474 }
wandelAndGoltermannTechnologies   OBJECT IDENTIFIER ::= { enterprises 475 }
emersonComputerPower              OBJECT IDENTIFIER ::= { enterprises 476 }
networkSoftwareAssociates         OBJECT IDENTIFIER ::= { enterprises 477 }
procterAndGamble                  OBJECT IDENTIFIER ::= { enterprises 478 }
meridianTechnologyCorporation     OBJECT IDENTIFIER ::= { enterprises 479 }
qms                               OBJECT IDENTIFIER ::= { enterprises 480 }
networkExpress                    OBJECT IDENTIFIER ::= { enterprises 481 }
lancityCorporation                OBJECT IDENTIFIER ::= { enterprises 482 }
daynaCommunications               OBJECT IDENTIFIER ::= { enterprises 483 }
knX                               OBJECT IDENTIFIER ::= { enterprises 484 }
syncResearch                      OBJECT IDENTIFIER ::= { enterprises 485 }
premnet                           OBJECT IDENTIFIER ::= { enterprises 486 }
siac                              OBJECT IDENTIFIER ::= { enterprises 487 }
newYorkStockExchange              OBJECT IDENTIFIER ::= { enterprises 488 }
americanStockExchange             OBJECT IDENTIFIER ::= { enterprises 489 }
fcrSoftware                       OBJECT IDENTIFIER ::= { enterprises 490 }
nationalMedicalCare               OBJECT IDENTIFIER ::= { enterprises 491 }
dialogueCommunicationSystemes     OBJECT IDENTIFIER ::= { enterprises 492 }
nortele                           OBJECT IDENTIFIER ::= { enterprises 493 }
madgeNetworks                     OBJECT IDENTIFIER ::= { enterprises 494 }
memotecCommunications             OBJECT IDENTIFIER ::= { enterprises 495 }
cton                              OBJECT IDENTIFIER ::= { enterprises 496 }
leapTechnology                    OBJECT IDENTIFIER ::= { enterprises 497 }
generalDataComm                   OBJECT IDENTIFIER ::= { enterprises 498 }
aceCommunications                 OBJECT IDENTIFIER ::= { enterprises 499 }
automaticDataProcessing           OBJECT IDENTIFIER ::= { enterprises 500 }
programaSPRITEL                   OBJECT IDENTIFIER ::= { enterprises 501 }
adacom                            OBJECT IDENTIFIER ::= { enterprises 502 }
metrodata                         OBJECT IDENTIFIER ::= { enterprises 503 }
ellemtelTelecommunicationSystemsLaboratories OBJECT IDENTIFIER ::= { enterprises 504 }
arizonaPublicService              OBJECT IDENTIFIER ::= { enterprises 505 }
netwiz                            OBJECT IDENTIFIER ::= { enterprises 506 }
scienceAndEngineeringResearchCouncil OBJECT IDENTIFIER ::= { enterprises 507 }
theFirstBostonCorporation         OBJECT IDENTIFIER ::= { enterprises 508 }
hadaxElectronics                  OBJECT IDENTIFIER ::= { enterprises 509 }
vtkk                              OBJECT IDENTIFIER ::= { enterprises 510 }
northHillsIsrael                  OBJECT IDENTIFIER ::= { enterprises 511 }
tecsiel                           OBJECT IDENTIFIER ::= { enterprises 512 }
bayerischeMotorenWerke            OBJECT IDENTIFIER ::= { enterprises 513 }
cnetTechnologies                  OBJECT IDENTIFIER ::= { enterprises 514 }
mci                               OBJECT IDENTIFIER ::= { enterprises 515 }
humanEngineeringAG                OBJECT IDENTIFIER ::= { enterprises 516 }
filenetCorporation                OBJECT IDENTIFIER ::= { enterprises 517 }
nftEricsson                       OBJECT IDENTIFIER ::= { enterprises 518 }
dunAndBradstreet                  OBJECT IDENTIFIER ::= { enterprises 519 }
intercomputerCommunications       OBJECT IDENTIFIER ::= { enterprises 520 }
defenseIntelligenceAgency         OBJECT IDENTIFIER ::= { enterprises 521 }
telesystemsSLW                    OBJECT IDENTIFIER ::= { enterprises 522 }
aptCommunications                 OBJECT IDENTIFIER ::= { enterprises 523 }
deltaAirlines                     OBJECT IDENTIFIER ::= { enterprises 524 }
californiaMicrowave               OBJECT IDENTIFIER ::= { enterprises 525 }
avidTechnology                    OBJECT IDENTIFIER ::= { enterprises 526 }
integroAdvancedComputerSystems    OBJECT IDENTIFIER ::= { enterprises 527 }
rpti                              OBJECT IDENTIFIER ::= { enterprises 528 }
ascendCommunications              OBJECT IDENTIFIER ::= { enterprises 529 }
edenComputerSystems               OBJECT IDENTIFIER ::= { enterprises 530 }
kawasakiSteelCorp                 OBJECT IDENTIFIER ::= { enterprises 531 }
barclays                          OBJECT IDENTIFIER ::= { enterprises 532 }
bug                               OBJECT IDENTIFIER ::= { enterprises 533 }
exideElectronics                  OBJECT IDENTIFIER ::= { enterprises 534 }
superconductingSupercolliderLab   OBJECT IDENTIFIER ::= { enterprises 535 }
triticom                          OBJECT IDENTIFIER ::= { enterprises 536 }
universalInstrumentsCorp          OBJECT IDENTIFIER ::= { enterprises 537 }
informationResources              OBJECT IDENTIFIER ::= { enterprises 538 }
appliedInnovation                 OBJECT IDENTIFIER ::= { enterprises 539 }
cryptoAG                          OBJECT IDENTIFIER ::= { enterprises 540 }
infiniteNetworks                  OBJECT IDENTIFIER ::= { enterprises 541 }
rabbitSoftware                    OBJECT IDENTIFIER ::= { enterprises 542 }
apertusTechnologies               OBJECT IDENTIFIER ::= { enterprises 543 }
equinoxSystems                    OBJECT IDENTIFIER ::= { enterprises 544 }
hayesMicrocomputerProducts        OBJECT IDENTIFIER ::= { enterprises 545 }
empireTechnologies                OBJECT IDENTIFIER ::= { enterprises 546 }
glaxochem                         OBJECT IDENTIFIER ::= { enterprises 547 }
softwareProfessionals             OBJECT IDENTIFIER ::= { enterprises 548 }
agentTechnology                   OBJECT IDENTIFIER ::= { enterprises 549 }
dornierGMBH                       OBJECT IDENTIFIER ::= { enterprises 550 }
telxonCorporation                 OBJECT IDENTIFIER ::= { enterprises 551 }
entergyCorporation                OBJECT IDENTIFIER ::= { enterprises 552 }
garrettCommunications             OBJECT IDENTIFIER ::= { enterprises 553 }
agileNetworks                     OBJECT IDENTIFIER ::= { enterprises 554 }
larscom                           OBJECT IDENTIFIER ::= { enterprises 555 }
stockEquipment                    OBJECT IDENTIFIER ::= { enterprises 556 }
ittCorporation                    OBJECT IDENTIFIER ::= { enterprises 557 }
universalDataSystems              OBJECT IDENTIFIER ::= { enterprises 558 }
sonixCommunications               OBJECT IDENTIFIER ::= { enterprises 559 }
paulFreemanAssociates             OBJECT IDENTIFIER ::= { enterprises 560 }
johnSBarnes                       OBJECT IDENTIFIER ::= { enterprises 561 }
northernTelecom                   OBJECT IDENTIFIER ::= { enterprises 562 }
capDebris                         OBJECT IDENTIFIER ::= { enterprises 563 }
telcoSystemsNAC                   OBJECT IDENTIFIER ::= { enterprises 564 }
toscoRefiningCo                   OBJECT IDENTIFIER ::= { enterprises 565 }
russellInfoSys                    OBJECT IDENTIFIER ::= { enterprises 566 }
universityOfSalford               OBJECT IDENTIFIER ::= { enterprises 567 }
netquestCorp                      OBJECT IDENTIFIER ::= { enterprises 568 }
armonNetworking                   OBJECT IDENTIFIER ::= { enterprises 569 }
iaCorporation                     OBJECT IDENTIFIER ::= { enterprises 570 }
auSystemCommunicatonAB            OBJECT IDENTIFIER ::= { enterprises 571 }
goldstarInformationAndCommunications OBJECT IDENTIFIER ::= { enterprises 572 }
sectraAB                          OBJECT IDENTIFIER ::= { enterprises 573 }
oneacCorporation                  OBJECT IDENTIFIER ::= { enterprises 574 }
treeTechnologies                  OBJECT IDENTIFIER ::= { enterprises 575 }
gteGovernmentSystems              OBJECT IDENTIFIER ::= { enterprises 576 }
denmacSystems                     OBJECT IDENTIFIER ::= { enterprises 577 }
interlinkComputerSciences         OBJECT IDENTIFIER ::= { enterprises 578 }
bridgeInformationSystems          OBJECT IDENTIFIER ::= { enterprises 579 }
leedsAndNorthrupAustralia         OBJECT IDENTIFIER ::= { enterprises 580 }
bhaComputer                       OBJECT IDENTIFIER ::= { enterprises 581 }
newportSystemsSolutions           OBJECT IDENTIFIER ::= { enterprises 582 }
azelCorporation                   OBJECT IDENTIFIER ::= { enterprises 583 }
robotiker                         OBJECT IDENTIFIER ::= { enterprises 584 }
peerlogic                         OBJECT IDENTIFIER ::= { enterprises 585 }
digitalTransmittionSystems        OBJECT IDENTIFIER ::= { enterprises 586 }
farPointCommunications            OBJECT IDENTIFIER ::= { enterprises 587 }
xircom                            OBJECT IDENTIFIER ::= { enterprises 588 }
meadDataCentral                   OBJECT IDENTIFIER ::= { enterprises 589 }
royalBankOfCanada                 OBJECT IDENTIFIER ::= { enterprises 590 }
advantis                          OBJECT IDENTIFIER ::= { enterprises 591 }
chemicalBankingCorp               OBJECT IDENTIFIER ::= { enterprises 592 }
eagleTechnology                   OBJECT IDENTIFIER ::= { enterprises 593 }
britishTelecom                    OBJECT IDENTIFIER ::= { enterprises 594 }
radixBV                           OBJECT IDENTIFIER ::= { enterprises 595 }
tainetCommunicationSystemCorp     OBJECT IDENTIFIER ::= { enterprises 596 }
comtekServices                    OBJECT IDENTIFIER ::= { enterprises 597 }
fairIssac                         OBJECT IDENTIFIER ::= { enterprises 598 }
astResearch                       OBJECT IDENTIFIER ::= { enterprises 599 }
softStarSrlIngEnricoBadellaSoftstar OBJECT IDENTIFIER ::= { enterprises 600 }
bancomm                           OBJECT IDENTIFIER ::= { enterprises 601 }
trustedInformationSystems         OBJECT IDENTIFIER ::= { enterprises 602 }
harrisAndJeffries                 OBJECT IDENTIFIER ::= { enterprises 603 }
axelTechnologyCorp                OBJECT IDENTIFIER ::= { enterprises 604 }
gnNavtel                          OBJECT IDENTIFIER ::= { enterprises 605 }
capDebis                          OBJECT IDENTIFIER ::= { enterprises 606 }
lachmanTechnology                 OBJECT IDENTIFIER ::= { enterprises 607 }
galcomNetworking                  OBJECT IDENTIFIER ::= { enterprises 608 }
bazis                             OBJECT IDENTIFIER ::= { enterprises 609 }
synaptel                          OBJECT IDENTIFIER ::= { enterprises 610 }
investmentManagementServices      OBJECT IDENTIFIER ::= { enterprises 611 }
taiwanTelecommunicationLab        OBJECT IDENTIFIER ::= { enterprises 612 }
anagramCorporation                OBJECT IDENTIFIER ::= { enterprises 613 }
univel                            OBJECT IDENTIFIER ::= { enterprises 614 }
universityOfCalifornia            OBJECT IDENTIFIER ::= { enterprises 615 }
compuserve                        OBJECT IDENTIFIER ::= { enterprises 616 }
telstraOTCAustralia               OBJECT IDENTIFIER ::= { enterprises 617 }
westinghouseElectricCorp          OBJECT IDENTIFIER ::= { enterprises 618 }
dga                               OBJECT IDENTIFIER ::= { enterprises 619 }
elegantCommunications             OBJECT IDENTIFIER ::= { enterprises 620 }
experdata                         OBJECT IDENTIFIER ::= { enterprises 621 }
unisourceBusinessNetworksSwedenAB OBJECT IDENTIFIER ::= { enterprises 622 }
molex                             OBJECT IDENTIFIER ::= { enterprises 623 }
quayFinancialSoftware             OBJECT IDENTIFIER ::= { enterprises 624 }
vmx                               OBJECT IDENTIFIER ::= { enterprises 625 }
hypercom                          OBJECT IDENTIFIER ::= { enterprises 626 }
universityOfGuelph                OBJECT IDENTIFIER ::= { enterprises 627 }
dialogika                         OBJECT IDENTIFIER ::= { enterprises 628 }
nbaseSwitchCommunication          OBJECT IDENTIFIER ::= { enterprises 629 }
anchorDatacommBV                  OBJECT IDENTIFIER ::= { enterprises 630 }
pacdata                           OBJECT IDENTIFIER ::= { enterprises 631 }
universityOfColorado              OBJECT IDENTIFIER ::= { enterprises 632 }
tricomCommunicationsLimited       OBJECT IDENTIFIER ::= { enterprises 633 }
santixSoftwareGmbH                OBJECT IDENTIFIER ::= { enterprises 634 }
fastcommCommunicationsCorp        OBJECT IDENTIFIER ::= { enterprises 635 }
theGeorgiaInstituteOfTechnology   OBJECT IDENTIFIER ::= { enterprises 636 }
alcatelDataNetworks               OBJECT IDENTIFIER ::= { enterprises 637 }
gtech                             OBJECT IDENTIFIER ::= { enterprises 638 }
unocalCorporation                 OBJECT IDENTIFIER ::= { enterprises 639 }
firstPacificNetwork               OBJECT IDENTIFIER ::= { enterprises 640 }
lexmarkInternational              OBJECT IDENTIFIER ::= { enterprises 641 }
qnixComputer                      OBJECT IDENTIFIER ::= { enterprises 642 }
jigsawSoftwareConcepts            OBJECT IDENTIFIER ::= { enterprises 643 }
vir                               OBJECT IDENTIFIER ::= { enterprises 644 }
sfaDatacomm                       OBJECT IDENTIFIER ::= { enterprises 645 }
seikoCommunicationSystems         OBJECT IDENTIFIER ::= { enterprises 646 }
unifiedManagement                 OBJECT IDENTIFIER ::= { enterprises 647 }
radlinx                           OBJECT IDENTIFIER ::= { enterprises 648 }
microplexSystems                  OBJECT IDENTIFIER ::= { enterprises 649 }
objectaElektronikAndDataAB        OBJECT IDENTIFIER ::= { enterprises 650 }
phoenixMicrosystems               OBJECT IDENTIFIER ::= { enterprises 651 }
distributedSystemsInternational   OBJECT IDENTIFIER ::= { enterprises 652 }
evolvingSystems                   OBJECT IDENTIFIER ::= { enterprises 653 }
satGmbH                           OBJECT IDENTIFIER ::= { enterprises 654 }
celanTechnology                   OBJECT IDENTIFIER ::= { enterprises 655 }
landmarkSystemsCorp               OBJECT IDENTIFIER ::= { enterprises 656 }
netoneSystemsCo                   OBJECT IDENTIFIER ::= { enterprises 657 }
loralDataSystems                  OBJECT IDENTIFIER ::= { enterprises 658 }
cellwareBroadbandTechnology       OBJECT IDENTIFIER ::= { enterprises 659 }
muSystems                         OBJECT IDENTIFIER ::= { enterprises 660 }
imcNetworksCorp                   OBJECT IDENTIFIER ::= { enterprises 661 }
octelCommunicationsCorp           OBJECT IDENTIFIER ::= { enterprises 662 }
ritTechnologiesLTD                OBJECT IDENTIFIER ::= { enterprises 663 }
adtran                            OBJECT IDENTIFIER ::= { enterprises 664 }
powerplayTechnologies             OBJECT IDENTIFIER ::= { enterprises 665 }
okiElectricIndustryCo             OBJECT IDENTIFIER ::= { enterprises 666 }
specialixInternational            OBJECT IDENTIFIER ::= { enterprises 667 }
inesc                             OBJECT IDENTIFIER ::= { enterprises 668 }
globalnetCommunications           OBJECT IDENTIFIER ::= { enterprises 669 }
productLineEngineerSVECComputerCorp OBJECT IDENTIFIER ::= { enterprises 670 }
printerSystemsCorp                OBJECT IDENTIFIER ::= { enterprises 671 }
contecMicroElectronicsUSA         OBJECT IDENTIFIER ::= { enterprises 672 }
unixIntegrationServices           OBJECT IDENTIFIER ::= { enterprises 673 }
dellComputerCorporation           OBJECT IDENTIFIER ::= { enterprises 674 }
whittakerElectronicSystems        OBJECT IDENTIFIER ::= { enterprises 675 }
qpsxCommunications                OBJECT IDENTIFIER ::= { enterprises 676 }
loralWDl                          OBJECT IDENTIFIER ::= { enterprises 677 }
federalExpressCorp                OBJECT IDENTIFIER ::= { enterprises 678 }
eCOMMS                            OBJECT IDENTIFIER ::= { enterprises 679 }
softwareClearingHouse             OBJECT IDENTIFIER ::= { enterprises 680 }
antlowComputersLTD                OBJECT IDENTIFIER ::= { enterprises 681 }
emcomCorp                         OBJECT IDENTIFIER ::= { enterprises 682 }
extendedSystems                   OBJECT IDENTIFIER ::= { enterprises 683 }
solaElectric                      OBJECT IDENTIFIER ::= { enterprises 684 }
esixSystems                       OBJECT IDENTIFIER ::= { enterprises 685 }
threeMMMM                         OBJECT IDENTIFIER ::= { enterprises 686 }
cylinkCorp                        OBJECT IDENTIFIER ::= { enterprises 687 }
znyxAdvancedSystemsDivision       OBJECT IDENTIFIER ::= { enterprises 688 }
texaco                            OBJECT IDENTIFIER ::= { enterprises 689 }
mccawCellularCommunicationCorp    OBJECT IDENTIFIER ::= { enterprises 690 }
aspComputerProduct                OBJECT IDENTIFIER ::= { enterprises 691 }
hiperformanceSystems              OBJECT IDENTIFIER ::= { enterprises 692 }
regionalesRechenzentrum           OBJECT IDENTIFIER ::= { enterprises 693 }
sapAG                             OBJECT IDENTIFIER ::= { enterprises 694 }
electrospaceSystem                OBJECT IDENTIFIER ::= { enterprises 695 }
multiportSoftware                 OBJECT IDENTIFIER ::= { enterprises 697 }
combinet                          OBJECT IDENTIFIER ::= { enterprises 698 }
tscc                              OBJECT IDENTIFIER ::= { enterprises 699 }
teleosCommunications              OBJECT IDENTIFIER ::= { enterprises 700 }
altaResearch                      OBJECT IDENTIFIER ::= { enterprises 701 }
independenceBlueCross             OBJECT IDENTIFIER ::= { enterprises 702 }
adacomStationInterconnectivityLTD OBJECT IDENTIFIER ::= { enterprises 703 }
mirorSystems                      OBJECT IDENTIFIER ::= { enterprises 704 }
merlinGerin                       OBJECT IDENTIFIER ::= { enterprises 705 }
owenCorningFiberglas              OBJECT IDENTIFIER ::= { enterprises 706 }
talkingNetworks                   OBJECT IDENTIFIER ::= { enterprises 707 }
cubixCorporation                  OBJECT IDENTIFIER ::= { enterprises 708 }
formation2                        OBJECT IDENTIFIER ::= { enterprises 709 }
lannair                           OBJECT IDENTIFIER ::= { enterprises 710 }
lightstreamCorp                   OBJECT IDENTIFIER ::= { enterprises 711 }
lanartCorp                        OBJECT IDENTIFIER ::= { enterprises 712 }
universityOfStellenbosch          OBJECT IDENTIFIER ::= { enterprises 713 }
wyseTechnology                    OBJECT IDENTIFIER ::= { enterprises 714 }
dscCommunicationsCorp             OBJECT IDENTIFIER ::= { enterprises 715 }
netec                             OBJECT IDENTIFIER ::= { enterprises 716 }
breltenbachSoftwareEngineeringGmbH OBJECT IDENTIFIER ::= { enterprises 717 }
victorCompanyOfJapan              OBJECT IDENTIFIER ::= { enterprises 718 }
japanDirexCorporation             OBJECT IDENTIFIER ::= { enterprises 719 }
necsyNetworkControlSystems        OBJECT IDENTIFIER ::= { enterprises 720 }
isdnSystemsCorp                   OBJECT IDENTIFIER ::= { enterprises 721 }
zeroOneTechnologies               OBJECT IDENTIFIER ::= { enterprises 722 }
radixTechnologies                 OBJECT IDENTIFIER ::= { enterprises 723 }
nationalInstituteOfStandardsAndTechnology OBJECT IDENTIFIER ::= { enterprises 724 }
digitalTechnology                 OBJECT IDENTIFIER ::= { enterprises 725 }
castelleCorp                      OBJECT IDENTIFIER ::= { enterprises 726 }
presticom                         OBJECT IDENTIFIER ::= { enterprises 727 }
showaElectricWireAndCableCo       OBJECT IDENTIFIER ::= { enterprises 728 }
spectragraphics                   OBJECT IDENTIFIER ::= { enterprises 729 }
connectware                       OBJECT IDENTIFIER ::= { enterprises 730 }
windRiverSystems                  OBJECT IDENTIFIER ::= { enterprises 731 }
radwayInternational               OBJECT IDENTIFIER ::= { enterprises 732 }
systemManagementARTS              OBJECT IDENTIFIER ::= { enterprises 733 }
persoft                           OBJECT IDENTIFIER ::= { enterprises 734 }
xnetTechnology                    OBJECT IDENTIFIER ::= { enterprises 735 }
unisonTymlabs                     OBJECT IDENTIFIER ::= { enterprises 736 }
microMaticResearch                OBJECT IDENTIFIER ::= { enterprises 737 }
batmAdvanceTechnologies           OBJECT IDENTIFIER ::= { enterprises 738 }
universityOfCopenhagen            OBJECT IDENTIFIER ::= { enterprises 739 }
networkSecuritySystems            OBJECT IDENTIFIER ::= { enterprises 740 }
jnaTelecommunications             OBJECT IDENTIFIER ::= { enterprises 741 }
encoreComputerCorporation         OBJECT IDENTIFIER ::= { enterprises 742 }
centralIntelligentAgency          OBJECT IDENTIFIER ::= { enterprises 743 }
isc                               OBJECT IDENTIFIER ::= { enterprises 744 }
digitalCommunicationAssociates    OBJECT IDENTIFIER ::= { enterprises 745 }
cybermedia                        OBJECT IDENTIFIER ::= { enterprises 746 }
distributedSystemsInternational2  OBJECT IDENTIFIER ::= { enterprises 747 }
peterRadigEDPConsulting           OBJECT IDENTIFIER ::= { enterprises 748 }
vicorpInteractiveSystems          OBJECT IDENTIFIER ::= { enterprises 749 }
inet                              OBJECT IDENTIFIER ::= { enterprises 750 }
argonneNationalLaboratory         OBJECT IDENTIFIER ::= { enterprises 751 }
tekLogix                          OBJECT IDENTIFIER ::= { enterprises 752 }
northWesternUniversity            OBJECT IDENTIFIER ::= { enterprises 753 }
astarteFiberNetworks              OBJECT IDENTIFIER ::= { enterprises 754 }
diederichAndAssociates            OBJECT IDENTIFIER ::= { enterprises 755 }
floridaPowerCorporation           OBJECT IDENTIFIER ::= { enterprises 756 }
askINGRES                         OBJECT IDENTIFIER ::= { enterprises 757 }
openNetworkEnterprise             OBJECT IDENTIFIER ::= { enterprises 758 }
theHomeDepot                      OBJECT IDENTIFIER ::= { enterprises 759 }
panDacomTelekommunikations        OBJECT IDENTIFIER ::= { enterprises 760 }
nettek                            OBJECT IDENTIFIER ::= { enterprises 761 }
karlnetCorp                       OBJECT IDENTIFIER ::= { enterprises 762 }
efficientNetworks                 OBJECT IDENTIFIER ::= { enterprises 763 }
fiberdata                         OBJECT IDENTIFIER ::= { enterprises 764 }
lanser                            OBJECT IDENTIFIER ::= { enterprises 765 }
telebitCommunicationsAS           OBJECT IDENTIFIER ::= { enterprises 766 }
hilanGmbH                         OBJECT IDENTIFIER ::= { enterprises 767 }
networkComputing                  OBJECT IDENTIFIER ::= { enterprises 768 }
walgreensCompany                  OBJECT IDENTIFIER ::= { enterprises 769 }
internetInitiativeJapan           OBJECT IDENTIFIER ::= { enterprises 770 }
gpVanNiekerkOndernemings          OBJECT IDENTIFIER ::= { enterprises 771 }
queen                             OBJECT IDENTIFIER ::= { enterprises 772 }
securitiesIndustryAutomationCorporation OBJECT IDENTIFIER ::= { enterprises 773 }
synaptics                         OBJECT IDENTIFIER ::= { enterprises 774 }
dataSwitchCorporation             OBJECT IDENTIFIER ::= { enterprises 775 }
telindusDistribution              OBJECT IDENTIFIER ::= { enterprises 776 }
maxmSystemsCorporation            OBJECT IDENTIFIER ::= { enterprises 777 }
fraunhoferGesellschaft            OBJECT IDENTIFIER ::= { enterprises 778 }
eqsBusinessServices               OBJECT IDENTIFIER ::= { enterprises 779 }
cnetTechnology                    OBJECT IDENTIFIER ::= { enterprises 780 }
datentechnikGmbH                  OBJECT IDENTIFIER ::= { enterprises 781 }
networkSolutions                  OBJECT IDENTIFIER ::= { enterprises 782 }
viamanSoftware                    OBJECT IDENTIFIER ::= { enterprises 783 }
schweizerischeBankgesellschaftZuerich OBJECT IDENTIFIER ::= { enterprises 784 }
universityOfTwenteTIOS            OBJECT IDENTIFIER ::= { enterprises 785 }
simplesoft                        OBJECT IDENTIFIER ::= { enterprises 786 }
stonyBrook                        OBJECT IDENTIFIER ::= { enterprises 787 }
unifiedSystemsSolutions           OBJECT IDENTIFIER ::= { enterprises 788 }
networkApplianceCorporation       OBJECT IDENTIFIER ::= { enterprises 789 }
ornetDataCommunicationTechnologies OBJECT IDENTIFIER ::= { enterprises 790 }
computerAssociatesInternational   OBJECT IDENTIFIER ::= { enterprises 791 }
multipointNetwork                 OBJECT IDENTIFIER ::= { enterprises 792 }
nynexScienceAndTechnology         OBJECT IDENTIFIER ::= { enterprises 793 }
commercialLinkSystems             OBJECT IDENTIFIER ::= { enterprises 794 }
adaptec                           OBJECT IDENTIFIER ::= { enterprises 795 }
softswitch                        OBJECT IDENTIFIER ::= { enterprises 796 }
linkTechnologies                  OBJECT IDENTIFIER ::= { enterprises 797 }
iis                               OBJECT IDENTIFIER ::= { enterprises 798 }
mobileSolutions                   OBJECT IDENTIFIER ::= { enterprises 799 }
xylanCorp                         OBJECT IDENTIFIER ::= { enterprises 800 }
airtechSoftwareForgeLimited       OBJECT IDENTIFIER ::= { enterprises 801 }
nationalSemiconductor             OBJECT IDENTIFIER ::= { enterprises 802 }
videoLotteryTechnologies          OBJECT IDENTIFIER ::= { enterprises 803 }
nationalSemiconductorCorp         OBJECT IDENTIFIER ::= { enterprises 804 }
applicationsManagementCorp        OBJECT IDENTIFIER ::= { enterprises 805 }
travelersInsuranceCompany         OBJECT IDENTIFIER ::= { enterprises 806 }
taiwanInternationalStandardElectronics OBJECT IDENTIFIER ::= { enterprises 807 }
usPatentAndTrademarkOffice        OBJECT IDENTIFIER ::= { enterprises 808 }
hynet                             OBJECT IDENTIFIER ::= { enterprises 809 }
aydin                             OBJECT IDENTIFIER ::= { enterprises 810 }
addtronTechnologyCo               OBJECT IDENTIFIER ::= { enterprises 811 }
fannieMae                         OBJECT IDENTIFIER ::= { enterprises 812 }
multinetServices                  OBJECT IDENTIFIER ::= { enterprises 813 }
geckoMbH                          OBJECT IDENTIFIER ::= { enterprises 814 }
memorexTelex                      OBJECT IDENTIFIER ::= { enterprises 815 }
advancedCommunicationsNetworks    OBJECT IDENTIFIER ::= { enterprises 816 }
telekursAG                        OBJECT IDENTIFIER ::= { enterprises 817 }
victronBv                         OBJECT IDENTIFIER ::= { enterprises 818 }
cf6Company                        OBJECT IDENTIFIER ::= { enterprises 819 }
walkerRicherAndQuinn              OBJECT IDENTIFIER ::= { enterprises 820 }
saturnSystems                     OBJECT IDENTIFIER ::= { enterprises 821 }
mitsuiMarineAndFireInsuranceCoLTD OBJECT IDENTIFIER ::= { enterprises 822 }
loopTelecommunicationInternational OBJECT IDENTIFIER ::= { enterprises 823 }
telenexCorporation                OBJECT IDENTIFIER ::= { enterprises 824 }
busTech                           OBJECT IDENTIFIER ::= { enterprises 825 }
atrie                             OBJECT IDENTIFIER ::= { enterprises 826 }
gallagherAndRobertsonAS           OBJECT IDENTIFIER ::= { enterprises 827 }
networksNorthwest                 OBJECT IDENTIFIER ::= { enterprises 828 }
connerPeripherials                OBJECT IDENTIFIER ::= { enterprises 829 }
elfAntarFrance                    OBJECT IDENTIFIER ::= { enterprises 830 }
lloydInternetworking              OBJECT IDENTIFIER ::= { enterprises 831 }
datatecIndustries                 OBJECT IDENTIFIER ::= { enterprises 832 }
taicom                            OBJECT IDENTIFIER ::= { enterprises 833 }
brown                             OBJECT IDENTIFIER ::= { enterprises 834 }
milanTechnologyCorp               OBJECT IDENTIFIER ::= { enterprises 835 }
netedgeSystems                    OBJECT IDENTIFIER ::= { enterprises 836 }
netframeSystems                   OBJECT IDENTIFIER ::= { enterprises 837 }
xediaCorporation                  OBJECT IDENTIFIER ::= { enterprises 838 }
pepsi                             OBJECT IDENTIFIER ::= { enterprises 839 }
tricordSystems                    OBJECT IDENTIFIER ::= { enterprises 840 }
proxim                            OBJECT IDENTIFIER ::= { enterprises 841 }
applicationsPlus                  OBJECT IDENTIFIER ::= { enterprises 842 }
pacificBell                       OBJECT IDENTIFIER ::= { enterprises 843 }
scorpioCommunications             OBJECT IDENTIFIER ::= { enterprises 844 }
tpsTeleprocessingSystems          OBJECT IDENTIFIER ::= { enterprises 845 }
technologySolutionsCompany        OBJECT IDENTIFIER ::= { enterprises 846 }
computerSiteTechnologies          OBJECT IDENTIFIER ::= { enterprises 847 }
netportSoftware                   OBJECT IDENTIFIER ::= { enterprises 848 }
alonSystems                       OBJECT IDENTIFIER ::= { enterprises 849 }
trippLite                         OBJECT IDENTIFIER ::= { enterprises 850 }
netcommLimited                    OBJECT IDENTIFIER ::= { enterprises 851 }
precisionSystems                  OBJECT IDENTIFIER ::= { enterprises 852 }
objectiveSystemsIntegrators       OBJECT IDENTIFIER ::= { enterprises 853 }
simpactAssociates                 OBJECT IDENTIFIER ::= { enterprises 854 }
systemsEnhancementCorporation     OBJECT IDENTIFIER ::= { enterprises 855 }
informationIntegration            OBJECT IDENTIFIER ::= { enterprises 856 }
cetrelSC                          OBJECT IDENTIFIER ::= { enterprises 857 }
platinumTechnology                OBJECT IDENTIFIER ::= { enterprises 858 }
olivettiNorthAmerica              OBJECT IDENTIFIER ::= { enterprises 859 }
wilma                             OBJECT IDENTIFIER ::= { enterprises 860 }
ilxSystems                        OBJECT IDENTIFIER ::= { enterprises 861 }
totalPeripherals                  OBJECT IDENTIFIER ::= { enterprises 862 }
sunnetworksConsultant             OBJECT IDENTIFIER ::= { enterprises 863 }
arkhonTechnologies                OBJECT IDENTIFIER ::= { enterprises 864 }
computerSciencesCorporation       OBJECT IDENTIFIER ::= { enterprises 865 }
philipstrt                        OBJECT IDENTIFIER ::= { enterprises 866 }
katronTechnologies                OBJECT IDENTIFIER ::= { enterprises 867 }
transitionEngineering             OBJECT IDENTIFIER ::= { enterprises 868 }
altosEngineeringApplications      OBJECT IDENTIFIER ::= { enterprises 869 }
nicecom                           OBJECT IDENTIFIER ::= { enterprises 870 }
fiskarsDeltec                     OBJECT IDENTIFIER ::= { enterprises 871 }
avmGmbH                           OBJECT IDENTIFIER ::= { enterprises 872 }
commVision                        OBJECT IDENTIFIER ::= { enterprises 873 }
instituteForInformationIndustry   OBJECT IDENTIFIER ::= { enterprises 874 }
legentCorporation                 OBJECT IDENTIFIER ::= { enterprises 875 }
networkAutomation                 OBJECT IDENTIFIER ::= { enterprises 876 }
nettech                           OBJECT IDENTIFIER ::= { enterprises 877 }
comanDataCommunications           OBJECT IDENTIFIER ::= { enterprises 878 }
skattedirektoratet                OBJECT IDENTIFIER ::= { enterprises 879 }
clientServerTechnologies          OBJECT IDENTIFIER ::= { enterprises 880 }
societeInternationaleDeTelecommunicationsAeronautiques OBJECT IDENTIFIER ::= { enterprises 881 }
maximumStrategy                   OBJECT IDENTIFIER ::= { enterprises 882 }
integratedSystems                 OBJECT IDENTIFIER ::= { enterprises 883 }
eSystems                          OBJECT IDENTIFIER ::= { enterprises 884 }
relianceCommTec                   OBJECT IDENTIFIER ::= { enterprises 885 }
summaFour                         OBJECT IDENTIFIER ::= { enterprises 886 }
jAndLInformationSystems           OBJECT IDENTIFIER ::= { enterprises 887 }
forestComputer                    OBJECT IDENTIFIER ::= { enterprises 888 }
palindromeCorp                    OBJECT IDENTIFIER ::= { enterprises 889 }
zyxelCommunicationsCorp           OBJECT IDENTIFIER ::= { enterprises 890 }
networkManagers                   OBJECT IDENTIFIER ::= { enterprises 891 }
sensibleOfficeSystems             OBJECT IDENTIFIER ::= { enterprises 892 }
informixSoftware                  OBJECT IDENTIFIER ::= { enterprises 893 }
dynatekCommunications             OBJECT IDENTIFIER ::= { enterprises 894 }
versalynxCorp                     OBJECT IDENTIFIER ::= { enterprises 895 }
potomacSchedulingCommunicationsCompany OBJECT IDENTIFIER ::= { enterprises 896 }
sybase                            OBJECT IDENTIFIER ::= { enterprises 897 }
divicom                           OBJECT IDENTIFIER ::= { enterprises 898 }
datusElektronischeInformationssystemeGmbH OBJECT IDENTIFIER ::= { enterprises 899 }
matroxElectronicSystemsLimited    OBJECT IDENTIFIER ::= { enterprises 900 }
digitalProducts                   OBJECT IDENTIFIER ::= { enterprises 901 }
scitexCorp                        OBJECT IDENTIFIER ::= { enterprises 902 }
radVision                         OBJECT IDENTIFIER ::= { enterprises 903 }
tranNetworkSystems                OBJECT IDENTIFIER ::= { enterprises 904 }
scorpionLogic                     OBJECT IDENTIFIER ::= { enterprises 905 }
inotech                           OBJECT IDENTIFIER ::= { enterprises 906 }
controlledPowerCo                 OBJECT IDENTIFIER ::= { enterprises 907 }
elsagBailey                       OBJECT IDENTIFIER ::= { enterprises 908 }
jpMorgan                          OBJECT IDENTIFIER ::= { enterprises 909 }
clearCommunicationsCorp           OBJECT IDENTIFIER ::= { enterprises 910 }
generalTechnology                 OBJECT IDENTIFIER ::= { enterprises 911 }
adax                              OBJECT IDENTIFIER ::= { enterprises 912 }
mtelTechnologies                  OBJECT IDENTIFIER ::= { enterprises 913 }
underscore                        OBJECT IDENTIFIER ::= { enterprises 914 }
sercommCorp                       OBJECT IDENTIFIER ::= { enterprises 915 }
baxterHealthcareCorporation       OBJECT IDENTIFIER ::= { enterprises 916 }
tellusTechnology                  OBJECT IDENTIFIER ::= { enterprises 917 }
continuousElectronBeamAcceleratorFacility OBJECT IDENTIFIER ::= { enterprises 918 }
canogaPerkins                     OBJECT IDENTIFIER ::= { enterprises 919 }
risTechnologies                   OBJECT IDENTIFIER ::= { enterprises 920 }
infonexCorp                       OBJECT IDENTIFIER ::= { enterprises 921 }
wordperfectCorp                   OBJECT IDENTIFIER ::= { enterprises 922 }
nrad                              OBJECT IDENTIFIER ::= { enterprises 923 }
hongKongTelecommunications        OBJECT IDENTIFIER ::= { enterprises 924 }
signatureSystems                  OBJECT IDENTIFIER ::= { enterprises 925 }
alphaTechnologiesLTD              OBJECT IDENTIFIER ::= { enterprises 926 }
pairgainTechnologies              OBJECT IDENTIFIER ::= { enterprises 927 }
sonicSystems                      OBJECT IDENTIFIER ::= { enterprises 928 }
steinbrecherCorp                  OBJECT IDENTIFIER ::= { enterprises 929 }
centillionNetworks                OBJECT IDENTIFIER ::= { enterprises 930 }
networkCommunicationCorp          OBJECT IDENTIFIER ::= { enterprises 931 }
sysnetAS                          OBJECT IDENTIFIER ::= { enterprises 932 }
telecommunicationSystemsLab       OBJECT IDENTIFIER ::= { enterprises 933 }
qmi                               OBJECT IDENTIFIER ::= { enterprises 934 }
phoenixtecPowerCo                 OBJECT IDENTIFIER ::= { enterprises 935 }
hirakawaHewtechCorp               OBJECT IDENTIFIER ::= { enterprises 936 }
noWiresNeededBV                   OBJECT IDENTIFIER ::= { enterprises 937 }
primaryAccess                     OBJECT IDENTIFIER ::= { enterprises 938 }
fdSoftwareAS                      OBJECT IDENTIFIER ::= { enterprises 939 }
grabnerAndKapferGnbR              OBJECT IDENTIFIER ::= { enterprises 940 }
nemesysResearch                   OBJECT IDENTIFIER ::= { enterprises 941 }
pacificCommunicationSciences      OBJECT IDENTIFIER ::= { enterprises 942 }
levelOneCommunications            OBJECT IDENTIFIER ::= { enterprises 943 }
fastTrack                         OBJECT IDENTIFIER ::= { enterprises 944 }
andersenConsulting                OBJECT IDENTIFIER ::= { enterprises 945 }
bayTechnologiesPty                OBJECT IDENTIFIER ::= { enterprises 946 }
integratedNetworkCorp             OBJECT IDENTIFIER ::= { enterprises 947 }
epoch                             OBJECT IDENTIFIER ::= { enterprises 948 }
wangLaboratories                  OBJECT IDENTIFIER ::= { enterprises 949 }
polaroidCorp                      OBJECT IDENTIFIER ::= { enterprises 950 }
sunriseSierra                     OBJECT IDENTIFIER ::= { enterprises 951 }
silconGroup                       OBJECT IDENTIFIER ::= { enterprises 952 }
coastcom                          OBJECT IDENTIFIER ::= { enterprises 953 }
thDIMENSIONSOFTWARELTD            OBJECT IDENTIFIER ::= { enterprises 954 }
seikoSYSTEMS                      OBJECT IDENTIFIER ::= { enterprises 955 }
perform                           OBJECT IDENTIFIER ::= { enterprises 956 }
tvCOMInternational                OBJECT IDENTIFIER ::= { enterprises 957 }
networkIntegration                OBJECT IDENTIFIER ::= { enterprises 958 }
solaElectric2                     OBJECT IDENTIFIER ::= { enterprises 959 }
gradientTechnologies              OBJECT IDENTIFIER ::= { enterprises 960 }
tokyoElectricCo                   OBJECT IDENTIFIER ::= { enterprises 961 }
codonics                          OBJECT IDENTIFIER ::= { enterprises 962 }
delftTechnicalUniversity          OBJECT IDENTIFIER ::= { enterprises 963 }
carrierAccessCorp                 OBJECT IDENTIFIER ::= { enterprises 964 }
eoncorp                           OBJECT IDENTIFIER ::= { enterprises 965 }
navalUnderseaWarfareCenter        OBJECT IDENTIFIER ::= { enterprises 966 }
awaLimited                        OBJECT IDENTIFIER ::= { enterprises 967 }
distinctCorp                      OBJECT IDENTIFIER ::= { enterprises 968 }
nationalTechnicalUniversityOfAthens OBJECT IDENTIFIER ::= { enterprises 969 }
bgsSystems                        OBJECT IDENTIFIER ::= { enterprises 970 }
mccawWirelessData                 OBJECT IDENTIFIER ::= { enterprises 971 }
bekaert                           OBJECT IDENTIFIER ::= { enterprises 972 }
epicData                          OBJECT IDENTIFIER ::= { enterprises 973 }
prodigyServicesCo                 OBJECT IDENTIFIER ::= { enterprises 974 }
firstPacificNetworks              OBJECT IDENTIFIER ::= { enterprises 975 }
xylink                            OBJECT IDENTIFIER ::= { enterprises 976 }
reliaTechnologiesCorp             OBJECT IDENTIFIER ::= { enterprises 977 }
legacyStorageSystems              OBJECT IDENTIFIER ::= { enterprises 978 }
digicom                           OBJECT IDENTIFIER ::= { enterprises 979 }
arkTelecom                        OBJECT IDENTIFIER ::= { enterprises 980 }
nationalSecurityAgency            OBJECT IDENTIFIER ::= { enterprises 981 }
southwesternBellCorporation       OBJECT IDENTIFIER ::= { enterprises 982 }
virtualDesignGroup                OBJECT IDENTIFIER ::= { enterprises 983 }
rhonePoulenc                      OBJECT IDENTIFIER ::= { enterprises 984 }
swissBankCorporation              OBJECT IDENTIFIER ::= { enterprises 985 }
ateaNV                            OBJECT IDENTIFIER ::= { enterprises 986 }
computerCommunicationsSpecialists OBJECT IDENTIFIER ::= { enterprises 987 }
objectQuest                       OBJECT IDENTIFIER ::= { enterprises 988 }
dclSystemInternational            OBJECT IDENTIFIER ::= { enterprises 989 }
solitonSYSTEMSKK                  OBJECT IDENTIFIER ::= { enterprises 990 }
uSSoftware                        OBJECT IDENTIFIER ::= { enterprises 991 }
systemsResearchAndApplicationsCorporation OBJECT IDENTIFIER ::= { enterprises 992 }
universityOfFlorida               OBJECT IDENTIFIER ::= { enterprises 993 }
dantel                            OBJECT IDENTIFIER ::= { enterprises 994 }
multiTechSystems                  OBJECT IDENTIFIER ::= { enterprises 995 }
softlink                          OBJECT IDENTIFIER ::= { enterprises 996 }
prosum                            OBJECT IDENTIFIER ::= { enterprises 997 }
marchSystemsConsultancy           OBJECT IDENTIFIER ::= { enterprises 998 }
hongTechnology                    OBJECT IDENTIFIER ::= { enterprises 999 }
internetAssignedNumbersAuthority  OBJECT IDENTIFIER ::= { enterprises 1000 }
pecoEnergyCo                      OBJECT IDENTIFIER ::= { enterprises 1001 }
unitedParcelService               OBJECT IDENTIFIER ::= { enterprises 1002 }
storageDimensions                 OBJECT IDENTIFIER ::= { enterprises 1003 }
itvTechnologies                   OBJECT IDENTIFIER ::= { enterprises 1004 }
tcpsi                             OBJECT IDENTIFIER ::= { enterprises 1005 }
promptusCommunications            OBJECT IDENTIFIER ::= { enterprises 1006 }
normanDataDefenseSystems          OBJECT IDENTIFIER ::= { enterprises 1007 }
pilotNetworkServices              OBJECT IDENTIFIER ::= { enterprises 1008 }
integratedSystemsSolutionsCorporation OBJECT IDENTIFIER ::= { enterprises 1009 }
sisro                             OBJECT IDENTIFIER ::= { enterprises 1010 }
netvantage                        OBJECT IDENTIFIER ::= { enterprises 1011 }
marconiSpA                        OBJECT IDENTIFIER ::= { enterprises 1012 }
surecom                           OBJECT IDENTIFIER ::= { enterprises 1013 }
royalHongKongJockeyClub           OBJECT IDENTIFIER ::= { enterprises 1014 }
gupta                             OBJECT IDENTIFIER ::= { enterprises 1015 }
toneSoftwareCorporation           OBJECT IDENTIFIER ::= { enterprises 1016 }
opusTelecom                       OBJECT IDENTIFIER ::= { enterprises 1017 }
cogsys                            OBJECT IDENTIFIER ::= { enterprises 1018 }
komatsu                           OBJECT IDENTIFIER ::= { enterprises 1019 }
roiSystems                        OBJECT IDENTIFIER ::= { enterprises 1020 }
lightningInstrumentationSA        OBJECT IDENTIFIER ::= { enterprises 1021 }
timestepCorp                      OBJECT IDENTIFIER ::= { enterprises 1022 }
intelsat                          OBJECT IDENTIFIER ::= { enterprises 1023 }
networkResearchCorporationJapan   OBJECT IDENTIFIER ::= { enterprises 1024 }
relationalDevelopment             OBJECT IDENTIFIER ::= { enterprises 1025 }
emeraldSystems                    OBJECT IDENTIFIER ::= { enterprises 1026 }
mitel                             OBJECT IDENTIFIER ::= { enterprises 1027 }
softwareAG                        OBJECT IDENTIFIER ::= { enterprises 1028 }
millennet                         OBJECT IDENTIFIER ::= { enterprises 1029 }
nkEXACorp                         OBJECT IDENTIFIER ::= { enterprises 1030 }
bmcSoftware                       OBJECT IDENTIFIER ::= { enterprises 1031 }
starfireEnterprises               OBJECT IDENTIFIER ::= { enterprises 1032 }
hybridNetworks                    OBJECT IDENTIFIER ::= { enterprises 1033 }
quantumSoftwareGmbH               OBJECT IDENTIFIER ::= { enterprises 1034 }
openvisionTechnologiesLimited     OBJECT IDENTIFIER ::= { enterprises 1035 }
healthcareCommunications          OBJECT IDENTIFIER ::= { enterprises 1036 }
saitSystems                       OBJECT IDENTIFIER ::= { enterprises 1037 }
sat                               OBJECT IDENTIFIER ::= { enterprises 1038 }
compusci                          OBJECT IDENTIFIER ::= { enterprises 1039 }
aimTechnology                     OBJECT IDENTIFIER ::= { enterprises 1040 }
ciesin                            OBJECT IDENTIFIER ::= { enterprises 1041 }
systemsAndTechnologiesInternational OBJECT IDENTIFIER ::= { enterprises 1042 }
israeliElectricCompany            OBJECT IDENTIFIER ::= { enterprises 1043 }
phoenixWirelessGroup              OBJECT IDENTIFIER ::= { enterprises 1044 }
swl                               OBJECT IDENTIFIER ::= { enterprises 1045 }
ncube                             OBJECT IDENTIFIER ::= { enterprises 1046 }
cerner                            OBJECT IDENTIFIER ::= { enterprises 1047 }
andersenConsulting2               OBJECT IDENTIFIER ::= { enterprises 1048 }
lincolnTelephoneCompany           OBJECT IDENTIFIER ::= { enterprises 1049 }
acer                              OBJECT IDENTIFIER ::= { enterprises 1050 }
cedros                            OBJECT IDENTIFIER ::= { enterprises 1051 }
airaccess                         OBJECT IDENTIFIER ::= { enterprises 1052 }
expersoftCorporation              OBJECT IDENTIFIER ::= { enterprises 1053 }
eskom                             OBJECT IDENTIFIER ::= { enterprises 1054 }
sbe                               OBJECT IDENTIFIER ::= { enterprises 1055 }
ebs                               OBJECT IDENTIFIER ::= { enterprises 1056 }
americanComputerAndElectronics    OBJECT IDENTIFIER ::= { enterprises 1057 }
syndesisLimited                   OBJECT IDENTIFIER ::= { enterprises 1058 }
isisDistributedSystems            OBJECT IDENTIFIER ::= { enterprises 1059 }
priorityCallManagement            OBJECT IDENTIFIER ::= { enterprises 1060 }
koelschAndAltmannGmbH             OBJECT IDENTIFIER ::= { enterprises 1061 }
wiproINFOTECHLTDChandrashekarKapse OBJECT IDENTIFIER ::= { enterprises 1062 }
controlware                       OBJECT IDENTIFIER ::= { enterprises 1063 }
mosaicSoftware                    OBJECT IDENTIFIER ::= { enterprises 1064 }
canonInformationSystems           OBJECT IDENTIFIER ::= { enterprises 1065 }
americaonline                     OBJECT IDENTIFIER ::= { enterprises 1066 }
whitetreeNetworkTechnologies      OBJECT IDENTIFIER ::= { enterprises 1067 }
xetronCorp                        OBJECT IDENTIFIER ::= { enterprises 1068 }
targetConcepts                    OBJECT IDENTIFIER ::= { enterprises 1069 }
dmhSoftware                       OBJECT IDENTIFIER ::= { enterprises 1070 }
innosoftInternational             OBJECT IDENTIFIER ::= { enterprises 1071 }
controlwareGmbH                   OBJECT IDENTIFIER ::= { enterprises 1072 }
telecommunicationsIndustryAssociation OBJECT IDENTIFIER ::= { enterprises 1073 }
booleAndBabbage                   OBJECT IDENTIFIER ::= { enterprises 1074 }
systemEngineeringSupport          OBJECT IDENTIFIER ::= { enterprises 1075 }
surfnet                           OBJECT IDENTIFIER ::= { enterprises 1076 }
openconnectSystems                OBJECT IDENTIFIER ::= { enterprises 1077 }
pdts                              OBJECT IDENTIFIER ::= { enterprises 1078 }
cornet                            OBJECT IDENTIFIER ::= { enterprises 1079 }
netstar                           OBJECT IDENTIFIER ::= { enterprises 1080 }
semaphoreCommunications           OBJECT IDENTIFIER ::= { enterprises 1081 }
casioComputerCo                   OBJECT IDENTIFIER ::= { enterprises 1082 }
csir                              OBJECT IDENTIFIER ::= { enterprises 1083 }
apogeeCommunications              OBJECT IDENTIFIER ::= { enterprises 1084 }
informationManagementCompany      OBJECT IDENTIFIER ::= { enterprises 1085 }
wordlink                          OBJECT IDENTIFIER ::= { enterprises 1086 }
peer                              OBJECT IDENTIFIER ::= { enterprises 1087 }
telstraCorp                       OBJECT IDENTIFIER ::= { enterprises 1088 }
netX                              OBJECT IDENTIFIER ::= { enterprises 1089 }
pncPLC                            OBJECT IDENTIFIER ::= { enterprises 1090 }
danasoft                          OBJECT IDENTIFIER ::= { enterprises 1091 }
yokogawaHewlettPackard            OBJECT IDENTIFIER ::= { enterprises 1092 }
universitiesOfAustriaEurope       OBJECT IDENTIFIER ::= { enterprises 1093 }
linkTelecom                       OBJECT IDENTIFIER ::= { enterprises 1094 }
xirionBv                          OBJECT IDENTIFIER ::= { enterprises 1095 }
centigramCommunications           OBJECT IDENTIFIER ::= { enterprises 1096 }
gensymCorp                        OBJECT IDENTIFIER ::= { enterprises 1097 }
apricotComputers                  OBJECT IDENTIFIER ::= { enterprises 1098 }
canal                             OBJECT IDENTIFIER ::= { enterprises 1099 }
cambridgeTechnologyPartners       OBJECT IDENTIFIER ::= { enterprises 1100 }
monetSystems                      OBJECT IDENTIFIER ::= { enterprises 1101 }
metricom                          OBJECT IDENTIFIER ::= { enterprises 1102 }
xact                              OBJECT IDENTIFIER ::= { enterprises 1103 }
firstVirtualHoldings              OBJECT IDENTIFIER ::= { enterprises 1104 }
netcellSystems                    OBJECT IDENTIFIER ::= { enterprises 1105 }
uniQ                              OBJECT IDENTIFIER ::= { enterprises 1106 }
disaSpaceSystemsDevelopmentDivision OBJECT IDENTIFIER ::= { enterprises 1107 }
intersolv                         OBJECT IDENTIFIER ::= { enterprises 1108 }
velaResearch                      OBJECT IDENTIFIER ::= { enterprises 1109 }
tetherlessAccess                  OBJECT IDENTIFIER ::= { enterprises 1110 }
magistratWien                     OBJECT IDENTIFIER ::= { enterprises 1111 }
franklinTelecom                   OBJECT IDENTIFIER ::= { enterprises 1112 }
edaInstruments                    OBJECT IDENTIFIER ::= { enterprises 1113 }
efiElectronics                    OBJECT IDENTIFIER ::= { enterprises 1114 }
gmd                               OBJECT IDENTIFIER ::= { enterprises 1115 }
voicetek                          OBJECT IDENTIFIER ::= { enterprises 1116 }
avantiTechnology                  OBJECT IDENTIFIER ::= { enterprises 1117 }
atlanLTD                          OBJECT IDENTIFIER ::= { enterprises 1118 }
lehmanBrothers                    OBJECT IDENTIFIER ::= { enterprises 1119 }
lanHopperSystems                  OBJECT IDENTIFIER ::= { enterprises 1120 }
webSystems                        OBJECT IDENTIFIER ::= { enterprises 1121 }
pillerGmbH                        OBJECT IDENTIFIER ::= { enterprises 1122 }
symbiosLogic                      OBJECT IDENTIFIER ::= { enterprises 1123 }
netspan                           OBJECT IDENTIFIER ::= { enterprises 1124 }
nielsenMediaResearch              OBJECT IDENTIFIER ::= { enterprises 1125 }
sterlingSoftware                  OBJECT IDENTIFIER ::= { enterprises 1126 }
appliedNetworkTechnology          OBJECT IDENTIFIER ::= { enterprises 1127 }
unionPacificRailroad              OBJECT IDENTIFIER ::= { enterprises 1128 }
tecCorporation                    OBJECT IDENTIFIER ::= { enterprises 1129 }
datametricsSystems                OBJECT IDENTIFIER ::= { enterprises 1130 }
intersectionDevelopmentCorporation OBJECT IDENTIFIER ::= { enterprises 1131 }
bacsLimited                       OBJECT IDENTIFIER ::= { enterprises 1132 }
engageCommunication               OBJECT IDENTIFIER ::= { enterprises 1133 }
fastware                          OBJECT IDENTIFIER ::= { enterprises 1134 }
longshineElectronicsCorpCTTseng   OBJECT IDENTIFIER ::= { enterprises 1135 }
bowSoftware                       OBJECT IDENTIFIER ::= { enterprises 1136 }
emotion                           OBJECT IDENTIFIER ::= { enterprises 1137 }
rautaruukkiSteelFactory           OBJECT IDENTIFIER ::= { enterprises 1138 }
emcCorp                           OBJECT IDENTIFIER ::= { enterprises 1139 }
universityOfWestEngland           OBJECT IDENTIFIER ::= { enterprises 1140 }
com21                             OBJECT IDENTIFIER ::= { enterprises 1141 }
compressionTehnologies            OBJECT IDENTIFIER ::= { enterprises 1142 }
buslogic                          OBJECT IDENTIFIER ::= { enterprises 1143 }
firefoxCorporation                OBJECT IDENTIFIER ::= { enterprises 1144 }
mercuryCommunications             OBJECT IDENTIFIER ::= { enterprises 1145 }
computerPROTOCOLMALAYSIASDNBHD    OBJECT IDENTIFIER ::= { enterprises 1146 }
instituteForInformationIndustry   OBJECT IDENTIFIER ::= { enterprises 1147 }
pacificElectricWireAndCableCo     OBJECT IDENTIFIER ::= { enterprises 1148 }
mprTeltech                        OBJECT IDENTIFIER ::= { enterprises 1149 }
pCOM                              OBJECT IDENTIFIER ::= { enterprises 1150 }
anritsuCorporation                OBJECT IDENTIFIER ::= { enterprises 1151 }
spyrus                            OBJECT IDENTIFIER ::= { enterprises 1152 }
netpower                          OBJECT IDENTIFIER ::= { enterprises 1153 }
diehlISDNGmbH                     OBJECT IDENTIFIER ::= { enterprises 1154 }
carnet                            OBJECT IDENTIFIER ::= { enterprises 1155 }
asTECH                            OBJECT IDENTIFIER ::= { enterprises 1156 }
sg2InnovationEtProduits           OBJECT IDENTIFIER ::= { enterprises 1157 }
cellaccessTechnology              OBJECT IDENTIFIER ::= { enterprises 1158 }
bureauOfMeteorology               OBJECT IDENTIFIER ::= { enterprises 1159 }
hiTECHConnections                 OBJECT IDENTIFIER ::= { enterprises 1160 }
thamesWaterUtilitiesLimited       OBJECT IDENTIFIER ::= { enterprises 1161 }
micropolis                        OBJECT IDENTIFIER ::= { enterprises 1162 }
integratedSystemsTechnology       OBJECT IDENTIFIER ::= { enterprises 1163 }
briteVoiceSystems                 OBJECT IDENTIFIER ::= { enterprises 1164 }
associatedGrocer                  OBJECT IDENTIFIER ::= { enterprises 1165 }
generalInstrument                 OBJECT IDENTIFIER ::= { enterprises 1166 }
stanfordTelecom                   OBJECT IDENTIFIER ::= { enterprises 1167 }
icomInformatique                  OBJECT IDENTIFIER ::= { enterprises 1168 }
mpxDataSystems                    OBJECT IDENTIFIER ::= { enterprises 1169 }
syntellect                        OBJECT IDENTIFIER ::= { enterprises 1170 }
perihelionTechnology              OBJECT IDENTIFIER ::= { enterprises 1171 }
shoppersDrugMart                  OBJECT IDENTIFIER ::= { enterprises 1172 }
apolloTravelServices              OBJECT IDENTIFIER ::= { enterprises 1173 }
timeWarnerCable                   OBJECT IDENTIFIER ::= { enterprises 1174 }
americanTechnologyLabs            OBJECT IDENTIFIER ::= { enterprises 1175 }
dowJonesAndCompany                OBJECT IDENTIFIER ::= { enterprises 1176 }
fra                               OBJECT IDENTIFIER ::= { enterprises 1177 }
equitableLifeAssuranceSociety     OBJECT IDENTIFIER ::= { enterprises 1178 }
smithBarney                       OBJECT IDENTIFIER ::= { enterprises 1179 }
compactData                       OBJECT IDENTIFIER ::= { enterprises 1180 }
inetCommunications                OBJECT IDENTIFIER ::= { enterprises 1181 }
yamahaCorporation                 OBJECT IDENTIFIER ::= { enterprises 1182 }
illinoisStateUniversity           OBJECT IDENTIFIER ::= { enterprises 1183 }
radguard                          OBJECT IDENTIFIER ::= { enterprises 1184 }
calypsoSoftwareSystems            OBJECT IDENTIFIER ::= { enterprises 1185 }
actNetworks                       OBJECT IDENTIFIER ::= { enterprises 1186 }
kingstonCommunications            OBJECT IDENTIFIER ::= { enterprises 1187 }
incite                            OBJECT IDENTIFIER ::= { enterprises 1188 }
vvnet                             OBJECT IDENTIFIER ::= { enterprises 1189 }
ontarioHydro                      OBJECT IDENTIFIER ::= { enterprises 1190 }
csTelecom                         OBJECT IDENTIFIER ::= { enterprises 1191 }
ictv                              OBJECT IDENTIFIER ::= { enterprises 1192 }
coreInternational                 OBJECT IDENTIFIER ::= { enterprises 1193 }
mibs4you                          OBJECT IDENTIFIER ::= { enterprises 1194 }
itk                               OBJECT IDENTIFIER ::= { enterprises 1195 }
networkIntegrity                  OBJECT IDENTIFIER ::= { enterprises 1196 }
bluelineSoftware                  OBJECT IDENTIFIER ::= { enterprises 1197 }
migrantComputingServices          OBJECT IDENTIFIER ::= { enterprises 1198 }
linklatersAndPaines               OBJECT IDENTIFIER ::= { enterprises 1199 }
ejvPartners                       OBJECT IDENTIFIER ::= { enterprises 1200 }
softwareAndSystemsEngineering     OBJECT IDENTIFIER ::= { enterprises 1201 }
varcomCorporation                 OBJECT IDENTIFIER ::= { enterprises 1202 }
equitel                           OBJECT IDENTIFIER ::= { enterprises 1203 }
theSouthernCompany                OBJECT IDENTIFIER ::= { enterprises 1204 }
dataproductsCorporation           OBJECT IDENTIFIER ::= { enterprises 1205 }
nationalElectricalManufacturersAssociation OBJECT IDENTIFIER ::= { enterprises 1206 }
riscmanagement                    OBJECT IDENTIFIER ::= { enterprises 1207 }
gvcCorporation                    OBJECT IDENTIFIER ::= { enterprises 1208 }
timonware                         OBJECT IDENTIFIER ::= { enterprises 1209 }
capitalResourcesComputerCorporation OBJECT IDENTIFIER ::= { enterprises 1210 }
storageTechnologyCorporation      OBJECT IDENTIFIER ::= { enterprises 1211 }
tadiranTelecomunicationsLTD       OBJECT IDENTIFIER ::= { enterprises 1212 }
ncp                               OBJECT IDENTIFIER ::= { enterprises 1213 }
operationsControlSystems          OBJECT IDENTIFIER ::= { enterprises 1214 }
theNASDAQStockMarket              OBJECT IDENTIFIER ::= { enterprises 1215 }
tiernanCommunications             OBJECT IDENTIFIER ::= { enterprises 1216 }
goldman                           OBJECT IDENTIFIER ::= { enterprises 1217 }
advancedTelecommunicationsModules OBJECT IDENTIFIER ::= { enterprises 1218 }
phoenixDataCommunications         OBJECT IDENTIFIER ::= { enterprises 1219 }
qualityConsultingServices         OBJECT IDENTIFIER ::= { enterprises 1220 }
milan                             OBJECT IDENTIFIER ::= { enterprises 1221 }
instrumental                      OBJECT IDENTIFIER ::= { enterprises 1222 }
yellowTechnologyServices          OBJECT IDENTIFIER ::= { enterprises 1223 }
mierCommunications                OBJECT IDENTIFIER ::= { enterprises 1224 }
cableServicesGroup                OBJECT IDENTIFIER ::= { enterprises 1225 }
forteNetworks                     OBJECT IDENTIFIER ::= { enterprises 1226 }
americanManagementSystems         OBJECT IDENTIFIER ::= { enterprises 1227 }
choiceHotelsIntl                  OBJECT IDENTIFIER ::= { enterprises 1228 }
sehComputertechnik                OBJECT IDENTIFIER ::= { enterprises 1229 }
mcafeeAssociates                  OBJECT IDENTIFIER ::= { enterprises 1230 }
networkIntelligent                OBJECT IDENTIFIER ::= { enterprises 1231 }
luxcomTechnologies                OBJECT IDENTIFIER ::= { enterprises 1232 }
itron                             OBJECT IDENTIFIER ::= { enterprises 1233 }
linkageSoftware                   OBJECT IDENTIFIER ::= { enterprises 1234 }
spardatAG                         OBJECT IDENTIFIER ::= { enterprises 1235 }
verifone                          OBJECT IDENTIFIER ::= { enterprises 1236 }
revcoDS                           OBJECT IDENTIFIER ::= { enterprises 1237 }
hrbSystems                        OBJECT IDENTIFIER ::= { enterprises 1238 }
littonFibercom                    OBJECT IDENTIFIER ::= { enterprises 1239 }
xcd                               OBJECT IDENTIFIER ::= { enterprises 1240 }
prosjektleveranserAS              OBJECT IDENTIFIER ::= { enterprises 1241 }
halcyon                           OBJECT IDENTIFIER ::= { enterprises 1242 }
sbb                               OBJECT IDENTIFIER ::= { enterprises 1243 }
leutek                            OBJECT IDENTIFIER ::= { enterprises 1244 }
zeitnet                           OBJECT IDENTIFIER ::= { enterprises 1245 }
visualNetworks                    OBJECT IDENTIFIER ::= { enterprises 1246 }
coronetSystems                    OBJECT IDENTIFIER ::= { enterprises 1247 }
seikoEPSONCORPORATION             OBJECT IDENTIFIER ::= { enterprises 1248 }
dnhTechnologies                   OBJECT IDENTIFIER ::= { enterprises 1249 }
deluxeData                        OBJECT IDENTIFIER ::= { enterprises 1250 }
michaelAOkulski                   OBJECT IDENTIFIER ::= { enterprises 1251 }
saberSoftwareCorporation          OBJECT IDENTIFIER ::= { enterprises 1252 }
missionSystems                    OBJECT IDENTIFIER ::= { enterprises 1253 }
siemensPlesseyElectronicsSystems  OBJECT IDENTIFIER ::= { enterprises 1254 }
appliedCommunications             OBJECT IDENTIFIER ::= { enterprises 1255 }
transactionTechnology             OBJECT IDENTIFIER ::= { enterprises 1256 }
hst                               OBJECT IDENTIFIER ::= { enterprises 1257 }
michiganTechnologicalUniversity   OBJECT IDENTIFIER ::= { enterprises 1258 }
nextLevelCommunications           OBJECT IDENTIFIER ::= { enterprises 1259 }
instinetCorp                      OBJECT IDENTIFIER ::= { enterprises 1260 }
analogAndDigitalSystems           OBJECT IDENTIFIER ::= { enterprises 1261 }
ansaldoTrasportiSpA               OBJECT IDENTIFIER ::= { enterprises 1262 }
ecci                              OBJECT IDENTIFIER ::= { enterprises 1263 }
imatekCorporation                 OBJECT IDENTIFIER ::= { enterprises 1264 }
pttTelecomBv                      OBJECT IDENTIFIER ::= { enterprises 1265 }
dataRace                          OBJECT IDENTIFIER ::= { enterprises 1266 }
networkSafetyCorporation          OBJECT IDENTIFIER ::= { enterprises 1267 }
applicationDesTechniquesNouvellesEnElectronique OBJECT IDENTIFIER ::= { enterprises 1268 }
mfsCommunicationsCompany          OBJECT IDENTIFIER ::= { enterprises 1269 }
informationServicesDivision       OBJECT IDENTIFIER ::= { enterprises 1270 }
cienaCorporation                  OBJECT IDENTIFIER ::= { enterprises 1271 }
ascomNexion                       OBJECT IDENTIFIER ::= { enterprises 1272 }
standardNetworks                  OBJECT IDENTIFIER ::= { enterprises 1273 }
scientificResearchCorporation     OBJECT IDENTIFIER ::= { enterprises 1274 }
micadoSoftwareConsultGmbH         OBJECT IDENTIFIER ::= { enterprises 1275 }
concertManagementServices         OBJECT IDENTIFIER ::= { enterprises 1276 }
universityOfDelaware              OBJECT IDENTIFIER ::= { enterprises 1277 }
biasConsultancy                   OBJECT IDENTIFIER ::= { enterprises 1278 }
micromusePLC                      OBJECT IDENTIFIER ::= { enterprises 1279 }
translinkSystems                  OBJECT IDENTIFIER ::= { enterprises 1280 }
piNET                             OBJECT IDENTIFIER ::= { enterprises 1281 }
amberWaveSystems                  OBJECT IDENTIFIER ::= { enterprises 1282 }
superiorElectronicsGroup          OBJECT IDENTIFIER ::= { enterprises 1283 }
networkTelemetrics                OBJECT IDENTIFIER ::= { enterprises 1284 }
bswData                           OBJECT IDENTIFIER ::= { enterprises 1285 }
eciTelecom                        OBJECT IDENTIFIER ::= { enterprises 1286 }
broadvision                       OBJECT IDENTIFIER ::= { enterprises 1287 }
alfa                              OBJECT IDENTIFIER ::= { enterprises 1288 }
telefonicaSISTEMAS                OBJECT IDENTIFIER ::= { enterprises 1289 }
imageSciences                     OBJECT IDENTIFIER ::= { enterprises 1290 }
mitsubishiELECTRICINFORMATIONNETWORKCORPORATION OBJECT IDENTIFIER ::= { enterprises 1291 }
centralFlowManagementUnit         OBJECT IDENTIFIER ::= { enterprises 1292 }
woodsHoleOceanographicInstitution OBJECT IDENTIFIER ::= { enterprises 1293 }
raptorSystems                     OBJECT IDENTIFIER ::= { enterprises 1294 }
telelinkTechnologies              OBJECT IDENTIFIER ::= { enterprises 1295 }
firstVirtualCorporation           OBJECT IDENTIFIER ::= { enterprises 1296 }
networkServicesGroup              OBJECT IDENTIFIER ::= { enterprises 1297 }
silcomManufacturingTechnology     OBJECT IDENTIFIER ::= { enterprises 1298 }
netsoft                           OBJECT IDENTIFIER ::= { enterprises 1299 }
fidelityInvestments               OBJECT IDENTIFIER ::= { enterprises 1300 }
telradTelecommunications          OBJECT IDENTIFIER ::= { enterprises 1301 }
arcadaSoftware                    OBJECT IDENTIFIER ::= { enterprises 1302 }
leemahDataComSecurityCorporation  OBJECT IDENTIFIER ::= { enterprises 1303 }
secureware                        OBJECT IDENTIFIER ::= { enterprises 1304 }
usair                             OBJECT IDENTIFIER ::= { enterprises 1305 }
jetPropulsionLaboratory           OBJECT IDENTIFIER ::= { enterprises 1306 }
abitCo                            OBJECT IDENTIFIER ::= { enterprises 1307 }
dataplexPty                       OBJECT IDENTIFIER ::= { enterprises 1308 }
creativeInteractionTechnologies   OBJECT IDENTIFIER ::= { enterprises 1309 }
networkDefenders                  OBJECT IDENTIFIER ::= { enterprises 1310 }
optusCommunications               OBJECT IDENTIFIER ::= { enterprises 1311 }
klosTechnologies                  OBJECT IDENTIFIER ::= { enterprises 1312 }
acotec                            OBJECT IDENTIFIER ::= { enterprises 1313 }
datacommManagementSciences        OBJECT IDENTIFIER ::= { enterprises 1314 }
mgSOFTCo                          OBJECT IDENTIFIER ::= { enterprises 1315 }
plesseyTellumatSA                 OBJECT IDENTIFIER ::= { enterprises 1316 }
painewebber                       OBJECT IDENTIFIER ::= { enterprises 1317 }
datasys                           OBJECT IDENTIFIER ::= { enterprises 1318 }
qvc                               OBJECT IDENTIFIER ::= { enterprises 1319 }
iplSystems                        OBJECT IDENTIFIER ::= { enterprises 1320 }
pacificMicroData                  OBJECT IDENTIFIER ::= { enterprises 1321 }
desknetSystems                    OBJECT IDENTIFIER ::= { enterprises 1322 }
tcTechnologies                    OBJECT IDENTIFIER ::= { enterprises 1323 }
racotek                           OBJECT IDENTIFIER ::= { enterprises 1324 }
celsiustechAB                     OBJECT IDENTIFIER ::= { enterprises 1325 }
xingTechnologyCorpJonWalker       OBJECT IDENTIFIER ::= { enterprises 1326 }
dzineNv                           OBJECT IDENTIFIER ::= { enterprises 1327 }
electronicMerchantServices        OBJECT IDENTIFIER ::= { enterprises 1328 }
linmorInformationSystemsManagement OBJECT IDENTIFIER ::= { enterprises 1329 }
ablCanada                         OBJECT IDENTIFIER ::= { enterprises 1330 }
universityOfCoimbra               OBJECT IDENTIFIER ::= { enterprises 1331 }
iskratel                          OBJECT IDENTIFIER ::= { enterprises 1332 }
isaCo                             OBJECT IDENTIFIER ::= { enterprises 1333 }
connect                           OBJECT IDENTIFIER ::= { enterprises 1334 }
digitalVideo                      OBJECT IDENTIFIER ::= { enterprises 1335 }
intervoice                        OBJECT IDENTIFIER ::= { enterprises 1336 }
livewareTecnologiaAServicoA       OBJECT IDENTIFIER ::= { enterprises 1337 }
preceptSoftware                   OBJECT IDENTIFIER ::= { enterprises 1338 }
heroixCorporation                 OBJECT IDENTIFIER ::= { enterprises 1339 }
hollandHouseBV                    OBJECT IDENTIFIER ::= { enterprises 1340 }
dedalusEngenhariaSC               OBJECT IDENTIFIER ::= { enterprises 1341 }
gecALSTHOMIT                      OBJECT IDENTIFIER ::= { enterprises 1342 }
deutschesElektronenSynchrotron    OBJECT IDENTIFIER ::= { enterprises 1343 }
switchview                        OBJECT IDENTIFIER ::= { enterprises 1344 }
dacoll                            OBJECT IDENTIFIER ::= { enterprises 1345 }
netcorp                           OBJECT IDENTIFIER ::= { enterprises 1346 }
kyoceraCorporation                OBJECT IDENTIFIER ::= { enterprises 1347 }
theLongabergerCompany             OBJECT IDENTIFIER ::= { enterprises 1348 }
ilex                              OBJECT IDENTIFIER ::= { enterprises 1349 }
conservationThroughInnovation     OBJECT IDENTIFIER ::= { enterprises 1350 }
softwareTechnologiesCorporation   OBJECT IDENTIFIER ::= { enterprises 1351 }
multexSystems                     OBJECT IDENTIFIER ::= { enterprises 1352 }
gambitCommunications              OBJECT IDENTIFIER ::= { enterprises 1353 }
centralDataCorporation            OBJECT IDENTIFIER ::= { enterprises 1354 }
compucomSystems                   OBJECT IDENTIFIER ::= { enterprises 1355 }
generexSystemsGMBH                OBJECT IDENTIFIER ::= { enterprises 1356 }
periphonicsCorporation            OBJECT IDENTIFIER ::= { enterprises 1357 }
freddieMac                        OBJECT IDENTIFIER ::= { enterprises 1358 }
digitalEquipmentBv                OBJECT IDENTIFIER ::= { enterprises 1359 }
phonelinkPlc                      OBJECT IDENTIFIER ::= { enterprises 1360 }
voiceTelEnterprises               OBJECT IDENTIFIER ::= { enterprises 1361 }
audilog                           OBJECT IDENTIFIER ::= { enterprises 1362 }
sanrexCorporation                 OBJECT IDENTIFIER ::= { enterprises 1363 }
chloride                          OBJECT IDENTIFIER ::= { enterprises 1364 }
gaSystems                         OBJECT IDENTIFIER ::= { enterprises 1365 }
microdyneCorporation              OBJECT IDENTIFIER ::= { enterprises 1366 }
bostonCollege                     OBJECT IDENTIFIER ::= { enterprises 1367 }
franceTelecom                     OBJECT IDENTIFIER ::= { enterprises 1368 }
stonesoftCorp                     OBJECT IDENTIFIER ::= { enterprises 1369 }
agEdwardsAndSons                  OBJECT IDENTIFIER ::= { enterprises 1370 }
attachmateCorp                    OBJECT IDENTIFIER ::= { enterprises 1371 }
lsiLogic                          OBJECT IDENTIFIER ::= { enterprises 1372 }
interwaveCommunications           OBJECT IDENTIFIER ::= { enterprises 1373 }
mdlConsult                        OBJECT IDENTIFIER ::= { enterprises 1374 }
bunyipInformationSystems          OBJECT IDENTIFIER ::= { enterprises 1375 }
nashobaNetworks                   OBJECT IDENTIFIER ::= { enterprises 1376 }
comediaInformationAB              OBJECT IDENTIFIER ::= { enterprises 1377 }
harveyMuddCollege                 OBJECT IDENTIFIER ::= { enterprises 1378 }
firstNationalBankOfChicago        OBJECT IDENTIFIER ::= { enterprises 1379 }
departmentOfNationalDefence       OBJECT IDENTIFIER ::= { enterprises 1380 }
cbmTechnologies                   OBJECT IDENTIFIER ::= { enterprises 1381 }
interproc                         OBJECT IDENTIFIER ::= { enterprises 1382 }
glenayreRAndD                     OBJECT IDENTIFIER ::= { enterprises 1383 }
telenetGmbHKommunikationssysteme  OBJECT IDENTIFIER ::= { enterprises 1384 }
softlabGmbH                       OBJECT IDENTIFIER ::= { enterprises 1385 }
storageComputerCorporation        OBJECT IDENTIFIER ::= { enterprises 1386 }
nineTilesComputerSystems          OBJECT IDENTIFIER ::= { enterprises 1387 }
networkPeopleInternational        OBJECT IDENTIFIER ::= { enterprises 1388 }
simpleNetworkMagicCorporation     OBJECT IDENTIFIER ::= { enterprises 1389 }
stallionTechnologiesPty           OBJECT IDENTIFIER ::= { enterprises 1390 }
loanSystem                        OBJECT IDENTIFIER ::= { enterprises 1391 }
dlrDeutscheForschungsanstalt      OBJECT IDENTIFIER ::= { enterprises 1392 }
icra                              OBJECT IDENTIFIER ::= { enterprises 1393 }
probita                           OBJECT IDENTIFIER ::= { enterprises 1394 }
nexor                             OBJECT IDENTIFIER ::= { enterprises 1395 }
americanInternationFacsimileProducts OBJECT IDENTIFIER ::= { enterprises 1396 }
tellabs                           OBJECT IDENTIFIER ::= { enterprises 1397 }
datax                             OBJECT IDENTIFIER ::= { enterprises 1398 }
intellisysCorporation             OBJECT IDENTIFIER ::= { enterprises 1399 }
sandiaNationalLaboratories        OBJECT IDENTIFIER ::= { enterprises 1400 }
synerdyneCorp                     OBJECT IDENTIFIER ::= { enterprises 1401 }
unicomElectric                    OBJECT IDENTIFIER ::= { enterprises 1402 }
centralDesignSystems              OBJECT IDENTIFIER ::= { enterprises 1403 }
theSilkRoadGroup                  OBJECT IDENTIFIER ::= { enterprises 1404 }
positiveComputingConcepts         OBJECT IDENTIFIER ::= { enterprises 1405 }
firstDataResources                OBJECT IDENTIFIER ::= { enterprises 1406 }
inetcoSystemsLimited              OBJECT IDENTIFIER ::= { enterprises 1407 }
nttMobileCommunicationsNetwork    OBJECT IDENTIFIER ::= { enterprises 1408 }
targetStores                      OBJECT IDENTIFIER ::= { enterprises 1409 }
advancedPeripheralsTechnologies   OBJECT IDENTIFIER ::= { enterprises 1410 }
funkSoftware                      OBJECT IDENTIFIER ::= { enterprises 1411 }
dunsgate                          OBJECT IDENTIFIER ::= { enterprises 1412 }
afp                               OBJECT IDENTIFIER ::= { enterprises 1413 }
comsatRSIPrecisionControlsDivision OBJECT IDENTIFIER ::= { enterprises 1414 }
williamsEnergyServicesCompany     OBJECT IDENTIFIER ::= { enterprises 1415 }
aspTechnologies                   OBJECT IDENTIFIER ::= { enterprises 1416 }
philipsCommunicationSystems       OBJECT IDENTIFIER ::= { enterprises 1417 }
dataprobe                         OBJECT IDENTIFIER ::= { enterprises 1418 }
astrocomCORP                      OBJECT IDENTIFIER ::= { enterprises 1419 }
csti                              OBJECT IDENTIFIER ::= { enterprises 1420 }
sprint                            OBJECT IDENTIFIER ::= { enterprises 1421 }
syntax                            OBJECT IDENTIFIER ::= { enterprises 1422 }
lightINFOCON                      OBJECT IDENTIFIER ::= { enterprises 1423 }
performanceTechnology             OBJECT IDENTIFIER ::= { enterprises 1424 }
cxrTelecom                        OBJECT IDENTIFIER ::= { enterprises 1425 }
amirTechnologyLabs                OBJECT IDENTIFIER ::= { enterprises 1426 }
isocor                            OBJECT IDENTIFIER ::= { enterprises 1427 }
arrayTechnologyCorportion         OBJECT IDENTIFIER ::= { enterprises 1428 }
scientificAtlanta                 OBJECT IDENTIFIER ::= { enterprises 1429 }
gammatech                         OBJECT IDENTIFIER ::= { enterprises 1430 }
telkomSA                          OBJECT IDENTIFIER ::= { enterprises 1431 }
cirelSYSTEMES                     OBJECT IDENTIFIER ::= { enterprises 1432 }
redflexLimitedAustralia           OBJECT IDENTIFIER ::= { enterprises 1433 }
hermesEnterpriseMessagingLTD      OBJECT IDENTIFIER ::= { enterprises 1434 }
acaciaNetworks                    OBJECT IDENTIFIER ::= { enterprises 1435 }
nationalAUSTRALIABANKLTD          OBJECT IDENTIFIER ::= { enterprises 1436 }
sinetecTechnologyCo               OBJECT IDENTIFIER ::= { enterprises 1437 }
badgerTechnology                  OBJECT IDENTIFIER ::= { enterprises 1438 }
arizonaStateUniversity            OBJECT IDENTIFIER ::= { enterprises 1439 }
xionicsDocumentTechnologies       OBJECT IDENTIFIER ::= { enterprises 1440 }
southernInformationSystem         OBJECT IDENTIFIER ::= { enterprises 1441 }
nebulaConsultants                 OBJECT IDENTIFIER ::= { enterprises 1442 }
sitre                             OBJECT IDENTIFIER ::= { enterprises 1443 }
paradigmTechnology                OBJECT IDENTIFIER ::= { enterprises 1444 }
telubAB                           OBJECT IDENTIFIER ::= { enterprises 1445 }
communicationsNetworkServices     OBJECT IDENTIFIER ::= { enterprises 1446 }
martisOy                          OBJECT IDENTIFIER ::= { enterprises 1447 }
iskraTRANSMISSION                 OBJECT IDENTIFIER ::= { enterprises 1448 }
qualcomm                          OBJECT IDENTIFIER ::= { enterprises 1449 }
netscapeCommunicationsCorp        OBJECT IDENTIFIER ::= { enterprises 1450 }
bellsouthWireless                 OBJECT IDENTIFIER ::= { enterprises 1451 }
nukoInformationSystems            OBJECT IDENTIFIER ::= { enterprises 1452 }
ipcInformationSystems             OBJECT IDENTIFIER ::= { enterprises 1453 }
estudiosYProyectosDeTelecomunicacion OBJECT IDENTIFIER ::= { enterprises 1454 }
winstarWireless                   OBJECT IDENTIFIER ::= { enterprises 1455 }
terayonCorp                       OBJECT IDENTIFIER ::= { enterprises 1456 }
harrisComputerSystemsCorporation  OBJECT IDENTIFIER ::= { enterprises 1457 }
siliconSystems                    OBJECT IDENTIFIER ::= { enterprises 1458 }
jupiterTechnology                 OBJECT IDENTIFIER ::= { enterprises 1459 }
delphiInternetServices            OBJECT IDENTIFIER ::= { enterprises 1460 }
kesmaiCorporation                 OBJECT IDENTIFIER ::= { enterprises 1461 }
compactDevices                    OBJECT IDENTIFIER ::= { enterprises 1462 }
optiquest                         OBJECT IDENTIFIER ::= { enterprises 1463 }
loralDefenseSystemsEagan          OBJECT IDENTIFIER ::= { enterprises 1464 }
onrampTechnologies                OBJECT IDENTIFIER ::= { enterprises 1465 }
markWahl                          OBJECT IDENTIFIER ::= { enterprises 1466 }
loranInternationalTechnologies    OBJECT IDENTIFIER ::= { enterprises 1467 }
sAndSInternationalPLC             OBJECT IDENTIFIER ::= { enterprises 1468 }
atlantechTechnologies             OBJECT IDENTIFIER ::= { enterprises 1469 }
inSNEC                            OBJECT IDENTIFIER ::= { enterprises 1470 }
melitaInternationalCorporation    OBJECT IDENTIFIER ::= { enterprises 1471 }
sharpLaboratoriesOfAmerica        OBJECT IDENTIFIER ::= { enterprises 1472 }
groupeDecan                       OBJECT IDENTIFIER ::= { enterprises 1473 }
spectronicsMicroSystemsLimited    OBJECT IDENTIFIER ::= { enterprises 1474 }
pcPlusCOMPUTINGGmbH               OBJECT IDENTIFIER ::= { enterprises 1475 }
microframe                        OBJECT IDENTIFIER ::= { enterprises 1476 }
telegateGlobalAccessTechnology    OBJECT IDENTIFIER ::= { enterprises 1477 }
merrillLynchAndCo                 OBJECT IDENTIFIER ::= { enterprises 1478 }
jcpenneyCo                        OBJECT IDENTIFIER ::= { enterprises 1479 }
theTorringtonCompany              OBJECT IDENTIFIER ::= { enterprises 1480 }
gsProActive                       OBJECT IDENTIFIER ::= { enterprises 1481 }
barcoCommunicationSystems         OBJECT IDENTIFIER ::= { enterprises 1482 }
vortexComputersystemeGmbH         OBJECT IDENTIFIER ::= { enterprises 1483 }
datafusionSystems                 OBJECT IDENTIFIER ::= { enterprises 1484 }
allenAndOvery                     OBJECT IDENTIFIER ::= { enterprises 1485 }
atlanticSystemsGroup              OBJECT IDENTIFIER ::= { enterprises 1486 }
kongsbergInformasjonskontrollAS   OBJECT IDENTIFIER ::= { enterprises 1487 }
eltecoAs                          OBJECT IDENTIFIER ::= { enterprises 1488 }
schlumbergerLimited               OBJECT IDENTIFIER ::= { enterprises 1489 }
cniCommunicationsNetworkInternational OBJECT IDENTIFIER ::= { enterprises 1490 }
mAndcSystems                      OBJECT IDENTIFIER ::= { enterprises 1491 }
omSystemsInternational            OBJECT IDENTIFIER ::= { enterprises 1492 }
davic                             OBJECT IDENTIFIER ::= { enterprises 1493 }
ismGmbH                           OBJECT IDENTIFIER ::= { enterprises 1494 }
efJohnsonCo                       OBJECT IDENTIFIER ::= { enterprises 1495 }
baranofSoftware                   OBJECT IDENTIFIER ::= { enterprises 1496 }
universityOfTexasHouston          OBJECT IDENTIFIER ::= { enterprises 1497 }
ukiahSoftwareSolutions            OBJECT IDENTIFIER ::= { enterprises 1498 }
steria                            OBJECT IDENTIFIER ::= { enterprises 1499 }
atiAustraliaPtyLimited            OBJECT IDENTIFIER ::= { enterprises 1500 }
theAerospaceCorporation           OBJECT IDENTIFIER ::= { enterprises 1501 }
orckitCommunications              OBJECT IDENTIFIER ::= { enterprises 1502 }
tertioLimited                     OBJECT IDENTIFIER ::= { enterprises 1503 }
comsoft                           OBJECT IDENTIFIER ::= { enterprises 1504 }
innovativeSoftware                OBJECT IDENTIFIER ::= { enterprises 1505 }
technologic                       OBJECT IDENTIFIER ::= { enterprises 1506 }
northWestWaterLimited             OBJECT IDENTIFIER ::= { enterprises 1507 }
esigetel                          OBJECT IDENTIFIER ::= { enterprises 1508 }
illinoisBusinessTrainingCenter    OBJECT IDENTIFIER ::= { enterprises 1509 }
concertCommunicationsCorporation  OBJECT IDENTIFIER ::= { enterprises 1510 }
teamquestCorporation              OBJECT IDENTIFIER ::= { enterprises 1511 }
cellmuxCommunicationsCorporation  OBJECT IDENTIFIER ::= { enterprises 1512 }
skyrr                             OBJECT IDENTIFIER ::= { enterprises 1513 }
tecnologiaYGestionDeLaInnovacion  OBJECT IDENTIFIER ::= { enterprises 1514 }
connectorGmbH                     OBJECT IDENTIFIER ::= { enterprises 1515 }
kaspiaSystems                     OBJECT IDENTIFIER ::= { enterprises 1516 }
smithKlineBeechan                 OBJECT IDENTIFIER ::= { enterprises 1517 }
netcentricCorp                    OBJECT IDENTIFIER ::= { enterprises 1518 }
atecomGmbH                        OBJECT IDENTIFIER ::= { enterprises 1519 }
citibankCanada                    OBJECT IDENTIFIER ::= { enterprises 1520 }
mms                               OBJECT IDENTIFIER ::= { enterprises 1521 }
intermediaCommunicationsOfFlorida OBJECT IDENTIFIER ::= { enterprises 1522 }
schoolOfComputerScience           OBJECT IDENTIFIER ::= { enterprises 1523 }
universityOfLimerick              OBJECT IDENTIFIER ::= { enterprises 1524 }
actane                            OBJECT IDENTIFIER ::= { enterprises 1525 }
collaborativeInformationTechnologyResearchInstitute OBJECT IDENTIFIER ::= { enterprises 1526 }
intermediumAS                     OBJECT IDENTIFIER ::= { enterprises 1527 }
ansCORESystems                    OBJECT IDENTIFIER ::= { enterprises 1528 }
uunetTechnologies                 OBJECT IDENTIFIER ::= { enterprises 1529 }
telesciences                      OBJECT IDENTIFIER ::= { enterprises 1530 }
qscAudioProducts                  OBJECT IDENTIFIER ::= { enterprises 1531 }
australianDepartmentOfEmployment  OBJECT IDENTIFIER ::= { enterprises 1532 }
networkMediaCommunications        OBJECT IDENTIFIER ::= { enterprises 1533 }
sodalia                           OBJECT IDENTIFIER ::= { enterprises 1534 }
innovativeConcepts                OBJECT IDENTIFIER ::= { enterprises 1535 }
japanComputerIndustry             OBJECT IDENTIFIER ::= { enterprises 1536 }
telogyNetworks                    OBJECT IDENTIFIER ::= { enterprises 1537 }
merckAndCompany                   OBJECT IDENTIFIER ::= { enterprises 1538 }
geotelCommunicationsCorporation   OBJECT IDENTIFIER ::= { enterprises 1539 }
sunAlliance                       OBJECT IDENTIFIER ::= { enterprises 1540 }
agCommunicationSystems            OBJECT IDENTIFIER ::= { enterprises 1541 }
pivotalNetworking                 OBJECT IDENTIFIER ::= { enterprises 1542 }
tsiTelSys                         OBJECT IDENTIFIER ::= { enterprises 1543 }
harmonicSystems                   OBJECT IDENTIFIER ::= { enterprises 1544 }
astronetCorporation               OBJECT IDENTIFIER ::= { enterprises 1545 }
frontec                           OBJECT IDENTIFIER ::= { enterprises 1546 }
netvision                         OBJECT IDENTIFIER ::= { enterprises 1547 }
flowpointCorporation              OBJECT IDENTIFIER ::= { enterprises 1548 }
tronBVDatacommunication           OBJECT IDENTIFIER ::= { enterprises 1549 }
nueraCommunication                OBJECT IDENTIFIER ::= { enterprises 1550 }
radnet                            OBJECT IDENTIFIER ::= { enterprises 1551 }
oceNederlandBV                    OBJECT IDENTIFIER ::= { enterprises 1552 }
airFrance                         OBJECT IDENTIFIER ::= { enterprises 1553 }
communicationsAndPowerEngineering OBJECT IDENTIFIER ::= { enterprises 1554 }
charterSystems                    OBJECT IDENTIFIER ::= { enterprises 1555 }
performanceTechnologies           OBJECT IDENTIFIER ::= { enterprises 1556 }
paragonNetworksInternational      OBJECT IDENTIFIER ::= { enterprises 1557 }
skogDataAS                        OBJECT IDENTIFIER ::= { enterprises 1558 }
mitecAS                           OBJECT IDENTIFIER ::= { enterprises 1559 }
thomsonCSFDepartementReseauxD     OBJECT IDENTIFIER ::= { enterprises 1560 }
ipsilonNetworks                   OBJECT IDENTIFIER ::= { enterprises 1561 }
kingstonTechnologyCompany         OBJECT IDENTIFIER ::= { enterprises 1562 }
harmonicLightwaves                OBJECT IDENTIFIER ::= { enterprises 1563 }
interactiveDigitalSolutions       OBJECT IDENTIFIER ::= { enterprises 1564 }
coactiveAesthetics                OBJECT IDENTIFIER ::= { enterprises 1565 }
techDataCorporation               OBJECT IDENTIFIER ::= { enterprises 1566 }
zCom                              OBJECT IDENTIFIER ::= { enterprises 1567 }
cotep                             OBJECT IDENTIFIER ::= { enterprises 1568 }
raytheonCompany                   OBJECT IDENTIFIER ::= { enterprises 1569 }
telesend                          OBJECT IDENTIFIER ::= { enterprises 1570 }
ncc                               OBJECT IDENTIFIER ::= { enterprises 1571 }
forteSoftware                     OBJECT IDENTIFIER ::= { enterprises 1572 }
secureComputingCorporation        OBJECT IDENTIFIER ::= { enterprises 1573 }
bezeq                             OBJECT IDENTIFIER ::= { enterprises 1574 }
technicalUniversityOfBraunschweig OBJECT IDENTIFIER ::= { enterprises 1575 }
stac                              OBJECT IDENTIFIER ::= { enterprises 1576 }
starnetCommunications             OBJECT IDENTIFIER ::= { enterprises 1577 }
universidadeDoMinho               OBJECT IDENTIFIER ::= { enterprises 1578 }
departmentOfComputerScience       OBJECT IDENTIFIER ::= { enterprises 1579 }
tekramTechnology                  OBJECT IDENTIFIER ::= { enterprises 1580 }
ratp                              OBJECT IDENTIFIER ::= { enterprises 1581 }
rainbowDiamondLimited             OBJECT IDENTIFIER ::= { enterprises 1582 }
magellanCommunications            OBJECT IDENTIFIER ::= { enterprises 1583 }
bayNetworks                       OBJECT IDENTIFIER ::= { enterprises 1584 }
quantitativeDataSystems           OBJECT IDENTIFIER ::= { enterprises 1585 }
esysLimited                       OBJECT IDENTIFIER ::= { enterprises 1586 }
switchedNetworkTechnologies       OBJECT IDENTIFIER ::= { enterprises 1587 }
brocadeCommunicationsSystems      OBJECT IDENTIFIER ::= { enterprises 1588 }
computerResourcesInternationalAS  OBJECT IDENTIFIER ::= { enterprises 1589 }
luchtverkeersbeveiliging          OBJECT IDENTIFIER ::= { enterprises 1590 }
gtil                              OBJECT IDENTIFIER ::= { enterprises 1591 }
xactlabsCorporation               OBJECT IDENTIFIER ::= { enterprises 1592 }
netproComputing                   OBJECT IDENTIFIER ::= { enterprises 1593 }
telesync                          OBJECT IDENTIFIER ::= { enterprises 1594 }
boschTelecom                      OBJECT IDENTIFIER ::= { enterprises 1595 }
insGmbH                           OBJECT IDENTIFIER ::= { enterprises 1596 }
distributedProcessingTechnology   OBJECT IDENTIFIER ::= { enterprises 1597 }
tivoliSystems                     OBJECT IDENTIFIER ::= { enterprises 1598 }
networkManagementTechnologies     OBJECT IDENTIFIER ::= { enterprises 1599 }
sirti                             OBJECT IDENTIFIER ::= { enterprises 1600 }
taskeTechnology                   OBJECT IDENTIFIER ::= { enterprises 1601 }
canonINC                          OBJECT IDENTIFIER ::= { enterprises 1602 }
systemsAndSynchronous             OBJECT IDENTIFIER ::= { enterprises 1603 }
xferInternational                 OBJECT IDENTIFIER ::= { enterprises 1604 }
scandpowerAS                      OBJECT IDENTIFIER ::= { enterprises 1605 }
consultancyAndProjectsGroupSrl    OBJECT IDENTIFIER ::= { enterprises 1606 }
stsTechnologies                   OBJECT IDENTIFIER ::= { enterprises 1607 }
mylexCorporation                  OBJECT IDENTIFIER ::= { enterprises 1608 }
cryptocardCorporation             OBJECT IDENTIFIER ::= { enterprises 1609 }
lxe                               OBJECT IDENTIFIER ::= { enterprises 1610 }
bdmInternational                  OBJECT IDENTIFIER ::= { enterprises 1611 }
geSpacenetServices                OBJECT IDENTIFIER ::= { enterprises 1612 }
datanetGmbH                       OBJECT IDENTIFIER ::= { enterprises 1613 }
opcom                             OBJECT IDENTIFIER ::= { enterprises 1614 }
mlinkInternet                     OBJECT IDENTIFIER ::= { enterprises 1615 }
netroCorporation                  OBJECT IDENTIFIER ::= { enterprises 1616 }
netPartners                       OBJECT IDENTIFIER ::= { enterprises 1617 }
peekTrafficTransytCorp            OBJECT IDENTIFIER ::= { enterprises 1618 }
comverseInformationSystems        OBJECT IDENTIFIER ::= { enterprises 1619 }
dataCommForBusiness               OBJECT IDENTIFIER ::= { enterprises 1620 }
cybecPty                          OBJECT IDENTIFIER ::= { enterprises 1621 }
mitsuiKnowledgeIndustryCo         OBJECT IDENTIFIER ::= { enterprises 1622 }
nordxCDT                          OBJECT IDENTIFIER ::= { enterprises 1623 }
blockadeSystemsCorp               OBJECT IDENTIFIER ::= { enterprises 1624 }
nixuOy                            OBJECT IDENTIFIER ::= { enterprises 1625 }
australianSoftwareInnovations     OBJECT IDENTIFIER ::= { enterprises 1626 }
omicronTelesystems                OBJECT IDENTIFIER ::= { enterprises 1627 }
demonInternet                     OBJECT IDENTIFIER ::= { enterprises 1628 }
pbFarradyne                       OBJECT IDENTIFIER ::= { enterprises 1629 }
telosCorporationSharonSutherlin   OBJECT IDENTIFIER ::= { enterprises 1630 }
manageInformationTechnologies     OBJECT IDENTIFIER ::= { enterprises 1631 }
harlowButlerBrokingServices       OBJECT IDENTIFIER ::= { enterprises 1632 }
eurologicSystems                  OBJECT IDENTIFIER ::= { enterprises 1633 }
telcoResearchCorporation          OBJECT IDENTIFIER ::= { enterprises 1634 }
mercedesBenzAG                    OBJECT IDENTIFIER ::= { enterprises 1635 }
hobElectronicGmbH                 OBJECT IDENTIFIER ::= { enterprises 1636 }
noaa                              OBJECT IDENTIFIER ::= { enterprises 1637 }
cornerstoneSoftware               OBJECT IDENTIFIER ::= { enterprises 1638 }
winkCommunications                OBJECT IDENTIFIER ::= { enterprises 1639 }
thomsonElectronicInformationResources OBJECT IDENTIFIER ::= { enterprises 1640 }
hittHollandInstituteOfTrafficTechnologyBV OBJECT IDENTIFIER ::= { enterprises 1641 }
kpmg                              OBJECT IDENTIFIER ::= { enterprises 1642 }
loralFederalSystems               OBJECT IDENTIFIER ::= { enterprises 1643 }
siaSocietaInterbancariaPerL       OBJECT IDENTIFIER ::= { enterprises 1644 }
unitedStatesCellularCorp          OBJECT IDENTIFIER ::= { enterprises 1645 }
amperDATOSSA                      OBJECT IDENTIFIER ::= { enterprises 1646 }
carelcompForestOy                 OBJECT IDENTIFIER ::= { enterprises 1647 }
openEnvironmentAustralia          OBJECT IDENTIFIER ::= { enterprises 1648 }
integratedTelecomTechnology       OBJECT IDENTIFIER ::= { enterprises 1649 }
langnerGesellschaftFuerDatentechnikMbH OBJECT IDENTIFIER ::= { enterprises 1650 }
wayneStateUniversity              OBJECT IDENTIFIER ::= { enterprises 1651 }
sicc                              OBJECT IDENTIFIER ::= { enterprises 1652 }
thomsonCSF                        OBJECT IDENTIFIER ::= { enterprises 1653 }
teleconnectDresdenGmbH            OBJECT IDENTIFIER ::= { enterprises 1654 }
panoramaSoftware                  OBJECT IDENTIFIER ::= { enterprises 1655 }
compunetSystemhausGmbH            OBJECT IDENTIFIER ::= { enterprises 1656 }
japanTELECOMCO                    OBJECT IDENTIFIER ::= { enterprises 1657 }
techforceCorporation              OBJECT IDENTIFIER ::= { enterprises 1658 }
graniteSystems                    OBJECT IDENTIFIER ::= { enterprises 1659 }
bit                               OBJECT IDENTIFIER ::= { enterprises 1660 }
companhiaDeInformatica            OBJECT IDENTIFIER ::= { enterprises 1661 }
rockwellInternationalCorporation  OBJECT IDENTIFIER ::= { enterprises 1662 }
ancorCommunications               OBJECT IDENTIFIER ::= { enterprises 1663 }
royalInstituteOfTechnology        OBJECT IDENTIFIER ::= { enterprises 1664 }
sunet                             OBJECT IDENTIFIER ::= { enterprises 1665 }
sageInstruments                   OBJECT IDENTIFIER ::= { enterprises 1666 }
candleCorporation                 OBJECT IDENTIFIER ::= { enterprises 1667 }
csoGmbH                           OBJECT IDENTIFIER ::= { enterprises 1668 }
m3iSystems                        OBJECT IDENTIFIER ::= { enterprises 1669 }
credintrans                       OBJECT IDENTIFIER ::= { enterprises 1670 }
bitCommunications                 OBJECT IDENTIFIER ::= { enterprises 1671 }
pierceAndAssociates               OBJECT IDENTIFIER ::= { enterprises 1672 }
rtsWireless                       OBJECT IDENTIFIER ::= { enterprises 1673 }
ricElectronics                    OBJECT IDENTIFIER ::= { enterprises 1674 }
amocoCorporation                  OBJECT IDENTIFIER ::= { enterprises 1675 }
qualixGroup                       OBJECT IDENTIFIER ::= { enterprises 1676 }
saharaNetworks                    OBJECT IDENTIFIER ::= { enterprises 1677 }
hyundaiElectronicsIndustriesCo    OBJECT IDENTIFIER ::= { enterprises 1678 }
rich                              OBJECT IDENTIFIER ::= { enterprises 1679 }
amatiCommunicationsCorp           OBJECT IDENTIFIER ::= { enterprises 1680 }
phuRysTECH                        OBJECT IDENTIFIER ::= { enterprises 1681 }
dataLabs                          OBJECT IDENTIFIER ::= { enterprises 1682 }
occidentalPetroleumServices       OBJECT IDENTIFIER ::= { enterprises 1683 }
rijnhaaveInternetServices         OBJECT IDENTIFIER ::= { enterprises 1684 }
lynxRealTimeSystems               OBJECT IDENTIFIER ::= { enterprises 1685 }
pontisConsulting                  OBJECT IDENTIFIER ::= { enterprises 1686 }
softouchSystems                   OBJECT IDENTIFIER ::= { enterprises 1687 }
sondaSA                           OBJECT IDENTIFIER ::= { enterprises 1688 }
mccormickNunesCompany             OBJECT IDENTIFIER ::= { enterprises 1689 }
umeE5Universitet                  OBJECT IDENTIFIER ::= { enterprises 1690 }
netiqCorporation                  OBJECT IDENTIFIER ::= { enterprises 1691 }
starlightNetworks                 OBJECT IDENTIFIER ::= { enterprises 1692 }
informacionSelectivaSADeCV        OBJECT IDENTIFIER ::= { enterprises 1693 }
hclTechnologiesLimited            OBJECT IDENTIFIER ::= { enterprises 1694 }
maryvilleDataSystems              OBJECT IDENTIFIER ::= { enterprises 1695 }
ethercomCorp                      OBJECT IDENTIFIER ::= { enterprises 1696 }
multicomSoftware                  OBJECT IDENTIFIER ::= { enterprises 1697 }
beaSystems                        OBJECT IDENTIFIER ::= { enterprises 1698 }
advancedTechnology                OBJECT IDENTIFIER ::= { enterprises 1699 }
mobilOil                          OBJECT IDENTIFIER ::= { enterprises 1700 }
arenaConsultingLimited            OBJECT IDENTIFIER ::= { enterprises 1701 }
netsysInternational               OBJECT IDENTIFIER ::= { enterprises 1702 }
titanInformationSystemsCorp       OBJECT IDENTIFIER ::= { enterprises 1703 }
cogentDataTechnologies            OBJECT IDENTIFIER ::= { enterprises 1704 }
reliasoftCorporation              OBJECT IDENTIFIER ::= { enterprises 1705 }
midlandBusinessSystems            OBJECT IDENTIFIER ::= { enterprises 1706 }
optimalNetworks                   OBJECT IDENTIFIER ::= { enterprises 1707 }
greshamComputingPlc               OBJECT IDENTIFIER ::= { enterprises 1708 }
scienceApplicationsInternationalCorporation OBJECT IDENTIFIER ::= { enterprises 1709 }
acclaimCommunications             OBJECT IDENTIFIER ::= { enterprises 1710 }
bissLimited                       OBJECT IDENTIFIER ::= { enterprises 1711 }
caravelle                         OBJECT IDENTIFIER ::= { enterprises 1712 }
diamondLaneCommunicationsCorporation OBJECT IDENTIFIER ::= { enterprises 1713 }
infortrendTechnology              OBJECT IDENTIFIER ::= { enterprises 1714 }
ordaBNV                           OBJECT IDENTIFIER ::= { enterprises 1715 }
arielCorporation                  OBJECT IDENTIFIER ::= { enterprises 1716 }
datalexCommunications             OBJECT IDENTIFIER ::= { enterprises 1717 }
serverTechnology                  OBJECT IDENTIFIER ::= { enterprises 1718 }
unimaxSystemsCorporation          OBJECT IDENTIFIER ::= { enterprises 1719 }
detemobilGmbH                     OBJECT IDENTIFIER ::= { enterprises 1720 }
infonovaGmbH                      OBJECT IDENTIFIER ::= { enterprises 1721 }
kudelskiSA                        OBJECT IDENTIFIER ::= { enterprises 1722 }
pronetGmbH                        OBJECT IDENTIFIER ::= { enterprises 1723 }
westell                           OBJECT IDENTIFIER ::= { enterprises 1724 }
nuponComputing                    OBJECT IDENTIFIER ::= { enterprises 1725 }
cianetIndECom                     OBJECT IDENTIFIER ::= { enterprises 1726 }
aumtechOfVirginia                 OBJECT IDENTIFIER ::= { enterprises 1727 }
cheongjoDataCommunication         OBJECT IDENTIFIER ::= { enterprises 1728 }
genesysTelecommunicationsLaboratories OBJECT IDENTIFIER ::= { enterprises 1729 }
progressSoftware                  OBJECT IDENTIFIER ::= { enterprises 1730 }
ericssonFIBERACCESS               OBJECT IDENTIFIER ::= { enterprises 1731 }
openAccessPty                     OBJECT IDENTIFIER ::= { enterprises 1732 }
sterlingCommerce                  OBJECT IDENTIFIER ::= { enterprises 1733 }
predictiveSystems                 OBJECT IDENTIFIER ::= { enterprises 1734 }
architelSystemsCorporation        OBJECT IDENTIFIER ::= { enterprises 1735 }
usWestInterAct                    OBJECT IDENTIFIER ::= { enterprises 1736 }
eclipseTechnologies               OBJECT IDENTIFIER ::= { enterprises 1737 }
navy                              OBJECT IDENTIFIER ::= { enterprises 1738 }
bindiTechnologies                 OBJECT IDENTIFIER ::= { enterprises 1739 }
hallmarkCards                     OBJECT IDENTIFIER ::= { enterprises 1740 }
objectDesign                      OBJECT IDENTIFIER ::= { enterprises 1741 }
vsys                              OBJECT IDENTIFIER ::= { enterprises 1742 }
zenithDataSystems                 OBJECT IDENTIFIER ::= { enterprises 1743 }
gobiCorp                          OBJECT IDENTIFIER ::= { enterprises 1744 }
universitatDeBarcelona            OBJECT IDENTIFIER ::= { enterprises 1745 }
instituteForSimulationAndTraining OBJECT IDENTIFIER ::= { enterprises 1746 }
usAgencyForInternationalDevelopment OBJECT IDENTIFIER ::= { enterprises 1747 }
tutSystems                        OBJECT IDENTIFIER ::= { enterprises 1748 }
answerzPty                        OBJECT IDENTIFIER ::= { enterprises 1749 }
hbollmannManufacturers            OBJECT IDENTIFIER ::= { enterprises 1750 }
lucentTechnologies                OBJECT IDENTIFIER ::= { enterprises 1751 }
phase2Networks                    OBJECT IDENTIFIER ::= { enterprises 1752 }
unifyCorporation                  OBJECT IDENTIFIER ::= { enterprises 1753 }
gadzooxMicrosystems               OBJECT IDENTIFIER ::= { enterprises 1754 }
networkOne                        OBJECT IDENTIFIER ::= { enterprises 1755 }
mulogicBv                         OBJECT IDENTIFIER ::= { enterprises 1756 }
opticalMicrowaveNetworks          OBJECT IDENTIFIER ::= { enterprises 1757 }
sitel                             OBJECT IDENTIFIER ::= { enterprises 1758 }
cergFinance                       OBJECT IDENTIFIER ::= { enterprises 1759 }
americanInternetCorporation       OBJECT IDENTIFIER ::= { enterprises 1760 }
pluskomGmbH                       OBJECT IDENTIFIER ::= { enterprises 1761 }
deptOfCommunications              OBJECT IDENTIFIER ::= { enterprises 1762 }
mindspringEnterprises             OBJECT IDENTIFIER ::= { enterprises 1763 }
dbTech                            OBJECT IDENTIFIER ::= { enterprises 1764 }
apexVoiceCommunications           OBJECT IDENTIFIER ::= { enterprises 1765 }
nationalDataCommCorporation       OBJECT IDENTIFIER ::= { enterprises 1766 }
telenorConaxAS                    OBJECT IDENTIFIER ::= { enterprises 1767 }
pattonElectronicsCompany          OBJECT IDENTIFIER ::= { enterprises 1768 }
theFulgentGroup                   OBJECT IDENTIFIER ::= { enterprises 1769 }
broadbandTechnologies             OBJECT IDENTIFIER ::= { enterprises 1770 }
myricom                           OBJECT IDENTIFIER ::= { enterprises 1771 }
decisionone                       OBJECT IDENTIFIER ::= { enterprises 1772 }
tandbergTelevision                OBJECT IDENTIFIER ::= { enterprises 1773 }
auditecSA                         OBJECT IDENTIFIER ::= { enterprises 1774 }
pcMagic                           OBJECT IDENTIFIER ::= { enterprises 1775 }
philipsElectronicsNV              OBJECT IDENTIFIER ::= { enterprises 1776 }
origin                            OBJECT IDENTIFIER ::= { enterprises 1777 }
csgSystems                        OBJECT IDENTIFIER ::= { enterprises 1778 }
alphamericTechnologies            OBJECT IDENTIFIER ::= { enterprises 1779 }
ncrAustriaMichaelOstendorf        OBJECT IDENTIFIER ::= { enterprises 1780 }
chuckk                            OBJECT IDENTIFIER ::= { enterprises 1781 }
powertv                           OBJECT IDENTIFIER ::= { enterprises 1782 }
activeSoftware                    OBJECT IDENTIFIER ::= { enterprises 1783 }
enronCapitolAndTradeResources     OBJECT IDENTIFIER ::= { enterprises 1784 }
orbcomm                           OBJECT IDENTIFIER ::= { enterprises 1785 }
jwDirectShop                      OBJECT IDENTIFIER ::= { enterprises 1786 }
beta                              OBJECT IDENTIFIER ::= { enterprises 1787 }
healtheon                         OBJECT IDENTIFIER ::= { enterprises 1788 }
integralis                        OBJECT IDENTIFIER ::= { enterprises 1789 }
folioCorporation                  OBJECT IDENTIFIER ::= { enterprises 1790 }
ectf                              OBJECT IDENTIFIER ::= { enterprises 1791 }
webplanet                         OBJECT IDENTIFIER ::= { enterprises 1792 }
nstorCorporation                  OBJECT IDENTIFIER ::= { enterprises 1793 }
deutscheBahnAG                    OBJECT IDENTIFIER ::= { enterprises 1794 }
paradyne                          OBJECT IDENTIFIER ::= { enterprises 1795 }
nastelTechnologies                OBJECT IDENTIFIER ::= { enterprises 1796 }
metaphaseTechnology               OBJECT IDENTIFIER ::= { enterprises 1797 }
zweigartAndSawitzki               OBJECT IDENTIFIER ::= { enterprises 1798 }
pixel                             OBJECT IDENTIFIER ::= { enterprises 1799 }
waveaccess                        OBJECT IDENTIFIER ::= { enterprises 1800 }
theSABREGroup                     OBJECT IDENTIFIER ::= { enterprises 1801 }
redlandTechnologyCorp             OBJECT IDENTIFIER ::= { enterprises 1802 }
pbs                               OBJECT IDENTIFIER ::= { enterprises 1803 }
consensusDevelopmentCorporation   OBJECT IDENTIFIER ::= { enterprises 1804 }
sagemSA                           OBJECT IDENTIFIER ::= { enterprises 1805 }
iCube                             OBJECT IDENTIFIER ::= { enterprises 1806 }
--                                OBJECT IDENTIFIER ::= { enterprises 1807 }
aetna                             OBJECT IDENTIFIER ::= { enterprises 1808 }
dowJonesMarkets                   OBJECT IDENTIFIER ::= { enterprises 1809 }
czechRailwaysSoCIT                OBJECT IDENTIFIER ::= { enterprises 1810 }
scanMaticAS                       OBJECT IDENTIFIER ::= { enterprises 1811 }
decisionEurope                    OBJECT IDENTIFIER ::= { enterprises 1812 }
vtelCorporation                   OBJECT IDENTIFIER ::= { enterprises 1813 }
bloomberg                         OBJECT IDENTIFIER ::= { enterprises 1814 }
eyretel                           OBJECT IDENTIFIER ::= { enterprises 1815 }
roseHulmanInstituteOfTechnology   OBJECT IDENTIFIER ::= { enterprises 1816 }
aetherTechnologies                OBJECT IDENTIFIER ::= { enterprises 1817 }
infonetSoftwareSolutions          OBJECT IDENTIFIER ::= { enterprises 1818 }
csti                              OBJECT IDENTIFIER ::= { enterprises 1819 }
leroyMERLIN                       OBJECT IDENTIFIER ::= { enterprises 1820 }
totalEntertainmentNetwork         OBJECT IDENTIFIER ::= { enterprises 1821 }
openPortTechnology                OBJECT IDENTIFIER ::= { enterprises 1822 }
mikroelektronikAnwendungszentrumHamburgGmbH OBJECT IDENTIFIER ::= { enterprises 1823 }
internationalManagementConsulting OBJECT IDENTIFIER ::= { enterprises 1824 }
foreSystems                       OBJECT IDENTIFIER ::= { enterprises 1825 }
mtechSystemsTimothyJMadden        OBJECT IDENTIFIER ::= { enterprises 1826 }
rxsoft                            OBJECT IDENTIFIER ::= { enterprises 1827 }
deptComputerStudies               OBJECT IDENTIFIER ::= { enterprises 1828 }
beta80SpA                         OBJECT IDENTIFIER ::= { enterprises 1829 }
galiso                            OBJECT IDENTIFIER ::= { enterprises 1830 }
s2Systems                         OBJECT IDENTIFIER ::= { enterprises 1831 }
optivision                        OBJECT IDENTIFIER ::= { enterprises 1832 }
countrywideHomeLoans              OBJECT IDENTIFIER ::= { enterprises 1833 }
oaLaboratoryCo                    OBJECT IDENTIFIER ::= { enterprises 1834 }
sdxBusinessSystems                OBJECT IDENTIFIER ::= { enterprises 1835 }
westEndSystemsCorp                OBJECT IDENTIFIER ::= { enterprises 1836 }
dkDigitalMedia                    OBJECT IDENTIFIER ::= { enterprises 1837 }
westel                            OBJECT IDENTIFIER ::= { enterprises 1838 }
fujitsuTelecommuncationsEurope    OBJECT IDENTIFIER ::= { enterprises 1839 }
inmarsat                          OBJECT IDENTIFIER ::= { enterprises 1840 }
timsTechnology                    OBJECT IDENTIFIER ::= { enterprises 1841 }
callwareTechnologies              OBJECT IDENTIFIER ::= { enterprises 1842 }
nextlink                          OBJECT IDENTIFIER ::= { enterprises 1843 }
turnquaySolutionsLimited          OBJECT IDENTIFIER ::= { enterprises 1844 }
accusortSystems                   OBJECT IDENTIFIER ::= { enterprises 1845 }
deutscherBUNDESTAG                OBJECT IDENTIFIER ::= { enterprises 1846 }
jointResearchCentre               OBJECT IDENTIFIER ::= { enterprises 1847 }
faxsav                            OBJECT IDENTIFIER ::= { enterprises 1848 }
chevyChaseApplicationsDesign      OBJECT IDENTIFIER ::= { enterprises 1849 }
bankBrusselLambert                OBJECT IDENTIFIER ::= { enterprises 1850 }
outbackResourceGroup              OBJECT IDENTIFIER ::= { enterprises 1851 }
screenSubtitlingSystems           OBJECT IDENTIFIER ::= { enterprises 1852 }
cambridgeParallelProcessing       OBJECT IDENTIFIER ::= { enterprises 1853 }
bostonUniversity                  OBJECT IDENTIFIER ::= { enterprises 1854 }
newsDigitalSystems                OBJECT IDENTIFIER ::= { enterprises 1855 }
nutek2000                         OBJECT IDENTIFIER ::= { enterprises 1856 }
overlandMobileCommunicationAB     OBJECT IDENTIFIER ::= { enterprises 1857 }
axonITAB                          OBJECT IDENTIFIER ::= { enterprises 1858 }
gradientMedicalSystems            OBJECT IDENTIFIER ::= { enterprises 1859 }
wavespanCorporation               OBJECT IDENTIFIER ::= { enterprises 1860 }
netResearch                       OBJECT IDENTIFIER ::= { enterprises 1861 }
browncroftCommunityChurch         OBJECT IDENTIFIER ::= { enterprises 1862 }
net2netCorporation                OBJECT IDENTIFIER ::= { enterprises 1863 }
usInternet                        OBJECT IDENTIFIER ::= { enterprises 1864 }
absoluteTime                      OBJECT IDENTIFIER ::= { enterprises 1865 }
vpnet                             OBJECT IDENTIFIER ::= { enterprises 1866 }
ntech                             OBJECT IDENTIFIER ::= { enterprises 1867 }
nipponUnisoftCorporation          OBJECT IDENTIFIER ::= { enterprises 1868 }
opticalTransmissionLabs           OBJECT IDENTIFIER ::= { enterprises 1869 }
cybercash                         OBJECT IDENTIFIER ::= { enterprises 1870 }
netspeed                          OBJECT IDENTIFIER ::= { enterprises 1871 }
alteonNetworks                    OBJECT IDENTIFIER ::= { enterprises 1872 }
internetMiddlewareCorporation     OBJECT IDENTIFIER ::= { enterprises 1873 }
isonovaGmbH                       OBJECT IDENTIFIER ::= { enterprises 1874 }
amigaIOPSProject                  OBJECT IDENTIFIER ::= { enterprises 1875 }
softbankServicesGroup             OBJECT IDENTIFIER ::= { enterprises 1876 }
sourcecomCorporation              OBJECT IDENTIFIER ::= { enterprises 1877 }
teliaPromotorAB                   OBJECT IDENTIFIER ::= { enterprises 1878 }
heliossCommunications             OBJECT IDENTIFIER ::= { enterprises 1879 }
opticalAccessInternational        OBJECT IDENTIFIER ::= { enterprises 1880 }
mmcNetworks                       OBJECT IDENTIFIER ::= { enterprises 1881 }
lanyon                            OBJECT IDENTIFIER ::= { enterprises 1882 }
rubico                            OBJECT IDENTIFIER ::= { enterprises 1883 }
quantumTelecomSolutions           OBJECT IDENTIFIER ::= { enterprises 1884 }
archinet                          OBJECT IDENTIFIER ::= { enterprises 1885 }
iCubed                            OBJECT IDENTIFIER ::= { enterprises 1886 }
siemensSwitzerland                OBJECT IDENTIFIER ::= { enterprises 1887 }
gigalabs                          OBJECT IDENTIFIER ::= { enterprises 1888 }
metMatraEricsson                  OBJECT IDENTIFIER ::= { enterprises 1889 }
jbmElectronics                    OBJECT IDENTIFIER ::= { enterprises 1890 }
optimSystems                      OBJECT IDENTIFIER ::= { enterprises 1891 }
softwareBrewery                   OBJECT IDENTIFIER ::= { enterprises 1892 }
wavelinq                          OBJECT IDENTIFIER ::= { enterprises 1893 }
siemensICN                        OBJECT IDENTIFIER ::= { enterprises 1894 }
iexCorporation                    OBJECT IDENTIFIER ::= { enterprises 1895 }
truetime                          OBJECT IDENTIFIER ::= { enterprises 1896 }
htCommunications                  OBJECT IDENTIFIER ::= { enterprises 1897 }
avantcompOy                       OBJECT IDENTIFIER ::= { enterprises 1898 }
infovista                         OBJECT IDENTIFIER ::= { enterprises 1899 }
phonecom                          OBJECT IDENTIFIER ::= { enterprises 1900 }
seaWonders                        OBJECT IDENTIFIER ::= { enterprises 1901 }
headstartEnterprise               OBJECT IDENTIFIER ::= { enterprises 1902 }
bSMART                            OBJECT IDENTIFIER ::= { enterprises 1903 }
isma                              OBJECT IDENTIFIER ::= { enterprises 1904 }
threeDVTechnology                 OBJECT IDENTIFIER ::= { enterprises 1905 }
starcomTechnologies               OBJECT IDENTIFIER ::= { enterprises 1906 }
llbean                            OBJECT IDENTIFIER ::= { enterprises 1907 }
netics                            OBJECT IDENTIFIER ::= { enterprises 1908 }
infratecPlusGmbH                  OBJECT IDENTIFIER ::= { enterprises 1909 }
the3eGroup                        OBJECT IDENTIFIER ::= { enterprises 1910 }
giseMbH                           OBJECT IDENTIFIER ::= { enterprises 1911 }
lanAndPcServices                  OBJECT IDENTIFIER ::= { enterprises 1912 }
redpointSoftwareCorporation       OBJECT IDENTIFIER ::= { enterprises 1913 }
quadratec                         OBJECT IDENTIFIER ::= { enterprises 1914 }
i95CC                             OBJECT IDENTIFIER ::= { enterprises 1915 }
extremeNetworks                   OBJECT IDENTIFIER ::= { enterprises 1916 }
villageOfRockvilleCentre          OBJECT IDENTIFIER ::= { enterprises 1917 }
swichtecPowerSystems              OBJECT IDENTIFIER ::= { enterprises 1918 }
deutscherWetterdienst             OBJECT IDENTIFIER ::= { enterprises 1919 }
bluebirdSoftware                  OBJECT IDENTIFIER ::= { enterprises 1920 }
svahaInteractiveMedia             OBJECT IDENTIFIER ::= { enterprises 1921 }
sullySolutions                    OBJECT IDENTIFIER ::= { enterprises 1922 }
blueLine                          OBJECT IDENTIFIER ::= { enterprises 1923 }
castletonNetworkSystems           OBJECT IDENTIFIER ::= { enterprises 1924 }
visualEdgeSoftware                OBJECT IDENTIFIER ::= { enterprises 1925 }
netguardTechnologies              OBJECT IDENTIFIER ::= { enterprises 1926 }
softsell                          OBJECT IDENTIFIER ::= { enterprises 1927 }
marneSOFTWARE                     OBJECT IDENTIFIER ::= { enterprises 1928 }
cadiaNetworks                     OBJECT IDENTIFIER ::= { enterprises 1929 }
milton                            OBJECT IDENTIFIER ::= { enterprises 1930 }
delMarSolutions                   OBJECT IDENTIFIER ::= { enterprises 1931 }
kumaranSYSTEMS                    OBJECT IDENTIFIER ::= { enterprises 1932 }
equivalence                       OBJECT IDENTIFIER ::= { enterprises 1933 }
homewatchInternational            OBJECT IDENTIFIER ::= { enterprises 1934 }
johnRivers                        OBJECT IDENTIFIER ::= { enterprises 1935 }
remarkServices                    OBJECT IDENTIFIER ::= { enterprises 1936 }
deloitteAndToucheConsultingGroup  OBJECT IDENTIFIER ::= { enterprises 1937 }
flyingPenguinProductions          OBJECT IDENTIFIER ::= { enterprises 1938 }
theMatrix                         OBJECT IDENTIFIER ::= { enterprises 1939 }
easternComputers                  OBJECT IDENTIFIER ::= { enterprises 1940 }
princetonBioMedica                OBJECT IDENTIFIER ::= { enterprises 1941 }
sancomTechnology                  OBJECT IDENTIFIER ::= { enterprises 1942 }
nationalComputingCentre           OBJECT IDENTIFIER ::= { enterprises 1943 }
avalCommunications                OBJECT IDENTIFIER ::= { enterprises 1944 }
wortecSearchNetCO                 OBJECT IDENTIFIER ::= { enterprises 1945 }
dogwoodMedia                      OBJECT IDENTIFIER ::= { enterprises 1946 }
alliedDomecq                      OBJECT IDENTIFIER ::= { enterprises 1947 }
telesoftRussia                    OBJECT IDENTIFIER ::= { enterprises 1948 }
utstarcom                         OBJECT IDENTIFIER ::= { enterprises 1949 }
comunit                           OBJECT IDENTIFIER ::= { enterprises 1950 }
trafficSofware                    OBJECT IDENTIFIER ::= { enterprises 1951 }
qualopSystemsCorp                 OBJECT IDENTIFIER ::= { enterprises 1952 }
vincaCorporation                  OBJECT IDENTIFIER ::= { enterprises 1953 }
amtecSpa                          OBJECT IDENTIFIER ::= { enterprises 1954 }
gretacoderDataSystemsAG           OBJECT IDENTIFIER ::= { enterprises 1955 }
kmsystems                         OBJECT IDENTIFIER ::= { enterprises 1956 }
geva                              OBJECT IDENTIFIER ::= { enterprises 1957 }
redCreekCommunications            OBJECT IDENTIFIER ::= { enterprises 1958 }
borgTechnology                    OBJECT IDENTIFIER ::= { enterprises 1959 }
concordElectronics                OBJECT IDENTIFIER ::= { enterprises 1960 }
richardRicciDDS                   OBJECT IDENTIFIER ::= { enterprises 1961 }
linkInternationalCorp             OBJECT IDENTIFIER ::= { enterprises 1962 }
intermecCorp                      OBJECT IDENTIFIER ::= { enterprises 1963 }
optimumDataAG                     OBJECT IDENTIFIER ::= { enterprises 1964 }
dmcnw                             OBJECT IDENTIFIER ::= { enterprises 1965 }
perleSystemsLimited               OBJECT IDENTIFIER ::= { enterprises 1966 }
inktomiCorporation                OBJECT IDENTIFIER ::= { enterprises 1967 }
teleTVSystems                     OBJECT IDENTIFIER ::= { enterprises 1968 }
fritzHaberInstitut                OBJECT IDENTIFIER ::= { enterprises 1969 }
mediaonenet                       OBJECT IDENTIFIER ::= { enterprises 1970 }
seachangeInternational            OBJECT IDENTIFIER ::= { enterprises 1971 }
castonCorporation                 OBJECT IDENTIFIER ::= { enterprises 1972 }
localNet                          OBJECT IDENTIFIER ::= { enterprises 1973 }
japannet                          OBJECT IDENTIFIER ::= { enterprises 1974 }
nabisco                           OBJECT IDENTIFIER ::= { enterprises 1975 }
micrologicaGmbH                   OBJECT IDENTIFIER ::= { enterprises 1976 }
networkHarmoni                    OBJECT IDENTIFIER ::= { enterprises 1977 }
northropGrummanCanada             OBJECT IDENTIFIER ::= { enterprises 1978 }
globalMAINTECH                    OBJECT IDENTIFIER ::= { enterprises 1979 }
tele2AB                           OBJECT IDENTIFIER ::= { enterprises 1980 }
clariionAdvancedStorageSolutions  OBJECT IDENTIFIER ::= { enterprises 1981 }
itsCorporation                    OBJECT IDENTIFIER ::= { enterprises 1982 }
cleversoft                        OBJECT IDENTIFIER ::= { enterprises 1983 }
thePerseusGroup                   OBJECT IDENTIFIER ::= { enterprises 1984 }
joe                               OBJECT IDENTIFIER ::= { enterprises 1985 }
everythingInternetStore           OBJECT IDENTIFIER ::= { enterprises 1986 }
lanology                          OBJECT IDENTIFIER ::= { enterprises 1987 }
lycomingCountyPA                  OBJECT IDENTIFIER ::= { enterprises 1988 }
statensInstitutionsStyrelseSiS    OBJECT IDENTIFIER ::= { enterprises 1989 }
inwareSolutions                   OBJECT IDENTIFIER ::= { enterprises 1990 }
foundryNetworks                   OBJECT IDENTIFIER ::= { enterprises 1991 }
deutscheBank                      OBJECT IDENTIFIER ::= { enterprises 1992 }
xyratex                           OBJECT IDENTIFIER ::= { enterprises 1993 }
bauschDatacomBV                   OBJECT IDENTIFIER ::= { enterprises 1994 }
advancedRadioTelecom              OBJECT IDENTIFIER ::= { enterprises 1995 }
copperMountainCommunications      OBJECT IDENTIFIER ::= { enterprises 1996 }
planetSoftware                    OBJECT IDENTIFIER ::= { enterprises 1997 }
carltanComputerCorporation        OBJECT IDENTIFIER ::= { enterprises 1998 }
littvaMitchell                    OBJECT IDENTIFIER ::= { enterprises 1999 }
tibco                             OBJECT IDENTIFIER ::= { enterprises 2000 }
okiDataCorporation                OBJECT IDENTIFIER ::= { enterprises 2001 }
gotel                             OBJECT IDENTIFIER ::= { enterprises 2002 }
adobeSystems                      OBJECT IDENTIFIER ::= { enterprises 2003 }
sentricity                        OBJECT IDENTIFIER ::= { enterprises 2004 }
aeroportsDeParis                  OBJECT IDENTIFIER ::= { enterprises 2005 }
econz                             OBJECT IDENTIFIER ::= { enterprises 2006 }
teldat                            OBJECT IDENTIFIER ::= { enterprises 2007 }
offsetInfoServiceSrl              OBJECT IDENTIFIER ::= { enterprises 2008 }
aJBoggsAndCompany                 OBJECT IDENTIFIER ::= { enterprises 2009 }
staleOdegaardAS                   OBJECT IDENTIFIER ::= { enterprises 2010 }
huaweiTechnologyCo                OBJECT IDENTIFIER ::= { enterprises 2011 }
schroffGmbH                       OBJECT IDENTIFIER ::= { enterprises 2012 }
rehabilitationInstituteOfChicago  OBJECT IDENTIFIER ::= { enterprises 2013 }
adcTelecommunications             OBJECT IDENTIFIER ::= { enterprises 2014 }
systorAG                          OBJECT IDENTIFIER ::= { enterprises 2015 }
graiymage                         OBJECT IDENTIFIER ::= { enterprises 2016 }
symicronComputerCommunications    OBJECT IDENTIFIER ::= { enterprises 2017 }
scandoramaAB                      OBJECT IDENTIFIER ::= { enterprises 2018 }
iNET                              OBJECT IDENTIFIER ::= { enterprises 2019 }
xland                             OBJECT IDENTIFIER ::= { enterprises 2020 }
ucDavis                           OBJECT IDENTIFIER ::= { enterprises 2021 }
canaryCOMMUNICATIONS              OBJECT IDENTIFIER ::= { enterprises 2022 }
netgain                           OBJECT IDENTIFIER ::= { enterprises 2023 }
westInformationPublishingGroup    OBJECT IDENTIFIER ::= { enterprises 2024 }
deutscheBundesbank                OBJECT IDENTIFIER ::= { enterprises 2025 }
broadxent                         OBJECT IDENTIFIER ::= { enterprises 2026 }
gaussGmbH                         OBJECT IDENTIFIER ::= { enterprises 2027 }
aldiscon                          OBJECT IDENTIFIER ::= { enterprises 2028 }
vividImage                        OBJECT IDENTIFIER ::= { enterprises 2029 }
afriqAccess                       OBJECT IDENTIFIER ::= { enterprises 2030 }
reliantNetworksCorporation	  OBJECT IDENTIFIER ::= { enterprises 2031 }
semaGroupTelecoms                 OBJECT IDENTIFIER ::= { enterprises 2032 }
mckinneyLightingAndSound          OBJECT IDENTIFIER ::= { enterprises 2033 }
wholeSystemsDesign                OBJECT IDENTIFIER ::= { enterprises 2034 }
--                                OBJECT IDENTIFIER ::= { enterprises 2035 }
atlProducts                       OBJECT IDENTIFIER ::= { enterprises 2036 }
ernstAndYoungLLP                  OBJECT IDENTIFIER ::= { enterprises 2037 }
telewareOy                        OBJECT IDENTIFIER ::= { enterprises 2038 }
fiduciaInformationszentraleAG     OBJECT IDENTIFIER ::= { enterprises 2039 }
kinetics                          OBJECT IDENTIFIER ::= { enterprises 2040 }
emceeBroadcastProducts            OBJECT IDENTIFIER ::= { enterprises 2041 }
clariantCorporation               OBJECT IDENTIFIER ::= { enterprises 2042 }
ieee8025                          OBJECT IDENTIFIER ::= { enterprises 2043 }
openDevelopmentCorporation        OBJECT IDENTIFIER ::= { enterprises 2044 }
rfgSystems                        OBJECT IDENTIFIER ::= { enterprises 2045 }
aspectTelecommunications          OBJECT IDENTIFIER ::= { enterprises 2046 }
leoAndAssociates                  OBJECT IDENTIFIER ::= { enterprises 2047 }
softlinx                          OBJECT IDENTIFIER ::= { enterprises 2048 }
generaleBank                      OBJECT IDENTIFIER ::= { enterprises 2049 }
windwardTechnologies              OBJECT IDENTIFIER ::= { enterprises 2050 }
netsolve                          OBJECT IDENTIFIER ::= { enterprises 2051 }
xantel                            OBJECT IDENTIFIER ::= { enterprises 2052 }
arago                             OBJECT IDENTIFIER ::= { enterprises 2053 }
kokusaiDenshinDenwaCo             OBJECT IDENTIFIER ::= { enterprises 2054 }
gillamSATEL                       OBJECT IDENTIFIER ::= { enterprises 2055 }
moebiusSYSTEMS                    OBJECT IDENTIFIER ::= { enterprises 2056 }
financialInternetTechnology       OBJECT IDENTIFIER ::= { enterprises 2057 }
marcSystems                       OBJECT IDENTIFIER ::= { enterprises 2058 }
bovaGallery                       OBJECT IDENTIFIER ::= { enterprises 2059 }
osxTelecomunicacoes               OBJECT IDENTIFIER ::= { enterprises 2060 }
telecomSolutions                  OBJECT IDENTIFIER ::= { enterprises 2061 }
cyberiqSystems                    OBJECT IDENTIFIER ::= { enterprises 2062 }
ardentCommunicationsCorporation   OBJECT IDENTIFIER ::= { enterprises 2063 }
aware                             OBJECT IDENTIFIER ::= { enterprises 2064 }
racalRadioLimited                 OBJECT IDENTIFIER ::= { enterprises 2065 }
controlResourcesCorporation       OBJECT IDENTIFIER ::= { enterprises 2066 }
advancedFibreCommunications       OBJECT IDENTIFIER ::= { enterprises 2067 }
elpromaElectronicaBV              OBJECT IDENTIFIER ::= { enterprises 2068 }
mtaSZTAKI                         OBJECT IDENTIFIER ::= { enterprises 2069 }
consensysComputers                OBJECT IDENTIFIER ::= { enterprises 2070 }
jadeDigitalResearchCo             OBJECT IDENTIFIER ::= { enterprises 2071 }
byteThisInteractivePty            OBJECT IDENTIFIER ::= { enterprises 2072 }
financialNetworkTechnologies      OBJECT IDENTIFIER ::= { enterprises 2073 }
brokatInformationssystemeGmbH     OBJECT IDENTIFIER ::= { enterprises 2074 }
mediawiseNetworks                 OBJECT IDENTIFIER ::= { enterprises 2075 }
futureSoftware                    OBJECT IDENTIFIER ::= { enterprises 2076 }
commitInformationSystems          OBJECT IDENTIFIER ::= { enterprises 2077 }
virtualAccess                     OBJECT IDENTIFIER ::= { enterprises 2078 }
jdsFITEL                          OBJECT IDENTIFIER ::= { enterprises 2079 }
ipmDATACOM                        OBJECT IDENTIFIER ::= { enterprises 2080 }
starburstCommunications           OBJECT IDENTIFIER ::= { enterprises 2081 }
tollgradeCommunications           OBJECT IDENTIFIER ::= { enterprises 2082 }
wildfireCommunications            OBJECT IDENTIFIER ::= { enterprises 2083 }
sankenElectricCo                  OBJECT IDENTIFIER ::= { enterprises 2084 }
isolationSystemsLimited           OBJECT IDENTIFIER ::= { enterprises 2085 }
avidiaSystems                     OBJECT IDENTIFIER ::= { enterprises 2086 }
wavephoreNetworks                 OBJECT IDENTIFIER ::= { enterprises 2087 }
radstoneTechnologyPlc             OBJECT IDENTIFIER ::= { enterprises 2088 }
philipsBusinessCommunications     OBJECT IDENTIFIER ::= { enterprises 2089 }
fmsServices                       OBJECT IDENTIFIER ::= { enterprises 2090 }
supernovaCommunications           OBJECT IDENTIFIER ::= { enterprises 2091 }
murphyAndMurphyRealEstate         OBJECT IDENTIFIER ::= { enterprises 2092 }
multiPlatformInformationSystems   OBJECT IDENTIFIER ::= { enterprises 2093 }
allegroConsultants                OBJECT IDENTIFIER ::= { enterprises 2094 }
aiab                              OBJECT IDENTIFIER ::= { enterprises 2095 }
previewMultimediaServices         OBJECT IDENTIFIER ::= { enterprises 2096 }
accessBeyond                      OBJECT IDENTIFIER ::= { enterprises 2097 }
sunburstTechnology                OBJECT IDENTIFIER ::= { enterprises 2098 }
sotas                             OBJECT IDENTIFIER ::= { enterprises 2099 }
cybersoulsEternalLifeSystems      OBJECT IDENTIFIER ::= { enterprises 2100 }
hanwhaCORPTELECOM                 OBJECT IDENTIFIER ::= { enterprises 2101 }
cometTELECOMMUNICATIONSINC        OBJECT IDENTIFIER ::= { enterprises 2102 }
carySYSTEMS                       OBJECT IDENTIFIER ::= { enterprises 2103 }
peerlessSystemsCorp               OBJECT IDENTIFIER ::= { enterprises 2104 }
adicomWireless                    OBJECT IDENTIFIER ::= { enterprises 2105 }
highTechnologySoftwareCorp        OBJECT IDENTIFIER ::= { enterprises 2106 }
lynk                              OBJECT IDENTIFIER ::= { enterprises 2107 }
robin                             OBJECT IDENTIFIER ::= { enterprises 2108 }
secantNetworkTech                 OBJECT IDENTIFIER ::= { enterprises 2109 }
orionPicturesCorporation          OBJECT IDENTIFIER ::= { enterprises 2110 }
globalVillageCommunication        OBJECT IDENTIFIER ::= { enterprises 2111 }
iowave                            OBJECT IDENTIFIER ::= { enterprises 2112 }
signalsAndSemaphores              OBJECT IDENTIFIER ::= { enterprises 2113 }
mayoFoundation                    OBJECT IDENTIFIER ::= { enterprises 2114 }
kroneAG                           OBJECT IDENTIFIER ::= { enterprises 2115 }
computerNetworkingResources       OBJECT IDENTIFIER ::= { enterprises 2116 }
telenetworks                      OBJECT IDENTIFIER ::= { enterprises 2117 }
staffordshireUniversity           OBJECT IDENTIFIER ::= { enterprises 2118 }
broadbandNetworks                 OBJECT IDENTIFIER ::= { enterprises 2119 }
federalAviationAdministration     OBJECT IDENTIFIER ::= { enterprises 2120 }
technicalCommunications           OBJECT IDENTIFIER ::= { enterprises 2121 }
rezo                              OBJECT IDENTIFIER ::= { enterprises 2122 }
grafxlab                          OBJECT IDENTIFIER ::= { enterprises 2123 }
savantCorp                        OBJECT IDENTIFIER ::= { enterprises 2124 }
comtecSYSTEMSCO                   OBJECT IDENTIFIER ::= { enterprises 2125 }
satcomMedia                       OBJECT IDENTIFIER ::= { enterprises 2126 }
uconxCorporation                  OBJECT IDENTIFIER ::= { enterprises 2127 }
tpgNetwork                        OBJECT IDENTIFIER ::= { enterprises 2128 }
cnj                               OBJECT IDENTIFIER ::= { enterprises 2129 }
greenbrierAndRussel               OBJECT IDENTIFIER ::= { enterprises 2130 }
mainnet                           OBJECT IDENTIFIER ::= { enterprises 2131 }
comnetDatensysteme                OBJECT IDENTIFIER ::= { enterprises 2132 }
novadigm                          OBJECT IDENTIFIER ::= { enterprises 2133 }
alfatech                          OBJECT IDENTIFIER ::= { enterprises 2134 }
financialSciencesCorporation      OBJECT IDENTIFIER ::= { enterprises 2135 }
electronicsForImaging             OBJECT IDENTIFIER ::= { enterprises 2136 }
casabyte                          OBJECT IDENTIFIER ::= { enterprises 2137 }
assurenetPathways                 OBJECT IDENTIFIER ::= { enterprises 2138 }
alexanderLAN                      OBJECT IDENTIFIER ::= { enterprises 2139 }
gillSimpson                       OBJECT IDENTIFIER ::= { enterprises 2140 }
mcns                              OBJECT IDENTIFIER ::= { enterprises 2141 }
futureSystems                     OBJECT IDENTIFIER ::= { enterprises 2142 }
imgis                             OBJECT IDENTIFIER ::= { enterprises 2143 }
skywireCorporation                OBJECT IDENTIFIER ::= { enterprises 2144 }
irdetoConsultantsBV               OBJECT IDENTIFIER ::= { enterprises 2145 }
peasantworks                      OBJECT IDENTIFIER ::= { enterprises 2146 }
onionPeelSoftware                 OBJECT IDENTIFIER ::= { enterprises 2147 }
psPartnership                     OBJECT IDENTIFIER ::= { enterprises 2148 }
irdg                              OBJECT IDENTIFIER ::= { enterprises 2149 }
sds                               OBJECT IDENTIFIER ::= { enterprises 2150 }
promusHotelCorporation            OBJECT IDENTIFIER ::= { enterprises 2151 }
cavidLawrenceCenter               OBJECT IDENTIFIER ::= { enterprises 2152 }
insiderTechnologies               OBJECT IDENTIFIER ::= { enterprises 2153 }
berkeleyNetworks                  OBJECT IDENTIFIER ::= { enterprises 2154 }
infonauticsCorporation            OBJECT IDENTIFIER ::= { enterprises 2155 }
easySoftware                      OBJECT IDENTIFIER ::= { enterprises 2156 }
cesg                              OBJECT IDENTIFIER ::= { enterprises 2157 }
salixTechnologies                 OBJECT IDENTIFIER ::= { enterprises 2158 }
essentialCommunications           OBJECT IDENTIFIER ::= { enterprises 2159 }
universityOfHawaii                OBJECT IDENTIFIER ::= { enterprises 2160 }
foxtelManagementPty               OBJECT IDENTIFIER ::= { enterprises 2161 }
adventNetworkManagement           OBJECT IDENTIFIER ::= { enterprises 2162 }
vayris                            OBJECT IDENTIFIER ::= { enterprises 2163 }
telecomMultimediaSystems          OBJECT IDENTIFIER ::= { enterprises 2164 }
guardall                          OBJECT IDENTIFIER ::= { enterprises 2165 }
wkkSYSTEMS                        OBJECT IDENTIFIER ::= { enterprises 2166 }
prominetCorporation               OBJECT IDENTIFIER ::= { enterprises 2167 }
lmcLanManagementConsultingGmbH    OBJECT IDENTIFIER ::= { enterprises 2168 }
lewisEnterprise                   OBJECT IDENTIFIER ::= { enterprises 2169 }
telesAG                           OBJECT IDENTIFIER ::= { enterprises 2170 }
pcsi                              OBJECT IDENTIFIER ::= { enterprises 2171 }
fourthWaveDesigns                 OBJECT IDENTIFIER ::= { enterprises 2172 }
mediagate                         OBJECT IDENTIFIER ::= { enterprises 2173 }
interactiveOnlineServices         OBJECT IDENTIFIER ::= { enterprises 2174 }
mutekTranscom                     OBJECT IDENTIFIER ::= { enterprises 2175 }
universityOfDortmund              OBJECT IDENTIFIER ::= { enterprises 2176 }
networkDiagnosticClinic           OBJECT IDENTIFIER ::= { enterprises 2177 }
tsiTelecomSystems                 OBJECT IDENTIFIER ::= { enterprises 2178 }
wirespeedCommCorp                 OBJECT IDENTIFIER ::= { enterprises 2179 }
versanetCommunications            OBJECT IDENTIFIER ::= { enterprises 2180 }
eunetCommunicationsServicesBV     OBJECT IDENTIFIER ::= { enterprises 2181 }
powCommunications                 OBJECT IDENTIFIER ::= { enterprises 2182 }
am                                OBJECT IDENTIFIER ::= { enterprises 2183 }
openArchitectureSystemsIntegrationSolutions OBJECT IDENTIFIER ::= { enterprises 2184 }
netpartnerSro                     OBJECT IDENTIFIER ::= { enterprises 2185 }
vinaTechnologies                  OBJECT IDENTIFIER ::= { enterprises 2186 }
deutschesKlimarechenzentrumGmbH   OBJECT IDENTIFIER ::= { enterprises 2189 }
absyss                            OBJECT IDENTIFIER ::= { enterprises 2190 }
quadrophonics                     OBJECT IDENTIFIER ::= { enterprises 2191 }
hypercoreTechnology               OBJECT IDENTIFIER ::= { enterprises 2192 }
obtk                              OBJECT IDENTIFIER ::= { enterprises 2193 }
voisCorporation                   OBJECT IDENTIFIER ::= { enterprises 2194 }
ixoSA                             OBJECT IDENTIFIER ::= { enterprises 2195 }
macro4OpenSystems                 OBJECT IDENTIFIER ::= { enterprises 2196 }
securityDynamicsTechnologies      OBJECT IDENTIFIER ::= { enterprises 2197 }
nextwaveWireless                  OBJECT IDENTIFIER ::= { enterprises 2198 }
piscesConsultancy                 OBJECT IDENTIFIER ::= { enterprises 2199 }
tpsCallSciences                   OBJECT IDENTIFIER ::= { enterprises 2200 }
iconsult                          OBJECT IDENTIFIER ::= { enterprises 2201 }
thirdPointSystems                 OBJECT IDENTIFIER ::= { enterprises 2202 }
masTechnology                     OBJECT IDENTIFIER ::= { enterprises 2203 }
advancedLogicResearch             OBJECT IDENTIFIER ::= { enterprises 2204 }
documentum                        OBJECT IDENTIFIER ::= { enterprises 2205 }
siemensBusinessCommunicationSystems OBJECT IDENTIFIER ::= { enterprises 2206 }
telmaxCommunicationsCorp          OBJECT IDENTIFIER ::= { enterprises 2207 }
zypcom                            OBJECT IDENTIFIER ::= { enterprises 2208 }
remoteSense                       OBJECT IDENTIFIER ::= { enterprises 2209 }
ootekCorporation                  OBJECT IDENTIFIER ::= { enterprises 2210 }
esoft                             OBJECT IDENTIFIER ::= { enterprises 2211 }
anydataLimited                    OBJECT IDENTIFIER ::= { enterprises 2212 }
dataFellows                       OBJECT IDENTIFIER ::= { enterprises 2213 }
productionsMedialog               OBJECT IDENTIFIER ::= { enterprises 2214 }
inovamerci                        OBJECT IDENTIFIER ::= { enterprises 2215 }
okitec                            OBJECT IDENTIFIER ::= { enterprises 2216 }
vertexNetworks                    OBJECT IDENTIFIER ::= { enterprises 2217 }
pulseCommunications               OBJECT IDENTIFIER ::= { enterprises 2218 }
cxaCommunications                 OBJECT IDENTIFIER ::= { enterprises 2219 }
iddInformationService             OBJECT IDENTIFIER ::= { enterprises 2220 }
atlasComputerEquipment            OBJECT IDENTIFIER ::= { enterprises 2221 }
syntegra                          OBJECT IDENTIFIER ::= { enterprises 2222 }
cccInformationServices            OBJECT IDENTIFIER ::= { enterprises 2223 }
wQuinnAssociates                  OBJECT IDENTIFIER ::= { enterprises 2224 }
broadcomEireannResearch           OBJECT IDENTIFIER ::= { enterprises 2225 }
riskManagementServicesLlc         OBJECT IDENTIFIER ::= { enterprises 2226 }
watkinsJohnsonCompany             OBJECT IDENTIFIER ::= { enterprises 2227 }
ericEWestbrook                    OBJECT IDENTIFIER ::= { enterprises 2228 }
martinhoDavisSystems              OBJECT IDENTIFIER ::= { enterprises 2229 }
xypointCorporation                OBJECT IDENTIFIER ::= { enterprises 2230 }
innovatCommunications             OBJECT IDENTIFIER ::= { enterprises 2231 }
charleswoodAndCo                  OBJECT IDENTIFIER ::= { enterprises 2232 }
idSoftwareAS                      OBJECT IDENTIFIER ::= { enterprises 2233 }
teliaAB                           OBJECT IDENTIFIER ::= { enterprises 2234 }
explorationEnterprises            OBJECT IDENTIFIER ::= { enterprises 2235 }
daimlerBenzAerospaceAG            OBJECT IDENTIFIER ::= { enterprises 2236 }
xaraNetworks                      OBJECT IDENTIFIER ::= { enterprises 2237 }
theFreeBSDProject                 OBJECT IDENTIFIER ::= { enterprises 2238 }
worldMerchandiseExchange          OBJECT IDENTIFIER ::= { enterprises 2239 }
lysis                             OBJECT IDENTIFIER ::= { enterprises 2240 }
cflResearch                       OBJECT IDENTIFIER ::= { enterprises 2241 }
netTELComputerSystemsLimited      OBJECT IDENTIFIER ::= { enterprises 2242 }
sattelCommunications              OBJECT IDENTIFIER ::= { enterprises 2243 }
promatoryCommunications           OBJECT IDENTIFIER ::= { enterprises 2244 }
syncsort                          OBJECT IDENTIFIER ::= { enterprises 2245 }
lloydstsbGroupPlc                 OBJECT IDENTIFIER ::= { enterprises 2246 }
itConsultancyEngineeringManagementGroup OBJECT IDENTIFIER ::= { enterprises 2247 }
liteONCOMMUNICATIONSCORP          OBJECT IDENTIFIER ::= { enterprises 2248 }
theNewMillennium                  OBJECT IDENTIFIER ::= { enterprises 2249 }
quatracoYugoslavia                OBJECT IDENTIFIER ::= { enterprises 2250 }
brBusinessSystems                 OBJECT IDENTIFIER ::= { enterprises 2251 }
wheelgroupCorporation             OBJECT IDENTIFIER ::= { enterprises 2252 }
ultimateTechnology                OBJECT IDENTIFIER ::= { enterprises 2253 }
deltaElectronics                  OBJECT IDENTIFIER ::= { enterprises 2254 }
waffleProductions                 OBJECT IDENTIFIER ::= { enterprises 2255 }
koreaInternet                     OBJECT IDENTIFIER ::= { enterprises 2256 }
baeSYSTEMS                        OBJECT IDENTIFIER ::= { enterprises 2257 }
thomsonBROADCASTSYSTEMS           OBJECT IDENTIFIER ::= { enterprises 2258 }
workflowAutomationCompany         OBJECT IDENTIFIER ::= { enterprises 2259 }
associatedRT                      OBJECT IDENTIFIER ::= { enterprises 2260 }
codemSystems                      OBJECT IDENTIFIER ::= { enterprises 2261 }
rightTIMEWATCHCENTER              OBJECT IDENTIFIER ::= { enterprises 2262 }
advancedVisionTechnologies        OBJECT IDENTIFIER ::= { enterprises 2263 }
appliedIntelligenceGroup          OBJECT IDENTIFIER ::= { enterprises 2264 }
acornComputers                    OBJECT IDENTIFIER ::= { enterprises 2265 }
tempestConsulting                 OBJECT IDENTIFIER ::= { enterprises 2266 }
digitalSoundCorporation           OBJECT IDENTIFIER ::= { enterprises 2267 }
fastlanSolutions                  OBJECT IDENTIFIER ::= { enterprises 2268 }
ordinoxNetwork                    OBJECT IDENTIFIER ::= { enterprises 2269 }
telincCorporation                 OBJECT IDENTIFIER ::= { enterprises 2270 }
drsConsultingGroup                OBJECT IDENTIFIER ::= { enterprises 2271 }
rapidCityCommunication            OBJECT IDENTIFIER ::= { enterprises 2272 }
invisibleFenceSalesCompany        OBJECT IDENTIFIER ::= { enterprises 2273 }
troikaManagementServices          OBJECT IDENTIFIER ::= { enterprises 2274 }
vxtreme                           OBJECT IDENTIFIER ::= { enterprises 2275 }
cryptsoftPty                      OBJECT IDENTIFIER ::= { enterprises 2276 }
brooktroutTechnology              OBJECT IDENTIFIER ::= { enterprises 2277 }
grassMbH                          OBJECT IDENTIFIER ::= { enterprises 2278 }
epicon                            OBJECT IDENTIFIER ::= { enterprises 2279 }
sadTrasportoLocaleSpa             OBJECT IDENTIFIER ::= { enterprises 2280 }
giganet                           OBJECT IDENTIFIER ::= { enterprises 2281 }
incaaInformaticaItaliaSrl         OBJECT IDENTIFIER ::= { enterprises 2282 }
vermontFirmwareCorporation        OBJECT IDENTIFIER ::= { enterprises 2283 }
automatedConcepts                 OBJECT IDENTIFIER ::= { enterprises 2284 }
flashNetworks                     OBJECT IDENTIFIER ::= { enterprises 2285 }
oracom                            OBJECT IDENTIFIER ::= { enterprises 2286 }
shellServicesCompany              OBJECT IDENTIFIER ::= { enterprises 2287 }
blackPigsOfDeath                  OBJECT IDENTIFIER ::= { enterprises 2288 }
n3erz                             OBJECT IDENTIFIER ::= { enterprises 2289 }
technologyRendezvous              OBJECT IDENTIFIER ::= { enterprises 2290 }
zapnet                            OBJECT IDENTIFIER ::= { enterprises 2291 }
premierTechnologies               OBJECT IDENTIFIER ::= { enterprises 2292 }
tennysonTechnologies              OBJECT IDENTIFIER ::= { enterprises 2293 }
artecon                           OBJECT IDENTIFIER ::= { enterprises 2294 }
dhTechnology                      OBJECT IDENTIFIER ::= { enterprises 2295 }
dagazTechnologies                 OBJECT IDENTIFIER ::= { enterprises 2296 }
ganymedeSoftware                  OBJECT IDENTIFIER ::= { enterprises 2297 }
teleCommunications                OBJECT IDENTIFIER ::= { enterprises 2298 }
freegateCorportation              OBJECT IDENTIFIER ::= { enterprises 2299 }
maincontrol                       OBJECT IDENTIFIER ::= { enterprises 2300 }
luminateSoftwareCorp              OBJECT IDENTIFIER ::= { enterprises 2301 }
k2net                             OBJECT IDENTIFIER ::= { enterprises 2302 }
auroraCommunciationsPty           OBJECT IDENTIFIER ::= { enterprises 2303 }
lanscapeLimited                   OBJECT IDENTIFIER ::= { enterprises 2304 }
gatewayTechnologies               OBJECT IDENTIFIER ::= { enterprises 2305 }
zergoLimited                      OBJECT IDENTIFIER ::= { enterprises 2306 }
c4uSolutions                      OBJECT IDENTIFIER ::= { enterprises 2307 }
bollReichEngineeringAG            OBJECT IDENTIFIER ::= { enterprises 2308 }
internetMailConsortium            OBJECT IDENTIFIER ::= { enterprises 2309 }
collegeOfMathematicsAndScienceUnivOfCentralOklahoma OBJECT IDENTIFIER ::= { enterprises 2310 }
instituteForAppliedSupercomputingCSUSB OBJECT IDENTIFIER ::= { enterprises 2311 }
redHatSoftware                    OBJECT IDENTIFIER ::= { enterprises 2312 }
legalAndGeneralAssuranceSociety   OBJECT IDENTIFIER ::= { enterprises 2313 }
fireNetworks                      OBJECT IDENTIFIER ::= { enterprises 2314 }
icti                              OBJECT IDENTIFIER ::= { enterprises 2315 }
internetCommunicationSecurity     OBJECT IDENTIFIER ::= { enterprises 2316 }
talxCorporation                   OBJECT IDENTIFIER ::= { enterprises 2317 }
repeaterTechnologies              OBJECT IDENTIFIER ::= { enterprises 2318 }
aumtech                           OBJECT IDENTIFIER ::= { enterprises 2319 }
eurosinet                         OBJECT IDENTIFIER ::= { enterprises 2320 }
keKommunikationsElektronik        OBJECT IDENTIFIER ::= { enterprises 2321 }
starvisionMultimediaCorp          OBJECT IDENTIFIER ::= { enterprises 2322 }
alcatelTelecomASD                 OBJECT IDENTIFIER ::= { enterprises 2323 }
avalDATACoporation                OBJECT IDENTIFIER ::= { enterprises 2324 }
pacificNorthwestNationalLaboratory OBJECT IDENTIFIER ::= { enterprises 2325 }
tortoiseSoftwareSystems           OBJECT IDENTIFIER ::= { enterprises 2326 }
verio                             OBJECT IDENTIFIER ::= { enterprises 2327 }
arraycomm                         OBJECT IDENTIFIER ::= { enterprises 2328 }
dstSystems                        OBJECT IDENTIFIER ::= { enterprises 2329 }
visionServicePlan                 OBJECT IDENTIFIER ::= { enterprises 2330 }
bestBuy                           OBJECT IDENTIFIER ::= { enterprises 2331 }
sharedNetworkServices             OBJECT IDENTIFIER ::= { enterprises 2332 }
bbc                               OBJECT IDENTIFIER ::= { enterprises 2333 }
packeteer                         OBJECT IDENTIFIER ::= { enterprises 2334 }
appliedDigitalAccess              OBJECT IDENTIFIER ::= { enterprises 2335 }
hisTechnologies                   OBJECT IDENTIFIER ::= { enterprises 2336 }
dneTechnologies                   OBJECT IDENTIFIER ::= { enterprises 2337 }
verticalNetworks                  OBJECT IDENTIFIER ::= { enterprises 2338 }
csoft                             OBJECT IDENTIFIER ::= { enterprises 2339 }
nationalGrocers                   OBJECT IDENTIFIER ::= { enterprises 2340 }
relianceComputerCorp              OBJECT IDENTIFIER ::= { enterprises 2341 }
akNORDEDVVertriebsgesMbH          OBJECT IDENTIFIER ::= { enterprises 2342 }
financialTechnologiesInternational OBJECT IDENTIFIER ::= { enterprises 2343 }
spaceworks                        OBJECT IDENTIFIER ::= { enterprises 2344 }
torrentNetworkingTechnologiesCorp OBJECT IDENTIFIER ::= { enterprises 2345 }
cti                               OBJECT IDENTIFIER ::= { enterprises 2346 }
datastreamInternational           OBJECT IDENTIFIER ::= { enterprises 2347 }
killion                           OBJECT IDENTIFIER ::= { enterprises 2348 }
missionCriticalSoftware           OBJECT IDENTIFIER ::= { enterprises 2349 }
dataResearchAndApplications       OBJECT IDENTIFIER ::= { enterprises 2350 }
resonate                          OBJECT IDENTIFIER ::= { enterprises 2351 }
redbackNetworks                   OBJECT IDENTIFIER ::= { enterprises 2352 }
nexwareCorporation                OBJECT IDENTIFIER ::= { enterprises 2353 }
adcWirelessSystems                OBJECT IDENTIFIER ::= { enterprises 2354 }
itis                              OBJECT IDENTIFIER ::= { enterprises 2355 }
elsaGmbH                          OBJECT IDENTIFIER ::= { enterprises 2356 }
psimedCorporation                 OBJECT IDENTIFIER ::= { enterprises 2357 }
transferDataTestGmbH              OBJECT IDENTIFIER ::= { enterprises 2358 }
tipGroupSA                        OBJECT IDENTIFIER ::= { enterprises 2359 }
redlink                           OBJECT IDENTIFIER ::= { enterprises 2360 }
japanInformationEngineeringCo     OBJECT IDENTIFIER ::= { enterprises 2361 }
richterSystemsDevelopment         OBJECT IDENTIFIER ::= { enterprises 2362 }
eurocontrolMASUAC                 OBJECT IDENTIFIER ::= { enterprises 2363 }
konicaCorporation                 OBJECT IDENTIFIER ::= { enterprises 2364 }
viacom                            OBJECT IDENTIFIER ::= { enterprises 2365 }
xiotechCorporation                OBJECT IDENTIFIER ::= { enterprises 2366 }
--                                OBJECT IDENTIFIER ::= { enterprises 2367 }
softworks                         OBJECT IDENTIFIER ::= { enterprises 2368 }
mobilewareCorporation             OBJECT IDENTIFIER ::= { enterprises 2369 }
memcoSoftware                     OBJECT IDENTIFIER ::= { enterprises 2370 }
advancedTechCom                   OBJECT IDENTIFIER ::= { enterprises 2371 }
bedfordAssociates                 OBJECT IDENTIFIER ::= { enterprises 2372 }
cyberwizard                       OBJECT IDENTIFIER ::= { enterprises 2373 }
smartTechnologies                 OBJECT IDENTIFIER ::= { enterprises 2374 }
concentricNetworkCorporation      OBJECT IDENTIFIER ::= { enterprises 2375 }
theSNMPWorkShop                   OBJECT IDENTIFIER ::= { enterprises 2376 }
reltecCorp                        OBJECT IDENTIFIER ::= { enterprises 2377 }
nera                              OBJECT IDENTIFIER ::= { enterprises 2378 }
nationsBank                       OBJECT IDENTIFIER ::= { enterprises 2379 }
integratedDesignTechniquesLimited OBJECT IDENTIFIER ::= { enterprises 2380 }
openlinkSoftware                  OBJECT IDENTIFIER ::= { enterprises 2381 }
netreality                        OBJECT IDENTIFIER ::= { enterprises 2382 }
imationCorp                       OBJECT IDENTIFIER ::= { enterprises 2383 }
sibis                             OBJECT IDENTIFIER ::= { enterprises 2384 }
sharpCorporation                  OBJECT IDENTIFIER ::= { enterprises 2385 }
desktopData                       OBJECT IDENTIFIER ::= { enterprises 2386 }
telecomDeviceKK                   OBJECT IDENTIFIER ::= { enterprises 2387 }
captechCommunication              OBJECT IDENTIFIER ::= { enterprises 2388 }
performanceTelecomCorp            OBJECT IDENTIFIER ::= { enterprises 2389 }
com                               OBJECT IDENTIFIER ::= { enterprises 2390 }
karim                             OBJECT IDENTIFIER ::= { enterprises 2391 }
systemsIntegrationGroup           OBJECT IDENTIFIER ::= { enterprises 2392 }
witcomInnovativeRadioSystems      OBJECT IDENTIFIER ::= { enterprises 2393 }
sfSoftware                        OBJECT IDENTIFIER ::= { enterprises 2394 }
marbenItaliaSpA                   OBJECT IDENTIFIER ::= { enterprises 2395 }
activcard                         OBJECT IDENTIFIER ::= { enterprises 2396 }
cognos                            OBJECT IDENTIFIER ::= { enterprises 2397 }
eagleTrafficControlSystemsWL      OBJECT IDENTIFIER ::= { enterprises 2398 }
netwave                           OBJECT IDENTIFIER ::= { enterprises 2399 }
hemetnet                          OBJECT IDENTIFIER ::= { enterprises 2400 }
nbxCorporation                    OBJECT IDENTIFIER ::= { enterprises 2401 }
alBaderShippingAndGenContCoDomnic OBJECT IDENTIFIER ::= { enterprises 2402 }
primeur                           OBJECT IDENTIFIER ::= { enterprises 2404 }
ilts                              OBJECT IDENTIFIER ::= { enterprises 2405 }
computerGeneration                OBJECT IDENTIFIER ::= { enterprises 2406 }
moutonNoirEnterprises             OBJECT IDENTIFIER ::= { enterprises 2407 }
baystateSoundAndRecording         OBJECT IDENTIFIER ::= { enterprises 2408 }
metapathCorporation               OBJECT IDENTIFIER ::= { enterprises 2409 }
tajeetGourmetFoodManufacturing    OBJECT IDENTIFIER ::= { enterprises 2410 }
telcel                            OBJECT IDENTIFIER ::= { enterprises 2411 }
intertrader                       OBJECT IDENTIFIER ::= { enterprises 2412 }
maxtronics                        OBJECT IDENTIFIER ::= { enterprises 2413 }
spiderplant                       OBJECT IDENTIFIER ::= { enterprises 2414 }
softwarecom                       OBJECT IDENTIFIER ::= { enterprises 2415 }
adherentSystems                   OBJECT IDENTIFIER ::= { enterprises 2416 }
korfmacher                        OBJECT IDENTIFIER ::= { enterprises 2417 }
svenskaEDITAB                     OBJECT IDENTIFIER ::= { enterprises 2418 }
mlm5000                           OBJECT IDENTIFIER ::= { enterprises 2419 }
init                              OBJECT IDENTIFIER ::= { enterprises 2420 }
teltoneCorporation                OBJECT IDENTIFIER ::= { enterprises 2421 }
faircrossComputers                OBJECT IDENTIFIER ::= { enterprises 2422 }
carycom                           OBJECT IDENTIFIER ::= { enterprises 2423 }
dominioPublicoInternet            OBJECT IDENTIFIER ::= { enterprises 2424 }
bkrNetworkSystems                 OBJECT IDENTIFIER ::= { enterprises 2425 }
mariposaTechnology                OBJECT IDENTIFIER ::= { enterprises 2426 }
nuview                            OBJECT IDENTIFIER ::= { enterprises 2427 }
uninett                           OBJECT IDENTIFIER ::= { enterprises 2428 }
ace                               OBJECT IDENTIFIER ::= { enterprises 2429 }
oyComptelAb                       OBJECT IDENTIFIER ::= { enterprises 2430 }
mmsCommunicationGmbH              OBJECT IDENTIFIER ::= { enterprises 2431 }
sortova                           OBJECT IDENTIFIER ::= { enterprises 2432 }
envoyCorporation                  OBJECT IDENTIFIER ::= { enterprises 2433 }
metronTechnologyLimited           OBJECT IDENTIFIER ::= { enterprises 2434 }
brotherIndustries                 OBJECT IDENTIFIER ::= { enterprises 2435 }
netcomSystems                     OBJECT IDENTIFIER ::= { enterprises 2436 }
kapschAG                          OBJECT IDENTIFIER ::= { enterprises 2437 }
shomitiSystems                    OBJECT IDENTIFIER ::= { enterprises 2438 }
computermCorporation              OBJECT IDENTIFIER ::= { enterprises 2439 }
networkEngineeringSoftwareSystems OBJECT IDENTIFIER ::= { enterprises 2440 }
certisoftTecnologia               OBJECT IDENTIFIER ::= { enterprises 2441 }
ediEnterprises                    OBJECT IDENTIFIER ::= { enterprises 2442 }
cciiSystems                       OBJECT IDENTIFIER ::= { enterprises 2443 }
connetix                          OBJECT IDENTIFIER ::= { enterprises 2444 }
tunixOpenSystemConsultants        OBJECT IDENTIFIER ::= { enterprises 2445 }
gnpComputers                      OBJECT IDENTIFIER ::= { enterprises 2446 }
intercopeInternational            OBJECT IDENTIFIER ::= { enterprises 2447 }
nxt                               OBJECT IDENTIFIER ::= { enterprises 2448 }
panDacomForcomTelekommunikationssystemeGmbH OBJECT IDENTIFIER ::= { enterprises 2449 }
auco                              OBJECT IDENTIFIER ::= { enterprises 2450 }
tecnomenOY                        OBJECT IDENTIFIER ::= { enterprises 2451 }
helaxAB                           OBJECT IDENTIFIER ::= { enterprises 2452 }
omtool                            OBJECT IDENTIFIER ::= { enterprises 2453 }
gConnect                          OBJECT IDENTIFIER ::= { enterprises 2454 }
dynamicMutualFunds                OBJECT IDENTIFIER ::= { enterprises 2455 }
antecNetworkTechnologies          OBJECT IDENTIFIER ::= { enterprises 2456 }
premierePromotions                OBJECT IDENTIFIER ::= { enterprises 2457 }
lanquest                          OBJECT IDENTIFIER ::= { enterprises 2458 }
guardianBankPZagreb               OBJECT IDENTIFIER ::= { enterprises 2459 }
ihlasNet                          OBJECT IDENTIFIER ::= { enterprises 2460 }
wavtrace                          OBJECT IDENTIFIER ::= { enterprises 2461 }
viggenCorporation                 OBJECT IDENTIFIER ::= { enterprises 2462 }
saifALICO                         OBJECT IDENTIFIER ::= { enterprises 2463 }
carynetInformationCenter          OBJECT IDENTIFIER ::= { enterprises 2464 }
applicationTelematiques           OBJECT IDENTIFIER ::= { enterprises 2465 }
channelmaticLIMT                  OBJECT IDENTIFIER ::= { enterprises 2466 }
arrowpointCommunications          OBJECT IDENTIFIER ::= { enterprises 2467 }
allionComputer                    OBJECT IDENTIFIER ::= { enterprises 2468 }
netbuilding                       OBJECT IDENTIFIER ::= { enterprises 2469 }
personalAndConfidentialKlaus      OBJECT IDENTIFIER ::= { enterprises 2470 }
comsysInternationalBV             OBJECT IDENTIFIER ::= { enterprises 2471 }
advanceTelecommunication          OBJECT IDENTIFIER ::= { enterprises 2472 }
gatekeySolutions                  OBJECT IDENTIFIER ::= { enterprises 2473 }
aviciSystems                      OBJECT IDENTIFIER ::= { enterprises 2474 }
sierraTechnology                  OBJECT IDENTIFIER ::= { enterprises 2475 }
encantoNetworks                   OBJECT IDENTIFIER ::= { enterprises 2476 }
mountOliveCollege                 OBJECT IDENTIFIER ::= { enterprises 2477 }
fujitsuDenso                      OBJECT IDENTIFIER ::= { enterprises 2478 }
edsGmbH                           OBJECT IDENTIFIER ::= { enterprises 2479 }
jyraResearch                      OBJECT IDENTIFIER ::= { enterprises 2480 }
summitCommunications              OBJECT IDENTIFIER ::= { enterprises 2481 }
ministryOfTransport               OBJECT IDENTIFIER ::= { enterprises 2482 }
winnetMCS                         OBJECT IDENTIFIER ::= { enterprises 2483 }
icgCommunications                 OBJECT IDENTIFIER ::= { enterprises 2484 }
crosslinkInternetServices         OBJECT IDENTIFIER ::= { enterprises 2485 }
cygnusComputerAssociates          OBJECT IDENTIFIER ::= { enterprises 2486 }
phoenixTechnologies               OBJECT IDENTIFIER ::= { enterprises 2487 }
internetclub                      OBJECT IDENTIFIER ::= { enterprises 2488 }
--                                OBJECT IDENTIFIER ::= { enterprises 2489 }
vixelCorporation                  OBJECT IDENTIFIER ::= { enterprises 2490 }
atmosphereNetworks                OBJECT IDENTIFIER ::= { enterprises 2491 }
montanaTelNet                     OBJECT IDENTIFIER ::= { enterprises 2492 }
jcpComputerServices               OBJECT IDENTIFIER ::= { enterprises 2493 }
interClearService                 OBJECT IDENTIFIER ::= { enterprises 2494 }
vixieEnterprises                  OBJECT IDENTIFIER ::= { enterprises 2495 }
lightspeedInternational           OBJECT IDENTIFIER ::= { enterprises 2496 }
gammagraphx                       OBJECT IDENTIFIER ::= { enterprises 2497 }
imanage                           OBJECT IDENTIFIER ::= { enterprises 2498 }
internetSecuritySystems           OBJECT IDENTIFIER ::= { enterprises 2499 }
viennaSystemsCorporation          OBJECT IDENTIFIER ::= { enterprises 2500 }
yagoSystems                       OBJECT IDENTIFIER ::= { enterprises 2501 }
lunarwaveCommunications           OBJECT IDENTIFIER ::= { enterprises 2502 }
bangkokPattayaHospital            OBJECT IDENTIFIER ::= { enterprises 2503 }
rokeManorResearchLimited          OBJECT IDENTIFIER ::= { enterprises 2504 }
newOakCommunications              OBJECT IDENTIFIER ::= { enterprises 2505 }
bugFreeDevelopment                OBJECT IDENTIFIER ::= { enterprises 2506 }
arcTechnologiesGroup              OBJECT IDENTIFIER ::= { enterprises 2507 }
internetDynamics                  OBJECT IDENTIFIER ::= { enterprises 2508 }
digitalMicrowaveCorp              OBJECT IDENTIFIER ::= { enterprises 2509 }
bearMountainSoftware              OBJECT IDENTIFIER ::= { enterprises 2510 }
accesslanCommunications           OBJECT IDENTIFIER ::= { enterprises 2511 }
crossroadsSystems                 OBJECT IDENTIFIER ::= { enterprises 2512 }
cr2aDI                            OBJECT IDENTIFIER ::= { enterprises 2513 }
mantraCommunications              OBJECT IDENTIFIER ::= { enterprises 2514 }
discovernet                       OBJECT IDENTIFIER ::= { enterprises 2515 }
vocaltecCommunications            OBJECT IDENTIFIER ::= { enterprises 2516 }
riversoftLimited                  OBJECT IDENTIFIER ::= { enterprises 2517 }
phaosTechnologyCorp               OBJECT IDENTIFIER ::= { enterprises 2518 }
tokyoCommunicationsNetworkCo      OBJECT IDENTIFIER ::= { enterprises 2519 }
internetSystems                   OBJECT IDENTIFIER ::= { enterprises 2520 }
comconsult                        OBJECT IDENTIFIER ::= { enterprises 2521 }
osicomTechnologies                OBJECT IDENTIFIER ::= { enterprises 2522 }
hitronTechnology                  OBJECT IDENTIFIER ::= { enterprises 2523 }
rabensteinEnterprises             OBJECT IDENTIFIER ::= { enterprises 2524 }
atSistemas                        OBJECT IDENTIFIER ::= { enterprises 2525 }
ipass                             OBJECT IDENTIFIER ::= { enterprises 2526 }
interlinearTechnology             OBJECT IDENTIFIER ::= { enterprises 2527 }
worldOneTelecom                   OBJECT IDENTIFIER ::= { enterprises 2528 }
quadritekSystems                  OBJECT IDENTIFIER ::= { enterprises 2529 }
syseca                            OBJECT IDENTIFIER ::= { enterprises 2530 }
netspeakCorporation               OBJECT IDENTIFIER ::= { enterprises 2531 }
opnet                             OBJECT IDENTIFIER ::= { enterprises 2532 }
mrmConsulting                     OBJECT IDENTIFIER ::= { enterprises 2533 }
tnsysTradingNetSystem             OBJECT IDENTIFIER ::= { enterprises 2534 }
jcmt                              OBJECT IDENTIFIER ::= { enterprises 2535 }
endeavourHillsComputerServices    OBJECT IDENTIFIER ::= { enterprises 2536 }
diversifiedTechnology             OBJECT IDENTIFIER ::= { enterprises 2537 }
lateralManagementLimited          OBJECT IDENTIFIER ::= { enterprises 2538 }
proxySoftwareSystems              OBJECT IDENTIFIER ::= { enterprises 2539 }
combox                            OBJECT IDENTIFIER ::= { enterprises 2540 }
spectrixCorporation               OBJECT IDENTIFIER ::= { enterprises 2541 }
electronicsAndTelecommunicationsResearchInstitute OBJECT IDENTIFIER ::= { enterprises 2542 }
arlottoComnet                     OBJECT IDENTIFIER ::= { enterprises 2543 }
advaGmbH                          OBJECT IDENTIFIER ::= { enterprises 2544 }
newtecGmbHSystementwicklungUndBeratung OBJECT IDENTIFIER ::= { enterprises 2545 }
pvtAsPvtnet                       OBJECT IDENTIFIER ::= { enterprises 2546 }
catholicUniversityOfPelotas       OBJECT IDENTIFIER ::= { enterprises 2547 }
cryptonymCorporation              OBJECT IDENTIFIER ::= { enterprises 2548 }
akerConsultoriaEInformatica       OBJECT IDENTIFIER ::= { enterprises 2549 }
elvisPlusCo                       OBJECT IDENTIFIER ::= { enterprises 2550 }
telegyrSystems                    OBJECT IDENTIFIER ::= { enterprises 2551 }
netegrity                         OBJECT IDENTIFIER ::= { enterprises 2552 }
cardinalNetwork                   OBJECT IDENTIFIER ::= { enterprises 2553 }
microIntegratedInnnovations       OBJECT IDENTIFIER ::= { enterprises 2554 }
jayatekSdnBhd                     OBJECT IDENTIFIER ::= { enterprises 2555 }
centralElectronicIndustry         OBJECT IDENTIFIER ::= { enterprises 2556 }
transcendAccessSystems            OBJECT IDENTIFIER ::= { enterprises 2557 }
outreachCommunicationsCorp        OBJECT IDENTIFIER ::= { enterprises 2558 }
bocatel                           OBJECT IDENTIFIER ::= { enterprises 2559 }
atAndtGNMCAmsterdam               OBJECT IDENTIFIER ::= { enterprises 2560 }
teamphonecom                      OBJECT IDENTIFIER ::= { enterprises 2561 }
sbbSoftwareBeratungGmbH           OBJECT IDENTIFIER ::= { enterprises 2562 }
comstatDataCommCorporation        OBJECT IDENTIFIER ::= { enterprises 2563 }
theNetworkTechnologyGroup         OBJECT IDENTIFIER ::= { enterprises 2564 }
averyDennison                     OBJECT IDENTIFIER ::= { enterprises 2565 }
rohdeAndSCHWARZGmbHAndCoKG        OBJECT IDENTIFIER ::= { enterprises 2566 }
datamediaSA                       OBJECT IDENTIFIER ::= { enterprises 2567 }
integrix                          OBJECT IDENTIFIER ::= { enterprises 2568 }
telenorNovitAS                    OBJECT IDENTIFIER ::= { enterprises 2569 }
preferedCommunications            OBJECT IDENTIFIER ::= { enterprises 2570 }
mu                                OBJECT IDENTIFIER ::= { enterprises 2571 }
networkTeleSystems                OBJECT IDENTIFIER ::= { enterprises 2572 }
decisionScienceApplications       OBJECT IDENTIFIER ::= { enterprises 2573 }
concentricity                     OBJECT IDENTIFIER ::= { enterprises 2574 }
ableCommunications                OBJECT IDENTIFIER ::= { enterprises 2575 }
computershareSystemsLimited       OBJECT IDENTIFIER ::= { enterprises 2576 }
edrTechnologies                   OBJECT IDENTIFIER ::= { enterprises 2577 }
abirnet                           OBJECT IDENTIFIER ::= { enterprises 2578 }
trikota                           OBJECT IDENTIFIER ::= { enterprises 2579 }
dieboldCompanyOfCanadaLimited     OBJECT IDENTIFIER ::= { enterprises 2580 }
preciseConnectivitySolutions      OBJECT IDENTIFIER ::= { enterprises 2581 }
ansCommunications                 OBJECT IDENTIFIER ::= { enterprises 2582 }
hydroQuebecTransEnergie           OBJECT IDENTIFIER ::= { enterprises 2583 }
radiolan                          OBJECT IDENTIFIER ::= { enterprises 2584 }
youthOpportunitiesUpheld          OBJECT IDENTIFIER ::= { enterprises 2585 }
teracomAB                         OBJECT IDENTIFIER ::= { enterprises 2586 }
freemontAvenueSoftware            OBJECT IDENTIFIER ::= { enterprises 2587 }
positronFiberSystems              OBJECT IDENTIFIER ::= { enterprises 2588 }
chuoElectronics                   OBJECT IDENTIFIER ::= { enterprises 2589 }
minoltaCo                         OBJECT IDENTIFIER ::= { enterprises 2590 }
radyneCorporation                 OBJECT IDENTIFIER ::= { enterprises 2591 }
nsiSoftware                       OBJECT IDENTIFIER ::= { enterprises 2592 }
exstreamPC                        OBJECT IDENTIFIER ::= { enterprises 2593 }
simulationLaboritories            OBJECT IDENTIFIER ::= { enterprises 2594 }
webtvNetworks                     OBJECT IDENTIFIER ::= { enterprises 2595 }
creditManagementSolutions         OBJECT IDENTIFIER ::= { enterprises 2596 }
chisholmTechnologies              OBJECT IDENTIFIER ::= { enterprises 2597 }
wondernetInternationalCorp        OBJECT IDENTIFIER ::= { enterprises 2598 }
percpeticsCorporation             OBJECT IDENTIFIER ::= { enterprises 2599 }
distributedSystemsLogic           OBJECT IDENTIFIER ::= { enterprises 2600 }
usWestInterpriseNetworkingServices OBJECT IDENTIFIER ::= { enterprises 2601 }
intrasoftCorporation              OBJECT IDENTIFIER ::= { enterprises 2602 }
allotCommunications               OBJECT IDENTIFIER ::= { enterprises 2603 }
sophosPlc                         OBJECT IDENTIFIER ::= { enterprises 2604 }
taylormadeMath                    OBJECT IDENTIFIER ::= { enterprises 2605 }
rittalWerkRudolfLohGmbHAndCoKG    OBJECT IDENTIFIER ::= { enterprises 2606 }
lanInternational                  OBJECT IDENTIFIER ::= { enterprises 2607 }
preciseSoftwareSolutions          OBJECT IDENTIFIER ::= { enterprises 2608 }
newPrime                          OBJECT IDENTIFIER ::= { enterprises 2609 }
datahavenProject                  OBJECT IDENTIFIER ::= { enterprises 2610 }
interspeed                        OBJECT IDENTIFIER ::= { enterprises 2611 }
iDataInternationalAS              OBJECT IDENTIFIER ::= { enterprises 2612 }
acceleratedNetworks               OBJECT IDENTIFIER ::= { enterprises 2613 }
forschungszentrumKarlsruheGmbH    OBJECT IDENTIFIER ::= { enterprises 2614 }
ixmicro                           OBJECT IDENTIFIER ::= { enterprises 2615 }
caoDiffusion                      OBJECT IDENTIFIER ::= { enterprises 2616 }
computerCommunicationsConsulting  OBJECT IDENTIFIER ::= { enterprises 2617 }
tracewellSystems                  OBJECT IDENTIFIER ::= { enterprises 2618 }
advancedInternetManagement        OBJECT IDENTIFIER ::= { enterprises 2619 }
checkPointSoftwareTechnologies    OBJECT IDENTIFIER ::= { enterprises 2620 }
martinZwernemann                  OBJECT IDENTIFIER ::= { enterprises 2621 }
amarexTechnology                  OBJECT IDENTIFIER ::= { enterprises 2622 }
asustekComputer                   OBJECT IDENTIFIER ::= { enterprises 2623 }
waveWirelessNetworking            OBJECT IDENTIFIER ::= { enterprises 2624 }
fciTelecommunicationsCorporation  OBJECT IDENTIFIER ::= { enterprises 2625 }
prosum                            OBJECT IDENTIFIER ::= { enterprises 2626 }
tcamSystems                       OBJECT IDENTIFIER ::= { enterprises 2627 }
naturalMicroSystems               OBJECT IDENTIFIER ::= { enterprises 2628 }
cityOfWauwatosa                   OBJECT IDENTIFIER ::= { enterprises 2629 }
theEsysCorporation                OBJECT IDENTIFIER ::= { enterprises 2630 }
altvaterAirdataSystemsGmbH        OBJECT IDENTIFIER ::= { enterprises 2631 }
ptWiryamasSinarPalapa             OBJECT IDENTIFIER ::= { enterprises 2632 }
compucentre                       OBJECT IDENTIFIER ::= { enterprises 2633 }
westernTelematic                  OBJECT IDENTIFIER ::= { enterprises 2634 }
adtx                              OBJECT IDENTIFIER ::= { enterprises 2635 }
juniperNetworks                   OBJECT IDENTIFIER ::= { enterprises 2636 }
aptisCommunications               OBJECT IDENTIFIER ::= { enterprises 2637 }
bstpromark                        OBJECT IDENTIFIER ::= { enterprises 2638 }
edgepointNetworks                 OBJECT IDENTIFIER ::= { enterprises 2639 }
aimetrix                          OBJECT IDENTIFIER ::= { enterprises 2640 }
arctunnConsulting                 OBJECT IDENTIFIER ::= { enterprises 2641 }
computelElectronicaSA             OBJECT IDENTIFIER ::= { enterprises 2642 }
flowwiseNetworks                  OBJECT IDENTIFIER ::= { enterprises 2643 }
synaptyxCorporation               OBJECT IDENTIFIER ::= { enterprises 2644 }
firstUnionNationalBank            OBJECT IDENTIFIER ::= { enterprises 2645 }
kommunikatorGmbH                  OBJECT IDENTIFIER ::= { enterprises 2646 }
c2s                               OBJECT IDENTIFIER ::= { enterprises 2647 }
siligom                           OBJECT IDENTIFIER ::= { enterprises 2648 }
radcom                            OBJECT IDENTIFIER ::= { enterprises 2649 }
goAheadSoftware                   OBJECT IDENTIFIER ::= { enterprises 2650 }
spaceConnectionNV                 OBJECT IDENTIFIER ::= { enterprises 2651 }
merckMedcoManagedCareLLC          OBJECT IDENTIFIER ::= { enterprises 2652 }
cityComBV                         OBJECT IDENTIFIER ::= { enterprises 2653 }
rAndsBICKMobilfunkGmbH            OBJECT IDENTIFIER ::= { enterprises 2654 }
keplerSoftware                    OBJECT IDENTIFIER ::= { enterprises 2655 }
banqueParibas                     OBJECT IDENTIFIER ::= { enterprises 2656 }
zitechNet                         OBJECT IDENTIFIER ::= { enterprises 2657 }
centuryAnalysis                   OBJECT IDENTIFIER ::= { enterprises 2658 }
talentDevelopmentGmbH             OBJECT IDENTIFIER ::= { enterprises 2659 }
coppercom                         OBJECT IDENTIFIER ::= { enterprises 2660 }
yutakaElectricMfgCo               OBJECT IDENTIFIER ::= { enterprises 2661 }
sbfBourseDeParis                  OBJECT IDENTIFIER ::= { enterprises 2662 }
economatica                       OBJECT IDENTIFIER ::= { enterprises 2663 }
gvnTechnologies                   OBJECT IDENTIFIER ::= { enterprises 2664 }
olsyUK                            OBJECT IDENTIFIER ::= { enterprises 2665 }
room42Software                    OBJECT IDENTIFIER ::= { enterprises 2666 }
cirilium                          OBJECT IDENTIFIER ::= { enterprises 2667 }
tavveSoftwareCo                   OBJECT IDENTIFIER ::= { enterprises 2668 }
solariDiUdine                     OBJECT IDENTIFIER ::= { enterprises 2669 }
netventure                        OBJECT IDENTIFIER ::= { enterprises 2670 }
connectedSystemsGroup             OBJECT IDENTIFIER ::= { enterprises 2671 }
corporateSoftwareAndTechnologies  OBJECT IDENTIFIER ::= { enterprises 2672 }
fibexSystems                      OBJECT IDENTIFIER ::= { enterprises 2673 }
claudeJardineDesign               OBJECT IDENTIFIER ::= { enterprises 2674 }
netMarketing                      OBJECT IDENTIFIER ::= { enterprises 2675 }
ibp                               OBJECT IDENTIFIER ::= { enterprises 2676 }
rd6                               OBJECT IDENTIFIER ::= { enterprises 2677 }
massmediaCommunications           OBJECT IDENTIFIER ::= { enterprises 2678 }
nexansSuisseSA                    OBJECT IDENTIFIER ::= { enterprises 2679 }
peakAudio                         OBJECT IDENTIFIER ::= { enterprises 2680 }
siaYiu                            OBJECT IDENTIFIER ::= { enterprises 2681 }
dps                               OBJECT IDENTIFIER ::= { enterprises 2682 }
callistoSoftware                  OBJECT IDENTIFIER ::= { enterprises 2683 }
viavideoCommunications            OBJECT IDENTIFIER ::= { enterprises 2684 }
sequelTechnologyCorporation       OBJECT IDENTIFIER ::= { enterprises 2685 }
wiLAN                             OBJECT IDENTIFIER ::= { enterprises 2686 }
networkSystemTechnologies         OBJECT IDENTIFIER ::= { enterprises 2687 }
centerTechnology                  OBJECT IDENTIFIER ::= { enterprises 2688 }
cobyRoberts                       OBJECT IDENTIFIER ::= { enterprises 2689 }
netronix                          OBJECT IDENTIFIER ::= { enterprises 2690 }
networkComputer                   OBJECT IDENTIFIER ::= { enterprises 2691 }
webweaving                        OBJECT IDENTIFIER ::= { enterprises 2692 }
institutJozefStefan               OBJECT IDENTIFIER ::= { enterprises 2693 }
eldatCommunication                OBJECT IDENTIFIER ::= { enterprises 2694 }
metacommunications                OBJECT IDENTIFIER ::= { enterprises 2695 }
digitalVideoBroadcasting          OBJECT IDENTIFIER ::= { enterprises 2696 }
baylyCommunications               OBJECT IDENTIFIER ::= { enterprises 2697 }
poznanSupercomputingAndNetworkingCenter OBJECT IDENTIFIER ::= { enterprises 2698 }
printerWorkingGroup               OBJECT IDENTIFIER ::= { enterprises 2699 }
directv                           OBJECT IDENTIFIER ::= { enterprises 2700 }
argonNetworks                     OBJECT IDENTIFIER ::= { enterprises 2701 }
wacos                             OBJECT IDENTIFIER ::= { enterprises 2702 }
objectZoneAB                      OBJECT IDENTIFIER ::= { enterprises 2703 }
icccAS                            OBJECT IDENTIFIER ::= { enterprises 2704 }
secudeGmbH                        OBJECT IDENTIFIER ::= { enterprises 2705 }
instituteForAppliedInformationProcessingAndCommunications OBJECT IDENTIFIER ::= { enterprises 2706 }
internationalNetworkServices      OBJECT IDENTIFIER ::= { enterprises 2707 }
jnrSystems                        OBJECT IDENTIFIER ::= { enterprises 2708 }
congreveComputing                 OBJECT IDENTIFIER ::= { enterprises 2709 }
northropGrummanSurveillanceAndBattleManagementSystems OBJECT IDENTIFIER ::= { enterprises 2710 }
littlewoodsStores                 OBJECT IDENTIFIER ::= { enterprises 2711 }
iceTELTLCA                        OBJECT IDENTIFIER ::= { enterprises 2712 }
mauswerks                         OBJECT IDENTIFIER ::= { enterprises 2713 }
depOfSignalTheoryAndCommunicationsUPC OBJECT IDENTIFIER ::= { enterprises 2714 }
zapexTechnologiesn                OBJECT IDENTIFIER ::= { enterprises 2715 }
glueckAndKanjaGmbH                OBJECT IDENTIFIER ::= { enterprises 2716 }
alcatelTelspace                   OBJECT IDENTIFIER ::= { enterprises 2717 }
intercall                         OBJECT IDENTIFIER ::= { enterprises 2718 }
townsendAnalytics                 OBJECT IDENTIFIER ::= { enterprises 2719 }
norcomInformationstechnologieUndUnternehmensberatungGmbH OBJECT IDENTIFIER ::= { enterprises 2720 }
newsInternetServices              OBJECT IDENTIFIER ::= { enterprises 2721 }
georgiaTechResearchInstitute      OBJECT IDENTIFIER ::= { enterprises 2722 }
guerrillaMail                     OBJECT IDENTIFIER ::= { enterprises 2723 }
easystreetOnlineServices          OBJECT IDENTIFIER ::= { enterprises 2724 }
artTechnologyGroup                OBJECT IDENTIFIER ::= { enterprises 2725 }
capitalOneFinancialCorp           OBJECT IDENTIFIER ::= { enterprises 2726 }
sfa                               OBJECT IDENTIFIER ::= { enterprises 2727 }
packardBellNEC                    OBJECT IDENTIFIER ::= { enterprises 2728 }
empireNet                         OBJECT IDENTIFIER ::= { enterprises 2729 }
ottosen                           OBJECT IDENTIFIER ::= { enterprises 2730 }
dialogdesign                      OBJECT IDENTIFIER ::= { enterprises 2731 }
innovativeDataTechnology          OBJECT IDENTIFIER ::= { enterprises 2732 }
group2000NederlandBv              OBJECT IDENTIFIER ::= { enterprises 2733 }
digitalLightwave                  OBJECT IDENTIFIER ::= { enterprises 2734 }
mibsRUS                           OBJECT IDENTIFIER ::= { enterprises 2735 }
etherwanSystems                   OBJECT IDENTIFIER ::= { enterprises 2736 }
cordlessTechnologyAS              OBJECT IDENTIFIER ::= { enterprises 2737 }
punjabCommunications              OBJECT IDENTIFIER ::= { enterprises 2738 }
tanstaaflConsulting               OBJECT IDENTIFIER ::= { enterprises 2739 }
simoco                            OBJECT IDENTIFIER ::= { enterprises 2740 }
calirnetSystems                   OBJECT IDENTIFIER ::= { enterprises 2741 }
managecom                         OBJECT IDENTIFIER ::= { enterprises 2742 }
rflElectronics                    OBJECT IDENTIFIER ::= { enterprises 2743 }
sarnoffRealTimeCorporation        OBJECT IDENTIFIER ::= { enterprises 2744 }
lancast                           OBJECT IDENTIFIER ::= { enterprises 2745 }
martinCommunications              OBJECT IDENTIFIER ::= { enterprises 2746 }
dirigSoftware                     OBJECT IDENTIFIER ::= { enterprises 2747 }
iclRetailSystemsEurope            OBJECT IDENTIFIER ::= { enterprises 2748 }
aptia                             OBJECT IDENTIFIER ::= { enterprises 2749 }
wavecomElectronics                OBJECT IDENTIFIER ::= { enterprises 2750 }
globalcastCommunications          OBJECT IDENTIFIER ::= { enterprises 2751 }
mccommInternationalBv             OBJECT IDENTIFIER ::= { enterprises 2752 }
argoDataResourceCorporation       OBJECT IDENTIFIER ::= { enterprises 2753 }
excelSwitchingCorporation         OBJECT IDENTIFIER ::= { enterprises 2754 }
palomarCommunications             OBJECT IDENTIFIER ::= { enterprises 2755 }
netstart                          OBJECT IDENTIFIER ::= { enterprises 2756 }
smartcommerceSolutions            OBJECT IDENTIFIER ::= { enterprises 2757 }
universalMicroApplications        OBJECT IDENTIFIER ::= { enterprises 2758 }
snsConsultants                    OBJECT IDENTIFIER ::= { enterprises 2759 }
enhancedMessagingSystem           OBJECT IDENTIFIER ::= { enterprises 2760 }
informaticaSpA                    OBJECT IDENTIFIER ::= { enterprises 2761 }
netgameLTD                        OBJECT IDENTIFIER ::= { enterprises 2762 }
intellinetTechnologies            OBJECT IDENTIFIER ::= { enterprises 2763 }
acxiomCorporation                 OBJECT IDENTIFIER ::= { enterprises 2764 }
dafurGmbH                         OBJECT IDENTIFIER ::= { enterprises 2765 }
platformComputingCorporation      OBJECT IDENTIFIER ::= { enterprises 2766 }
automotiveProductsPlc             OBJECT IDENTIFIER ::= { enterprises 2767 }
randdComputerServices             OBJECT IDENTIFIER ::= { enterprises 2768 }
knuerrAG                          OBJECT IDENTIFIER ::= { enterprises 2769 }
eurotelPrahaSro                   OBJECT IDENTIFIER ::= { enterprises 2770 }
inlabSoftwareGmbH                 OBJECT IDENTIFIER ::= { enterprises 2771 }
intersolveTechnologies            OBJECT IDENTIFIER ::= { enterprises 2772 }
redstoneCommunications            OBJECT IDENTIFIER ::= { enterprises 2773 }
algorithmicResearch               OBJECT IDENTIFIER ::= { enterprises 2774 }
agtInternational                  OBJECT IDENTIFIER ::= { enterprises 2775 }
fourthtrackSystems                OBJECT IDENTIFIER ::= { enterprises 2776 }
flextelSpa                        OBJECT IDENTIFIER ::= { enterprises 2777 }
warpspeedComputers                OBJECT IDENTIFIER ::= { enterprises 2778 }
c3                                OBJECT IDENTIFIER ::= { enterprises 2779 }
neoNetworks                       OBJECT IDENTIFIER ::= { enterprises 2780 }
technicalUniversityOfMadrid       OBJECT IDENTIFIER ::= { enterprises 2781 }
bomComputerServices               OBJECT IDENTIFIER ::= { enterprises 2782 }
controlSystemsInternational       OBJECT IDENTIFIER ::= { enterprises 2783 }
bbcomBroadbandCommunicationsGmbHAndCoKG OBJECT IDENTIFIER ::= { enterprises 2784 }
tecnoproSA                        OBJECT IDENTIFIER ::= { enterprises 2785 }
politecnicoDiTorino               OBJECT IDENTIFIER ::= { enterprises 2786 }
ingGroup                          OBJECT IDENTIFIER ::= { enterprises 2787 }
wytec                             OBJECT IDENTIFIER ::= { enterprises 2788 }
mauroEnterprise                   OBJECT IDENTIFIER ::= { enterprises 2789 }
roadrunner                        OBJECT IDENTIFIER ::= { enterprises 2790 }
deterministicNetworks             OBJECT IDENTIFIER ::= { enterprises 2791 }
sprintPCS                         OBJECT IDENTIFIER ::= { enterprises 2792 }
interactiveIntelligence           OBJECT IDENTIFIER ::= { enterprises 2793 }
jaycor                            OBJECT IDENTIFIER ::= { enterprises 2794 }
edifyCorporation                  OBJECT IDENTIFIER ::= { enterprises 2795 }
ultracomp                         OBJECT IDENTIFIER ::= { enterprises 2796 }
universityOfPennsylvania          OBJECT IDENTIFIER ::= { enterprises 2797 }
metawaveCommunicationsCorp        OBJECT IDENTIFIER ::= { enterprises 2798 }
enterpriseSolutions               OBJECT IDENTIFIER ::= { enterprises 2799 }
cblGmbH                           OBJECT IDENTIFIER ::= { enterprises 2800 }
adpDealerServices                 OBJECT IDENTIFIER ::= { enterprises 2801 }
efkon                             OBJECT IDENTIFIER ::= { enterprises 2802 }
sicanGmbH                         OBJECT IDENTIFIER ::= { enterprises 2803 }
keytrend                          OBJECT IDENTIFIER ::= { enterprises 2804 }
accTelEnterprises                 OBJECT IDENTIFIER ::= { enterprises 2805 }
eba                               OBJECT IDENTIFIER ::= { enterprises 2806 }
telewareCo                        OBJECT IDENTIFIER ::= { enterprises 2807 }
efusion                           OBJECT IDENTIFIER ::= { enterprises 2808 }
participantsTrustCompany          OBJECT IDENTIFIER ::= { enterprises 2809 }
peoplesoft                        OBJECT IDENTIFIER ::= { enterprises 2810 }
entrataCommunication              OBJECT IDENTIFIER ::= { enterprises 2811 }
musicscom                         OBJECT IDENTIFIER ::= { enterprises 2812 }
firstTelecomPlc                   OBJECT IDENTIFIER ::= { enterprises 2813 }
telesnapGmbH                      OBJECT IDENTIFIER ::= { enterprises 2814 }
newpointTechnologies              OBJECT IDENTIFIER ::= { enterprises 2815 }
tAnde                             OBJECT IDENTIFIER ::= { enterprises 2816 }
disneyRegionalEntertainment       OBJECT IDENTIFIER ::= { enterprises 2817 }
rampNetworks                      OBJECT IDENTIFIER ::= { enterprises 2818 }
openSoftwareAssociates            OBJECT IDENTIFIER ::= { enterprises 2819 }
procomTechnology                  OBJECT IDENTIFIER ::= { enterprises 2820 }
universityOfNotreDame             OBJECT IDENTIFIER ::= { enterprises 2821 }
arquitecturaAnimada               OBJECT IDENTIFIER ::= { enterprises 2822 }
sumbhaHologramsAndPackagingSystems OBJECT IDENTIFIER ::= { enterprises 2823 }
theAConsultingTeam                OBJECT IDENTIFIER ::= { enterprises 2824 }
worldgateCommunications           OBJECT IDENTIFIER ::= { enterprises 2825 }
toaElectronics                    OBJECT IDENTIFIER ::= { enterprises 2826 }
sytexSystemsCorp                  OBJECT IDENTIFIER ::= { enterprises 2827 }
zellDistributors                  OBJECT IDENTIFIER ::= { enterprises 2828 }
yrlessInternetCorporation         OBJECT IDENTIFIER ::= { enterprises 2829 }
haloTechnologies                  OBJECT IDENTIFIER ::= { enterprises 2830 }
beijingUnivOfPostsAndTelecom      OBJECT IDENTIFIER ::= { enterprises 2831 }
virtualDataSystems                OBJECT IDENTIFIER ::= { enterprises 2832 }
netdox                            OBJECT IDENTIFIER ::= { enterprises 2833 }
expertComputerService             OBJECT IDENTIFIER ::= { enterprises 2834 }
dictaphone                        OBJECT IDENTIFIER ::= { enterprises 2835 }
unexTechnologyCorporation         OBJECT IDENTIFIER ::= { enterprises 2836 }
globalMobilitySystems             OBJECT IDENTIFIER ::= { enterprises 2837 }
tfmAssociates                     OBJECT IDENTIFIER ::= { enterprises 2838 }
teleranTechnologies               OBJECT IDENTIFIER ::= { enterprises 2839 }
digitalTelecommunications         OBJECT IDENTIFIER ::= { enterprises 2840 }
kbInternet                        OBJECT IDENTIFIER ::= { enterprises 2841 }
agriDatalog                       OBJECT IDENTIFIER ::= { enterprises 2842 }
braidSystemsLimited               OBJECT IDENTIFIER ::= { enterprises 2843 }
newsnetITN                        OBJECT IDENTIFIER ::= { enterprises 2844 }
jtcs                              OBJECT IDENTIFIER ::= { enterprises 2845 }
keycorpPty                        OBJECT IDENTIFIER ::= { enterprises 2846 }
gteInternetworking                OBJECT IDENTIFIER ::= { enterprises 2847 }
royalblueTechnologiesPlcTrevorGoffTrevorGoff OBJECT IDENTIFIER ::= { enterprises 2848 }
uAndrConsultoresArgentina         OBJECT IDENTIFIER ::= { enterprises 2849 }
tevycomFapecoSA                   OBJECT IDENTIFIER ::= { enterprises 2850 }
polarisCommunications             OBJECT IDENTIFIER ::= { enterprises 2851 }
competitiveAutomation             OBJECT IDENTIFIER ::= { enterprises 2852 }
idexxSoftwareDivision             OBJECT IDENTIFIER ::= { enterprises 2853 }
networkComputingTechnologies      OBJECT IDENTIFIER ::= { enterprises 2854 }
integrityCommunications           OBJECT IDENTIFIER ::= { enterprises 2855 }
cablewareElectronics              OBJECT IDENTIFIER ::= { enterprises 2856 }
networkPowerAndLight              OBJECT IDENTIFIER ::= { enterprises 2857 }
clarentCorporation                OBJECT IDENTIFIER ::= { enterprises 2858 }
kingstonSCL                       OBJECT IDENTIFIER ::= { enterprises 2859 }
netvest                           OBJECT IDENTIFIER ::= { enterprises 2860 }
vsnSystemenBV                     OBJECT IDENTIFIER ::= { enterprises 2861 }
northwestConsultingServices       OBJECT IDENTIFIER ::= { enterprises 2862 }
thomsonConsumerElectronics        OBJECT IDENTIFIER ::= { enterprises 2863 }
digitelSAIndustriaEletronica      OBJECT IDENTIFIER ::= { enterprises 2864 }
cambrianSystemsCorp               OBJECT IDENTIFIER ::= { enterprises 2865 }
technicalInsights                 OBJECT IDENTIFIER ::= { enterprises 2866 }
nkfElectronics                    OBJECT IDENTIFIER ::= { enterprises 2867 }
glasshouseBusinessNetworksBV      OBJECT IDENTIFIER ::= { enterprises 2868 }
vsiEnterprises                    OBJECT IDENTIFIER ::= { enterprises 2869 }
eTECH                             OBJECT IDENTIFIER ::= { enterprises 2870 }
metainfo                          OBJECT IDENTIFIER ::= { enterprises 2871 }
unisourceBusinessNetworksNederlandBv OBJECT IDENTIFIER ::= { enterprises 2872 }
agentics                          OBJECT IDENTIFIER ::= { enterprises 2873 }
otcTelecom                        OBJECT IDENTIFIER ::= { enterprises 2874 }
guidevInternational               OBJECT IDENTIFIER ::= { enterprises 2875 }
cothernComputerSystems            OBJECT IDENTIFIER ::= { enterprises 2876 }
arbinetCommunications             OBJECT IDENTIFIER ::= { enterprises 2877 }
faxforwardCanada                  OBJECT IDENTIFIER ::= { enterprises 2878 }
sonusNetworks                     OBJECT IDENTIFIER ::= { enterprises 2879 }
iphighway                         OBJECT IDENTIFIER ::= { enterprises 2880 }
clarion                           OBJECT IDENTIFIER ::= { enterprises 2881 }
comtrolCorporation                OBJECT IDENTIFIER ::= { enterprises 2882 }
coherentCommunicationsSystems     OBJECT IDENTIFIER ::= { enterprises 2883 }
adsNetworks                       OBJECT IDENTIFIER ::= { enterprises 2884 }
chicagoSoft                       OBJECT IDENTIFIER ::= { enterprises 2885 }
netbalance                        OBJECT IDENTIFIER ::= { enterprises 2886 }
asProekspert                      OBJECT IDENTIFIER ::= { enterprises 2887 }
adfmMultimediaInternet            OBJECT IDENTIFIER ::= { enterprises 2888 }
praxisInternational               OBJECT IDENTIFIER ::= { enterprises 2889 }
solectekCorporation               OBJECT IDENTIFIER ::= { enterprises 2890 }
nanospace                         OBJECT IDENTIFIER ::= { enterprises 2891 }
kaps                              OBJECT IDENTIFIER ::= { enterprises 2892 }
computerAssociates                OBJECT IDENTIFIER ::= { enterprises 2893 }
mainsailNetworks                  OBJECT IDENTIFIER ::= { enterprises 2894 }
eds                               OBJECT IDENTIFIER ::= { enterprises 2895 }
breeceHillTechnologies            OBJECT IDENTIFIER ::= { enterprises 2896 }
atAndtCapitalCorpErnest           OBJECT IDENTIFIER ::= { enterprises 2897 }
highgroundSystems                 OBJECT IDENTIFIER ::= { enterprises 2898 }
omniaCommunications               OBJECT IDENTIFIER ::= { enterprises 2899 }
merTelemanagementSolutions        OBJECT IDENTIFIER ::= { enterprises 2900 }
replicase                         OBJECT IDENTIFIER ::= { enterprises 2901 }
micrologCorporation               OBJECT IDENTIFIER ::= { enterprises 2902 }
smartwaysTechnologyLimited        OBJECT IDENTIFIER ::= { enterprises 2903 }
computerServices                  OBJECT IDENTIFIER ::= { enterprises 2904 }
trumpetSoftwareInternationalPty   OBJECT IDENTIFIER ::= { enterprises 2905 }
rsiSolutions                      OBJECT IDENTIFIER ::= { enterprises 2906 }
cCorElectronics                   OBJECT IDENTIFIER ::= { enterprises 2907 }
castleNetworks                    OBJECT IDENTIFIER ::= { enterprises 2908 }
nexabitNetworks                   OBJECT IDENTIFIER ::= { enterprises 2909 }
generalElectricCompany            OBJECT IDENTIFIER ::= { enterprises 2910 }
objectiveSoftwareServices         OBJECT IDENTIFIER ::= { enterprises 2911 }
ameristarTechnologiesCorp         OBJECT IDENTIFIER ::= { enterprises 2912 }
hycorBiomedical                   OBJECT IDENTIFIER ::= { enterprises 2913 }
fellesdataAS                      OBJECT IDENTIFIER ::= { enterprises 2914 }
networkEngines                    OBJECT IDENTIFIER ::= { enterprises 2915 }
daimlerBenzAG                     OBJECT IDENTIFIER ::= { enterprises 2916 }
dataInterfaceSystemsCorp          OBJECT IDENTIFIER ::= { enterprises 2917 }
symmetryCommunicationsSystems     OBJECT IDENTIFIER ::= { enterprises 2918 }
rambusCorp                        OBJECT IDENTIFIER ::= { enterprises 2919 }
willDoInformationServices         OBJECT IDENTIFIER ::= { enterprises 2920 }
swissPharmaContract               OBJECT IDENTIFIER ::= { enterprises 2921 }
iOCorporation                     OBJECT IDENTIFIER ::= { enterprises 2922 }
formulaConsultants                OBJECT IDENTIFIER ::= { enterprises 2923 }
starTV                            OBJECT IDENTIFIER ::= { enterprises 2924 }
cycladesCorporation               OBJECT IDENTIFIER ::= { enterprises 2925 }
sonomaSystems                     OBJECT IDENTIFIER ::= { enterprises 2926 }
jacksonvilleElectricAuthority     OBJECT IDENTIFIER ::= { enterprises 2927 }
netInsightAB                      OBJECT IDENTIFIER ::= { enterprises 2928 }
quallaby                          OBJECT IDENTIFIER ::= { enterprises 2929 }
valicert                          OBJECT IDENTIFIER ::= { enterprises 2930 }
gadcNetworks                      OBJECT IDENTIFIER ::= { enterprises 2931 }
termaElektronikAS                 OBJECT IDENTIFIER ::= { enterprises 2932 }
flowareSystemSolutions            OBJECT IDENTIFIER ::= { enterprises 2933 }
citicorp                          OBJECT IDENTIFIER ::= { enterprises 2934 }
pathlightTechnology               OBJECT IDENTIFIER ::= { enterprises 2935 }
prominenceDotCom                  OBJECT IDENTIFIER ::= { enterprises 2936 }
deutscheTelekomAG                 OBJECT IDENTIFIER ::= { enterprises 2937 }
proginetCorporation               OBJECT IDENTIFIER ::= { enterprises 2938 }
infoexpress                       OBJECT IDENTIFIER ::= { enterprises 2939 }
argentSoftware                    OBJECT IDENTIFIER ::= { enterprises 2940 }
readycom                          OBJECT IDENTIFIER ::= { enterprises 2941 }
cocomAS                           OBJECT IDENTIFIER ::= { enterprises 2942 }
objtechSoftware                   OBJECT IDENTIFIER ::= { enterprises 2943 }
topLayerNetworks                  OBJECT IDENTIFIER ::= { enterprises 2944 }
tdsoftCommunicationsSoftware      OBJECT IDENTIFIER ::= { enterprises 2945 }
switch                            OBJECT IDENTIFIER ::= { enterprises 2946 }
bestPower                         OBJECT IDENTIFIER ::= { enterprises 2947 }
telesuiteCorporation              OBJECT IDENTIFIER ::= { enterprises 2948 }
globalQuestConsaltance            OBJECT IDENTIFIER ::= { enterprises 2949 }
ampersand                         OBJECT IDENTIFIER ::= { enterprises 2950 }
nentec                            OBJECT IDENTIFIER ::= { enterprises 2951 }
tAndeSoft                         OBJECT IDENTIFIER ::= { enterprises 2952 }
imedia                            OBJECT IDENTIFIER ::= { enterprises 2953 }
universitaetBielefeld             OBJECT IDENTIFIER ::= { enterprises 2954 }
psinetUK                          OBJECT IDENTIFIER ::= { enterprises 2955 }
infolibria                        OBJECT IDENTIFIER ::= { enterprises 2956 }
ericssonCommunications            OBJECT IDENTIFIER ::= { enterprises 2957 }
secureNetworkSolutions            OBJECT IDENTIFIER ::= { enterprises 2958 }
workstationSolutions              OBJECT IDENTIFIER ::= { enterprises 2959 }
nationalLandscapeAssn             OBJECT IDENTIFIER ::= { enterprises 2960 }
dialogsSoftwareGmbH               OBJECT IDENTIFIER ::= { enterprises 2961 }
netwiseBNAB                       OBJECT IDENTIFIER ::= { enterprises 2962 }
securityDynamicsTechnology        OBJECT IDENTIFIER ::= { enterprises 2963 }
zetaCommunications                OBJECT IDENTIFIER ::= { enterprises 2964 }
syscom                            OBJECT IDENTIFIER ::= { enterprises 2965 }
digitalChoreoGraphics             OBJECT IDENTIFIER ::= { enterprises 2966 }
cabledata                         OBJECT IDENTIFIER ::= { enterprises 2967 }
allenTelecomSystems               OBJECT IDENTIFIER ::= { enterprises 2968 }
charlesCraft                      OBJECT IDENTIFIER ::= { enterprises 2969 }
sunstoneEnterprises               OBJECT IDENTIFIER ::= { enterprises 2970 }
medialincsCo                      OBJECT IDENTIFIER ::= { enterprises 2971 }
networkAlchemy                    OBJECT IDENTIFIER ::= { enterprises 2972 }
integralAccess                    OBJECT IDENTIFIER ::= { enterprises 2973 }
ipMetricsSoftware                 OBJECT IDENTIFIER ::= { enterprises 2974 }
notariusTSIN                      OBJECT IDENTIFIER ::= { enterprises 2975 }
philipsMultimediaNetworkSystemsGmbH OBJECT IDENTIFIER ::= { enterprises 2976 }
teubnerAndAssociates              OBJECT IDENTIFIER ::= { enterprises 2977 }
imagecom                          OBJECT IDENTIFIER ::= { enterprises 2978 }
waveriderCommunications           OBJECT IDENTIFIER ::= { enterprises 2979 }
entEmpresaNacionalDeTelecomunicacoes OBJECT IDENTIFIER ::= { enterprises 2980 }
dukeEnergy                        OBJECT IDENTIFIER ::= { enterprises 2981 }
deutschesPatentamt                OBJECT IDENTIFIER ::= { enterprises 2982 }
semaGroupGmbH                     OBJECT IDENTIFIER ::= { enterprises 2983 }
keycodeStyle                      OBJECT IDENTIFIER ::= { enterprises 2984 }
baySystemsConsulting              OBJECT IDENTIFIER ::= { enterprises 2985 }
qiangjinCorp                      OBJECT IDENTIFIER ::= { enterprises 2986 }
ipivot                            OBJECT IDENTIFIER ::= { enterprises 2987 }
consultronicsDevelopment          OBJECT IDENTIFIER ::= { enterprises 2988 }
universityOfNorthLondon           OBJECT IDENTIFIER ::= { enterprises 2989 }
illuminata                        OBJECT IDENTIFIER ::= { enterprises 2990 }
enterpriseIT                      OBJECT IDENTIFIER ::= { enterprises 2991 }
cybertel                          OBJECT IDENTIFIER ::= { enterprises 2992 }
convergenetTechnologies           OBJECT IDENTIFIER ::= { enterprises 2993 }
teligent                          OBJECT IDENTIFIER ::= { enterprises 2994 }
acucomm                           OBJECT IDENTIFIER ::= { enterprises 2995 }
spectraworks                      OBJECT IDENTIFIER ::= { enterprises 2996 }
redtitan                          OBJECT IDENTIFIER ::= { enterprises 2997 }
andersonConsulting                OBJECT IDENTIFIER ::= { enterprises 2998 }
americanFamilyInsurance           OBJECT IDENTIFIER ::= { enterprises 2999 }
idbSystems                        OBJECT IDENTIFIER ::= { enterprises 3000 }
bailo                             OBJECT IDENTIFIER ::= { enterprises 3001 }
adaxisGroup                       OBJECT IDENTIFIER ::= { enterprises 3002 }
packetEngines                     OBJECT IDENTIFIER ::= { enterprises 3003 }
softwireCorporation               OBJECT IDENTIFIER ::= { enterprises 3004 }
tds                               OBJECT IDENTIFIER ::= { enterprises 3005 }
hciTechnologies                   OBJECT IDENTIFIER ::= { enterprises 3006 }
topcallInternational              OBJECT IDENTIFIER ::= { enterprises 3007 }
openService                       OBJECT IDENTIFIER ::= { enterprises 3008 }
aichiElectronicsCo                OBJECT IDENTIFIER ::= { enterprises 3009 }
universityOfAizu                  OBJECT IDENTIFIER ::= { enterprises 3010 }
videoserver                       OBJECT IDENTIFIER ::= { enterprises 3011 }
spaceAndTelecommunicationsSystemsPte OBJECT IDENTIFIER ::= { enterprises 3012 }
bicolInfonetSystem                OBJECT IDENTIFIER ::= { enterprises 3013 }
mediasoftTelecom                  OBJECT IDENTIFIER ::= { enterprises 3014 }
netproComputing2                  OBJECT IDENTIFIER ::= { enterprises 3015 }
ozemail                           OBJECT IDENTIFIER ::= { enterprises 3016 }
arcxelTechnologies                OBJECT IDENTIFIER ::= { enterprises 3017 }
enternetCorporation               OBJECT IDENTIFIER ::= { enterprises 3018 }
jonesWaldoHolbrookMcDonough       OBJECT IDENTIFIER ::= { enterprises 3019 }
universityAccess                  OBJECT IDENTIFIER ::= { enterprises 3020 }
senditAB                          OBJECT IDENTIFIER ::= { enterprises 3021 }
telecomSciencesCorporationLimited OBJECT IDENTIFIER ::= { enterprises 3022 }
qualityQuorm                      OBJECT IDENTIFIER ::= { enterprises 3023 }
grapevineSystems                  OBJECT IDENTIFIER ::= { enterprises 3024 }
thePandaProject                   OBJECT IDENTIFIER ::= { enterprises 3025 }
missionControlDevelopment         OBJECT IDENTIFIER ::= { enterprises 3026 }
ionaTechnologies                  OBJECT IDENTIFIER ::= { enterprises 3027 }
dialogicCorporation               OBJECT IDENTIFIER ::= { enterprises 3028 }
digitalDataSecurity               OBJECT IDENTIFIER ::= { enterprises 3029 }
iscni                             OBJECT IDENTIFIER ::= { enterprises 3030 }
daocon                            OBJECT IDENTIFIER ::= { enterprises 3031 }
beaufortMemorialHospital          OBJECT IDENTIFIER ::= { enterprises 3032 }
informationstechnikDrHansmeyer    OBJECT IDENTIFIER ::= { enterprises 3033 }
urmetSUDSpa                       OBJECT IDENTIFIER ::= { enterprises 3034 }
avestaTechnologies                OBJECT IDENTIFIER ::= { enterprises 3035 }
hyundaiElectronicsAmerica         OBJECT IDENTIFIER ::= { enterprises 3036 }
dmv                               OBJECT IDENTIFIER ::= { enterprises 3037 }
faxInternational                  OBJECT IDENTIFIER ::= { enterprises 3038 }
midamericanEnergyCompany          OBJECT IDENTIFIER ::= { enterprises 3039 }
bellsouthnet                      OBJECT IDENTIFIER ::= { enterprises 3040 }
assuredAccessTechnology           OBJECT IDENTIFIER ::= { enterprises 3041 }
logiconEagleTechnology            OBJECT IDENTIFIER ::= { enterprises 3042 }
frequentisNachrichtentechnikGesmbH OBJECT IDENTIFIER ::= { enterprises 3043 }
isis2000                          OBJECT IDENTIFIER ::= { enterprises 3044 }
jamesEGray                        OBJECT IDENTIFIER ::= { enterprises 3045 }
jamaicaCableTVAndInternetServices OBJECT IDENTIFIER ::= { enterprises 3046 }
informationTechnologyConsultantsPty OBJECT IDENTIFIER ::= { enterprises 3047 }
linickgrpcom                      OBJECT IDENTIFIER ::= { enterprises 3048 }
yankeeKnowHow                     OBJECT IDENTIFIER ::= { enterprises 3049 }
seahGroup                         OBJECT IDENTIFIER ::= { enterprises 3050 }
cincoNetworks                     OBJECT IDENTIFIER ::= { enterprises 3051 }
omnitronix                        OBJECT IDENTIFIER ::= { enterprises 3052 }
genieTelecommunication            OBJECT IDENTIFIER ::= { enterprises 3053 }
ixiaCommunications                OBJECT IDENTIFIER ::= { enterprises 3054 }
transmetaCorporation              OBJECT IDENTIFIER ::= { enterprises 3055 }
systemsoftCorp                    OBJECT IDENTIFIER ::= { enterprises 3056 }
jaspalMiracles                    OBJECT IDENTIFIER ::= { enterprises 3057 }
debisSystemhaus                   OBJECT IDENTIFIER ::= { enterprises 3058 }
sislerPromotions                  OBJECT IDENTIFIER ::= { enterprises 3059 }
iceManRefrigeration               OBJECT IDENTIFIER ::= { enterprises 3060 }
listingServiceSolutions           OBJECT IDENTIFIER ::= { enterprises 3061 }
jovianNetworks                    OBJECT IDENTIFIER ::= { enterprises 3062 }
elebraComDados                    OBJECT IDENTIFIER ::= { enterprises 3063 }
safetranSystems                   OBJECT IDENTIFIER ::= { enterprises 3064 }
objectiveCommunicaitons           OBJECT IDENTIFIER ::= { enterprises 3065 }
phasecom                          OBJECT IDENTIFIER ::= { enterprises 3066 }
eurocontrol                       OBJECT IDENTIFIER ::= { enterprises 3067 }
silverstreamSoftware              OBJECT IDENTIFIER ::= { enterprises 3068 }
cownet                            OBJECT IDENTIFIER ::= { enterprises 3069 }
worldAccess                       OBJECT IDENTIFIER ::= { enterprises 3070 }
virtualLineLLP                    OBJECT IDENTIFIER ::= { enterprises 3071 }
integratedConceptsLLP             OBJECT IDENTIFIER ::= { enterprises 3072 }
exabyteCorporation                OBJECT IDENTIFIER ::= { enterprises 3073 }
interactiveMediaCorporation       OBJECT IDENTIFIER ::= { enterprises 3074 }
netcoreSystems                    OBJECT IDENTIFIER ::= { enterprises 3075 }
altigaNetworks                    OBJECT IDENTIFIER ::= { enterprises 3076 }
nationalCenterForSupercomputingApplications OBJECT IDENTIFIER ::= { enterprises 3077 }
emass                             OBJECT IDENTIFIER ::= { enterprises 3078 }
primaTelematic                    OBJECT IDENTIFIER ::= { enterprises 3079 }
backwebTechnologies               OBJECT IDENTIFIER ::= { enterprises 3080 }
ntpSoftware                       OBJECT IDENTIFIER ::= { enterprises 3081 }
pbsAS                             OBJECT IDENTIFIER ::= { enterprises 3082 }
wquinnAssociates                  OBJECT IDENTIFIER ::= { enterprises 3083 }
quza                              OBJECT IDENTIFIER ::= { enterprises 3084 }
cosineCommunications              OBJECT IDENTIFIER ::= { enterprises 3085 }
pipelinks                         OBJECT IDENTIFIER ::= { enterprises 3086 }
wailanCommunications              OBJECT IDENTIFIER ::= { enterprises 3087 }
axentTechnologies                 OBJECT IDENTIFIER ::= { enterprises 3088 }
spawar                            OBJECT IDENTIFIER ::= { enterprises 3089 }
airsysATMSA                       OBJECT IDENTIFIER ::= { enterprises 3090 }
whiterMornSoftware                OBJECT IDENTIFIER ::= { enterprises 3091 }
entv                              OBJECT IDENTIFIER ::= { enterprises 3092 }
cybertanTechnology                OBJECT IDENTIFIER ::= { enterprises 3093 }
frilot                            OBJECT IDENTIFIER ::= { enterprises 3094 }
firstsenseSoftware                OBJECT IDENTIFIER ::= { enterprises 3095 }
starvox                           OBJECT IDENTIFIER ::= { enterprises 3096 }
watchguardTechnologies            OBJECT IDENTIFIER ::= { enterprises 3097 }
mtiTechnologyCorporation          OBJECT IDENTIFIER ::= { enterprises 3098 }
lumbrera                          OBJECT IDENTIFIER ::= { enterprises 3099 }
celogic                           OBJECT IDENTIFIER ::= { enterprises 3100 }
experianInformationSolutions      OBJECT IDENTIFIER ::= { enterprises 3101 }
kansaiElectricCo                  OBJECT IDENTIFIER ::= { enterprises 3102 }
innet                             OBJECT IDENTIFIER ::= { enterprises 3103 }
selVerteidigungssystemeGmbH       OBJECT IDENTIFIER ::= { enterprises 3104 }
europolitanAB                     OBJECT IDENTIFIER ::= { enterprises 3105 }
lciInternational                  OBJECT IDENTIFIER ::= { enterprises 3106 }
cityOfLosAngeles                  OBJECT IDENTIFIER ::= { enterprises 3107 }
g2Networks                        OBJECT IDENTIFIER ::= { enterprises 3108 }
tradewebLLC                       OBJECT IDENTIFIER ::= { enterprises 3109 }
rafael                            OBJECT IDENTIFIER ::= { enterprises 3110 }
crystalGroup                      OBJECT IDENTIFIER ::= { enterprises 3111 }
cBridgeInternetSolutions          OBJECT IDENTIFIER ::= { enterprises 3112 }
phaseForward                      OBJECT IDENTIFIER ::= { enterprises 3113 }
wonoa                             OBJECT IDENTIFIER ::= { enterprises 3114 }
dialog                            OBJECT IDENTIFIER ::= { enterprises 3115 }
racalRecordersLimited             OBJECT IDENTIFIER ::= { enterprises 3116 }
eTRADEGroup                       OBJECT IDENTIFIER ::= { enterprises 3117 }
junoOnlineServices                OBJECT IDENTIFIER ::= { enterprises 3118 }
dnbASA                            OBJECT IDENTIFIER ::= { enterprises 3119 }
cintelTechnologies                OBJECT IDENTIFIER ::= { enterprises 3120 }
tele1024Denmark                   OBJECT IDENTIFIER ::= { enterprises 3121 }
interlinkNetworkGroup             OBJECT IDENTIFIER ::= { enterprises 3122 }
lRichards                         OBJECT IDENTIFIER ::= { enterprises 3123 }
mediaCommunicationsEurAB          OBJECT IDENTIFIER ::= { enterprises 3124 }
rocxSoftwareCorp                  OBJECT IDENTIFIER ::= { enterprises 3125 }
ardaxSystems                      OBJECT IDENTIFIER ::= { enterprises 3126 }
pluris                            OBJECT IDENTIFIER ::= { enterprises 3127 }
oazCommunications                 OBJECT IDENTIFIER ::= { enterprises 3128 }
advancedSwitchingCommunications   OBJECT IDENTIFIER ::= { enterprises 3129 }
greatlinkNetworks                 OBJECT IDENTIFIER ::= { enterprises 3130 }
aydinTelecom                      OBJECT IDENTIFIER ::= { enterprises 3131 }
netkit                            OBJECT IDENTIFIER ::= { enterprises 3132 }
idp                               OBJECT IDENTIFIER ::= { enterprises 3133 }
ttmNederland                      OBJECT IDENTIFIER ::= { enterprises 3134 }
labouchere                        OBJECT IDENTIFIER ::= { enterprises 3135 }
comtrendCORPORATION               OBJECT IDENTIFIER ::= { enterprises 3136 }
berbeeInformationNetworksCorp     OBJECT IDENTIFIER ::= { enterprises 3137 }
wirelessOnline                    OBJECT IDENTIFIER ::= { enterprises 3138 }
liffe                             OBJECT IDENTIFIER ::= { enterprises 3139 }
celoCommunicationsAB              OBJECT IDENTIFIER ::= { enterprises 3140 }
markIVIndustries                  OBJECT IDENTIFIER ::= { enterprises 3141 }
leitchTechnologyInternational     OBJECT IDENTIFIER ::= { enterprises 3142 }
chalcroftInternational            OBJECT IDENTIFIER ::= { enterprises 3143 }
clarityWireless                   OBJECT IDENTIFIER ::= { enterprises 3144 }
cCCTechnology                     OBJECT IDENTIFIER ::= { enterprises 3145 }
frequentisNetworkSystemsGmbH      OBJECT IDENTIFIER ::= { enterprises 3146 }
daewooElectronics                 OBJECT IDENTIFIER ::= { enterprises 3147 }
franceCaraibeMobiles              OBJECT IDENTIFIER ::= { enterprises 3148 }
winchesterSystems                 OBJECT IDENTIFIER ::= { enterprises 3149 }
swd                               OBJECT IDENTIFIER ::= { enterprises 3150 }
automotiveIndustryActionGroup     OBJECT IDENTIFIER ::= { enterprises 3151 }
orionTechnologies                 OBJECT IDENTIFIER ::= { enterprises 3152 }
directorynet                      OBJECT IDENTIFIER ::= { enterprises 3153 }
kisanTelecomCo                    OBJECT IDENTIFIER ::= { enterprises 3154 }
concordEracom                     OBJECT IDENTIFIER ::= { enterprises 3155 }
secant                            OBJECT IDENTIFIER ::= { enterprises 3156 }
netracorp                         OBJECT IDENTIFIER ::= { enterprises 3157 }
masproDENKOHCorp                  OBJECT IDENTIFIER ::= { enterprises 3158 }
utimacoSafewareAG                 OBJECT IDENTIFIER ::= { enterprises 3159 }
financialInformationSystemCenter  OBJECT IDENTIFIER ::= { enterprises 3160 }
xybx                              OBJECT IDENTIFIER ::= { enterprises 3161 }
relationalDataSystems             OBJECT IDENTIFIER ::= { enterprises 3162 }
mAndtClearSolutions               OBJECT IDENTIFIER ::= { enterprises 3163 }
arbedSA                           OBJECT IDENTIFIER ::= { enterprises 3164 }
capGeminiTelecom                  OBJECT IDENTIFIER ::= { enterprises 3165 }
westekTechnology                  OBJECT IDENTIFIER ::= { enterprises 3166 }
niceSystems                       OBJECT IDENTIFIER ::= { enterprises 3167 }
incSA                             OBJECT IDENTIFIER ::= { enterprises 3168 }
silisSarl                         OBJECT IDENTIFIER ::= { enterprises 3169 }
interworkingLabs                  OBJECT IDENTIFIER ::= { enterprises 3170 }
ikonSystems                       OBJECT IDENTIFIER ::= { enterprises 3171 }
gteIntelligentNetworkServices     OBJECT IDENTIFIER ::= { enterprises 3172 }
turnstoneSystems                  OBJECT IDENTIFIER ::= { enterprises 3173 }
tiaraNetworks                     OBJECT IDENTIFIER ::= { enterprises 3174 }
webtrendsCorporation              OBJECT IDENTIFIER ::= { enterprises 3175 }
wernerTrainingAndConsulting       OBJECT IDENTIFIER ::= { enterprises 3176 }
ivc                               OBJECT IDENTIFIER ::= { enterprises 3177 }
blueCrossAndBlueShieldOfFlorida   OBJECT IDENTIFIER ::= { enterprises 3178 }
level8Systems                     OBJECT IDENTIFIER ::= { enterprises 3179 }
rescomAS                          OBJECT IDENTIFIER ::= { enterprises 3180 }
microsensGmbHAndCoKG              OBJECT IDENTIFIER ::= { enterprises 3181 }
uniholdTechnologies               OBJECT IDENTIFIER ::= { enterprises 3182 }
wiredForManagement                OBJECT IDENTIFIER ::= { enterprises 3183 }
raymondAndLaeEngineering          OBJECT IDENTIFIER ::= { enterprises 3184 }
parapscoDesigns                   OBJECT IDENTIFIER ::= { enterprises 3185 }
touchnetInformationSystems        OBJECT IDENTIFIER ::= { enterprises 3186 }
fuzzyInformatikGmbH              OBJECT IDENTIFIER ::= { enterprises 3187 }
sunnyComm                         OBJECT IDENTIFIER ::= { enterprises 3188 }
dsdComputing                      OBJECT IDENTIFIER ::= { enterprises 3189 }
cajaDeAhorrosDelMediterraneo      OBJECT IDENTIFIER ::= { enterprises 3190 }
dynetcomGuernsey                  OBJECT IDENTIFIER ::= { enterprises 3191 }
tachyon                           OBJECT IDENTIFIER ::= { enterprises 3192 }
silentCommunications              OBJECT IDENTIFIER ::= { enterprises 3193 }
effnetAB                          OBJECT IDENTIFIER ::= { enterprises 3194 }
audiAG                            OBJECT IDENTIFIER ::= { enterprises 3195 }
sideBySideGmbH                    OBJECT IDENTIFIER ::= { enterprises 3196 }
vodacomSouthAfrica                OBJECT IDENTIFIER ::= { enterprises 3197 }
volamp                            OBJECT IDENTIFIER ::= { enterprises 3198 }
shastaNetworks                    OBJECT IDENTIFIER ::= { enterprises 3199 }
appliedResources                  OBJECT IDENTIFIER ::= { enterprises 3200 }
lancome                           OBJECT IDENTIFIER ::= { enterprises 3201 }
sparAerospaceLimited              OBJECT IDENTIFIER ::= { enterprises 3202 }
glaxowellcome                     OBJECT IDENTIFIER ::= { enterprises 3203 }
atiSystemCo                       OBJECT IDENTIFIER ::= { enterprises 3204 }
exodusCommunications              OBJECT IDENTIFIER ::= { enterprises 3205 }
assuredDigital                    OBJECT IDENTIFIER ::= { enterprises 3206 }
web                               OBJECT IDENTIFIER ::= { enterprises 3207 }
athensUniversityOfEconomicsAndBusiness OBJECT IDENTIFIER ::= { enterprises 3208 }
dynarcAB                          OBJECT IDENTIFIER ::= { enterprises 3209 }
volkswagenAG                      OBJECT IDENTIFIER ::= { enterprises 3210 }
allgonAB                          OBJECT IDENTIFIER ::= { enterprises 3211 }
crestronElectronics               OBJECT IDENTIFIER ::= { enterprises 3212 }
transiciel                        OBJECT IDENTIFIER ::= { enterprises 3213 }
sanPeople                         OBJECT IDENTIFIER ::= { enterprises 3214 }
networkInstruments                OBJECT IDENTIFIER ::= { enterprises 3215 }
texasNetworking                   OBJECT IDENTIFIER ::= { enterprises 3216 }
piniComputerTrading               OBJECT IDENTIFIER ::= { enterprises 3217 }
xlnT                              OBJECT IDENTIFIER ::= { enterprises 3218 }
silicomp                          OBJECT IDENTIFIER ::= { enterprises 3219 }
signetSystemsPty                  OBJECT IDENTIFIER ::= { enterprises 3220 }
ohkuraElectricCo                  OBJECT IDENTIFIER ::= { enterprises 3221 }
newEliteTechnologies              OBJECT IDENTIFIER ::= { enterprises 3222 }
txcom                             OBJECT IDENTIFIER ::= { enterprises 3223 }
netscreenTechnologies             OBJECT IDENTIFIER ::= { enterprises 3224 }
sycamoreNetworks                  OBJECT IDENTIFIER ::= { enterprises 3225 }
franceConnexionIngenierie         OBJECT IDENTIFIER ::= { enterprises 3226 }
netleader                         OBJECT IDENTIFIER ::= { enterprises 3227 }
tekmarSistemiSrl                  OBJECT IDENTIFIER ::= { enterprises 3228 }
dstc                              OBJECT IDENTIFIER ::= { enterprises 3229 }
runtop                            OBJECT IDENTIFIER ::= { enterprises 3230 }
l3Communications                  OBJECT IDENTIFIER ::= { enterprises 3231 }
eumetsat                          OBJECT IDENTIFIER ::= { enterprises 3232 }
tonggongHighNewTechnologyDevelopmentCompany OBJECT IDENTIFIER ::= { enterprises 3233 }
trifolium                         OBJECT IDENTIFIER ::= { enterprises 3234 }
zenonNSP                          OBJECT IDENTIFIER ::= { enterprises 3235 }
ercom                             OBJECT IDENTIFIER ::= { enterprises 3236 }
sdc                               OBJECT IDENTIFIER ::= { enterprises 3237 }
losAngelesWeb                     OBJECT IDENTIFIER ::= { enterprises 3238 }
florenceOnLineSrl                 OBJECT IDENTIFIER ::= { enterprises 3239 }
escalateNetworks                  OBJECT IDENTIFIER ::= { enterprises 3240 }
trannexus                         OBJECT IDENTIFIER ::= { enterprises 3241 }
brighamYoungUniversity            OBJECT IDENTIFIER ::= { enterprises 3242 }
connovaSystemsAB                  OBJECT IDENTIFIER ::= { enterprises 3243 }
voxtronFlandersNV                 OBJECT IDENTIFIER ::= { enterprises 3244 }
votek                             OBJECT IDENTIFIER ::= { enterprises 3245 }
mirapoint                         OBJECT IDENTIFIER ::= { enterprises 3246 }
colorbus                          OBJECT IDENTIFIER ::= { enterprises 3247 }
dpbSA                             OBJECT IDENTIFIER ::= { enterprises 3248 }
starguideDigitalNetworks          OBJECT IDENTIFIER ::= { enterprises 3249 }
telinetTechnologies               OBJECT IDENTIFIER ::= { enterprises 3250 }
authenticaSecurityTechnologies    OBJECT IDENTIFIER ::= { enterprises 3251 }
hologramSystems                   OBJECT IDENTIFIER ::= { enterprises 3252 }
transystem                        OBJECT IDENTIFIER ::= { enterprises 3253 }
rrcExports                        OBJECT IDENTIFIER ::= { enterprises 3254 }
lakesideSoftware                  OBJECT IDENTIFIER ::= { enterprises 3255 }
channel100                        OBJECT IDENTIFIER ::= { enterprises 3256 }
magma                             OBJECT IDENTIFIER ::= { enterprises 3257 }
lansourceTechnologies             OBJECT IDENTIFIER ::= { enterprises 3258 }
incaaDatacomBV                    OBJECT IDENTIFIER ::= { enterprises 3259 }
globeset                          OBJECT IDENTIFIER ::= { enterprises 3260 }
martinPestana                     OBJECT IDENTIFIER ::= { enterprises 3261 }
acusonCorporation                 OBJECT IDENTIFIER ::= { enterprises 3262 }
drakeAutomationLimited            OBJECT IDENTIFIER ::= { enterprises 3263 }
kerrVayneSystems                  OBJECT IDENTIFIER ::= { enterprises 3264 }
ksquaredConsulting                OBJECT IDENTIFIER ::= { enterprises 3265 }
hsbcGroup                         OBJECT IDENTIFIER ::= { enterprises 3266 }
ironbridgeNetworks                OBJECT IDENTIFIER ::= { enterprises 3267 }
realTimeLogic                     OBJECT IDENTIFIER ::= { enterprises 3268 }
telserve                          OBJECT IDENTIFIER ::= { enterprises 3269 }
uniquestKorea                     OBJECT IDENTIFIER ::= { enterprises 3270 }
stockpower                        OBJECT IDENTIFIER ::= { enterprises 3271 }
yontemComputerAndElectronics      OBJECT IDENTIFIER ::= { enterprises 3272 }
nweGmbH                           OBJECT IDENTIFIER ::= { enterprises 3273 }
theInformationSystemsManager      OBJECT IDENTIFIER ::= { enterprises 3274 }
kosmosImageSrl                    OBJECT IDENTIFIER ::= { enterprises 3275 }
taihanElectricWireCo              OBJECT IDENTIFIER ::= { enterprises 3276 }
telspec                           OBJECT IDENTIFIER ::= { enterprises 3277 }
cCOMCorporation                   OBJECT IDENTIFIER ::= { enterprises 3278 }
adlexCorp                         OBJECT IDENTIFIER ::= { enterprises 3279 }
cciEurope                         OBJECT IDENTIFIER ::= { enterprises 3280 }
smsEnterprises                    OBJECT IDENTIFIER ::= { enterprises 3281 }
vicomSystems                      OBJECT IDENTIFIER ::= { enterprises 3282 }
internationalSoftwareSolutions    OBJECT IDENTIFIER ::= { enterprises 3283 }
oasisConsortium                   OBJECT IDENTIFIER ::= { enterprises 3284 }
novaTelecommunications            OBJECT IDENTIFIER ::= { enterprises 3285 }
neraSatcomAS                      OBJECT IDENTIFIER ::= { enterprises 3286 }
proactiveNetworks                 OBJECT IDENTIFIER ::= { enterprises 3287 }
jacobsRimellLimited               OBJECT IDENTIFIER ::= { enterprises 3288 }
cryptomathicAS                    OBJECT IDENTIFIER ::= { enterprises 3289 }
appliscope                        OBJECT IDENTIFIER ::= { enterprises 3290 }
simacTechniekNV                   OBJECT IDENTIFIER ::= { enterprises 3291 }
earthmenTechnology                OBJECT IDENTIFIER ::= { enterprises 3292 }
biffstersInternational            OBJECT IDENTIFIER ::= { enterprises 3293 }
digitronic                        OBJECT IDENTIFIER ::= { enterprises 3294 }
internetMultifeedCo               OBJECT IDENTIFIER ::= { enterprises 3295 }
argosyResearch                    OBJECT IDENTIFIER ::= { enterprises 3296 }
aetherworksCoporation             OBJECT IDENTIFIER ::= { enterprises 3297 }
mqsoftware                        OBJECT IDENTIFIER ::= { enterprises 3298 }
altairDataSystem                  OBJECT IDENTIFIER ::= { enterprises 3299 }
telsisLimited                     OBJECT IDENTIFIER ::= { enterprises 3300 }
impact                            OBJECT IDENTIFIER ::= { enterprises 3301 }
smiComputersystemeGmbH            OBJECT IDENTIFIER ::= { enterprises 3302 }
idm                               OBJECT IDENTIFIER ::= { enterprises 3303 }
winvistaCorp                      OBJECT IDENTIFIER ::= { enterprises 3304 }
splitrockServices                 OBJECT IDENTIFIER ::= { enterprises 3305 }
vailSystems                       OBJECT IDENTIFIER ::= { enterprises 3306 }
sanenet                           OBJECT IDENTIFIER ::= { enterprises 3307 }
ensembleSolutions                 OBJECT IDENTIFIER ::= { enterprises 3308 }
nomadix                           OBJECT IDENTIFIER ::= { enterprises 3309 }
jettInternational                 OBJECT IDENTIFIER ::= { enterprises 3310 }
crocodialCommunications           OBJECT IDENTIFIER ::= { enterprises 3311 }
consultingInformaticoDeCantabria  OBJECT IDENTIFIER ::= { enterprises 3312 }
broadcastServices                 OBJECT IDENTIFIER ::= { enterprises 3313 }
bergstresserAssociates            OBJECT IDENTIFIER ::= { enterprises 3314 }
kingstarComputer                  OBJECT IDENTIFIER ::= { enterprises 3315 }
microLogicSystems                 OBJECT IDENTIFIER ::= { enterprises 3316 }
portCommunityRotterdam            OBJECT IDENTIFIER ::= { enterprises 3317 }
computerAndCompetenceGmbH         OBJECT IDENTIFIER ::= { enterprises 3318 }
gnomeProject                      OBJECT IDENTIFIER ::= { enterprises 3319 }
shanghaiBaudDataCommunicationDevelopmentCorp OBJECT IDENTIFIER ::= { enterprises 3320 }
teledataCommunication             OBJECT IDENTIFIER ::= { enterprises 3321 }
ipswitch                          OBJECT IDENTIFIER ::= { enterprises 3322 }
tadiranMicrowaveNetworks          OBJECT IDENTIFIER ::= { enterprises 3323 }
callTechnologies                  OBJECT IDENTIFIER ::= { enterprises 3324 }
vocalis                           OBJECT IDENTIFIER ::= { enterprises 3325 }
bergenDataConsulting              OBJECT IDENTIFIER ::= { enterprises 3326 }
opendirectory                     OBJECT IDENTIFIER ::= { enterprises 3327 }
indusRiverNetworks                OBJECT IDENTIFIER ::= { enterprises 3328 }
newcomTechnologies                OBJECT IDENTIFIER ::= { enterprises 3329 }
partnergroup                      OBJECT IDENTIFIER ::= { enterprises 3330 }
deteweDeutscheTelephonwerkeAktiengesellschaftAndCo OBJECT IDENTIFIER ::= { enterprises 3331 }
rcxSystem                         OBJECT IDENTIFIER ::= { enterprises 3332 }
auburnUniversity                  OBJECT IDENTIFIER ::= { enterprises 3333 }
cap                               OBJECT IDENTIFIER ::= { enterprises 3334 }
hahtSoftware                      OBJECT IDENTIFIER ::= { enterprises 3335 }
utbf                              OBJECT IDENTIFIER ::= { enterprises 3336 }
chicagoPoliceDepartmentDataSystemsDivision OBJECT IDENTIFIER ::= { enterprises 3337 }
moraTechnologicalServices         OBJECT IDENTIFIER ::= { enterprises 3338 }
jhc                               OBJECT IDENTIFIER ::= { enterprises 3339 }
opentv                            OBJECT IDENTIFIER ::= { enterprises 3340 }
switchsoftSystems                 OBJECT IDENTIFIER ::= { enterprises 3341 }
machoneCommunications             OBJECT IDENTIFIER ::= { enterprises 3342 }
philipsDigitalVideoSystems        OBJECT IDENTIFIER ::= { enterprises 3343 }
helsinkiTelevisioOy               OBJECT IDENTIFIER ::= { enterprises 3344 }
nemetschekAG                      OBJECT IDENTIFIER ::= { enterprises 3345 }
vocom                             OBJECT IDENTIFIER ::= { enterprises 3346 }
kokusaiElectricCo                 OBJECT IDENTIFIER ::= { enterprises 3347 }
reliableNetworkSolutions          OBJECT IDENTIFIER ::= { enterprises 3348 }
vogoNetworks                      OBJECT IDENTIFIER ::= { enterprises 3349 }
beusen                            OBJECT IDENTIFIER ::= { enterprises 3350 }
overlandData                      OBJECT IDENTIFIER ::= { enterprises 3351 }
go2Technologies                   OBJECT IDENTIFIER ::= { enterprises 3352 }
transmediaCommunications          OBJECT IDENTIFIER ::= { enterprises 3353 }
innomedia                         OBJECT IDENTIFIER ::= { enterprises 3354 }
orkitFI                           OBJECT IDENTIFIER ::= { enterprises 3355 }
webmaster                         OBJECT IDENTIFIER ::= { enterprises 3356 }
softwareAndManagementAssociates   OBJECT IDENTIFIER ::= { enterprises 3357 }
researcher                        OBJECT IDENTIFIER ::= { enterprises 3358 }
cygnusGlobalConsulting            OBJECT IDENTIFIER ::= { enterprises 3359 }
columbineJDSSystems               OBJECT IDENTIFIER ::= { enterprises 3360 }
intraplex                         OBJECT IDENTIFIER ::= { enterprises 3361 }
seltaSpA                          OBJECT IDENTIFIER ::= { enterprises 3362 }
southernNewEnglandTelecommunications OBJECT IDENTIFIER ::= { enterprises 3363 }
balticOil                         OBJECT IDENTIFIER ::= { enterprises 3364 }
mailwizard                        OBJECT IDENTIFIER ::= { enterprises 3365 }
daVinciSystemsCc                  OBJECT IDENTIFIER ::= { enterprises 3366 }
nmsResearch                       OBJECT IDENTIFIER ::= { enterprises 3367 }
kimsungeunCo                      OBJECT IDENTIFIER ::= { enterprises 3368 }
genicomCorporation                OBJECT IDENTIFIER ::= { enterprises 3369 }
trangoSoftwareCorporation         OBJECT IDENTIFIER ::= { enterprises 3370 }
sungeunSystems                    OBJECT IDENTIFIER ::= { enterprises 3371 }
coveSistemas                      OBJECT IDENTIFIER ::= { enterprises 3372 }
siaeMicroelettronicaSpA           OBJECT IDENTIFIER ::= { enterprises 3373 }
cybertekCorp                      OBJECT IDENTIFIER ::= { enterprises 3374 }
f5Labs                            OBJECT IDENTIFIER ::= { enterprises 3375 }
valenciaSystems                   OBJECT IDENTIFIER ::= { enterprises 3376 }
hkcCommunications                 OBJECT IDENTIFIER ::= { enterprises 3377 }
plantEquipment                    OBJECT IDENTIFIER ::= { enterprises 3378 }
htIndustrialCo                    OBJECT IDENTIFIER ::= { enterprises 3379 }
fuellingAndPartner                OBJECT IDENTIFIER ::= { enterprises 3380 }
atreveSoftware                    OBJECT IDENTIFIER ::= { enterprises 3381 }
fourelleSystems                   OBJECT IDENTIFIER ::= { enterprises 3382 }
southEastWaterLimited             OBJECT IDENTIFIER ::= { enterprises 3383 }
wamnet                            OBJECT IDENTIFIER ::= { enterprises 3384 }
universityOfLeicester             OBJECT IDENTIFIER ::= { enterprises 3385 }
stCenturyNet                      OBJECT IDENTIFIER ::= { enterprises 3386 }
intellivoice                      OBJECT IDENTIFIER ::= { enterprises 3387 }
integralPartners                  OBJECT IDENTIFIER ::= { enterprises 3388 }
novotecComputersGmbH              OBJECT IDENTIFIER ::= { enterprises 3389 }
marathonTechnologiesCorporation   OBJECT IDENTIFIER ::= { enterprises 3390 }
softwareTechnologiesGroup         OBJECT IDENTIFIER ::= { enterprises 3391 }
quvintheumnFoundation             OBJECT IDENTIFIER ::= { enterprises 3392 }
sandsInternational                OBJECT IDENTIFIER ::= { enterprises 3393 }
netrueCommunications              OBJECT IDENTIFIER ::= { enterprises 3394 }
certicomCorp                      OBJECT IDENTIFIER ::= { enterprises 3395 }
dicosGmbHKommunikationssysteme    OBJECT IDENTIFIER ::= { enterprises 3396 }
borderBluesProductions            OBJECT IDENTIFIER ::= { enterprises 3397 }
fieldbusFoundation                OBJECT IDENTIFIER ::= { enterprises 3398 }
olencomElectronics                OBJECT IDENTIFIER ::= { enterprises 3399 }
alacrityCommunications            OBJECT IDENTIFIER ::= { enterprises 3400 }
networkAssociates                 OBJECT IDENTIFIER ::= { enterprises 3401 }
magicomIntegratedSolutions        OBJECT IDENTIFIER ::= { enterprises 3402 }
marimba                           OBJECT IDENTIFIER ::= { enterprises 3403 }
adicom                            OBJECT IDENTIFIER ::= { enterprises 3404 }
expandNetworks                    OBJECT IDENTIFIER ::= { enterprises 3405 }
eisCorporation                    OBJECT IDENTIFIER ::= { enterprises 3406 }
compuDAWN                         OBJECT IDENTIFIER ::= { enterprises 3407 }
nylcareHealthPlans                OBJECT IDENTIFIER ::= { enterprises 3408 }
zTelCommunications                OBJECT IDENTIFIER ::= { enterprises 3409 }
land5Corporation                  OBJECT IDENTIFIER ::= { enterprises 3410 }
jSlivko                           OBJECT IDENTIFIER ::= { enterprises 3411 }
sancastleTechnologies             OBJECT IDENTIFIER ::= { enterprises 3412 }
radiotel                          OBJECT IDENTIFIER ::= { enterprises 3413 }
voicestreamWireless               OBJECT IDENTIFIER ::= { enterprises 3414 }
mobileTelephoneNetworks           OBJECT IDENTIFIER ::= { enterprises 3415 }
netoCorporation                   OBJECT IDENTIFIER ::= { enterprises 3416 }
cacheflow                         OBJECT IDENTIFIER ::= { enterprises 3417 }
interactiveChannelTechnologies    OBJECT IDENTIFIER ::= { enterprises 3418 }
dera                              OBJECT IDENTIFIER ::= { enterprises 3419 }
rossiyskiyKreditBank              OBJECT IDENTIFIER ::= { enterprises 3420 }
performanceReportingServices      OBJECT IDENTIFIER ::= { enterprises 3421 }
networkAware                      OBJECT IDENTIFIER ::= { enterprises 3422 }
project25                         OBJECT IDENTIFIER ::= { enterprises 3423 }
apogeeNetworks                    OBJECT IDENTIFIER ::= { enterprises 3424 }
amsdell                           OBJECT IDENTIFIER ::= { enterprises 3425 }
tokyoDenshiSekeiKK                OBJECT IDENTIFIER ::= { enterprises 3426 }
microjuris                        OBJECT IDENTIFIER ::= { enterprises 3427 }
computerAssociatesTCGSoftware     OBJECT IDENTIFIER ::= { enterprises 3428 }
gennetTechnologyCo                OBJECT IDENTIFIER ::= { enterprises 3429 }
microtronixDatacom                OBJECT IDENTIFIER ::= { enterprises 3430 }
westernDataComCo                  OBJECT IDENTIFIER ::= { enterprises 3431 }
tellium                           OBJECT IDENTIFIER ::= { enterprises 3432 }
goldencomTechnologies             OBJECT IDENTIFIER ::= { enterprises 3433 }
leightronix                       OBJECT IDENTIFIER ::= { enterprises 3434 }
portaSystems                      OBJECT IDENTIFIER ::= { enterprises 3435 }
brivida                           OBJECT IDENTIFIER ::= { enterprises 3436 }
pitchonpe                         OBJECT IDENTIFIER ::= { enterprises 3437 }
missouriFreeNet                   OBJECT IDENTIFIER ::= { enterprises 3438 }
braintreeCommunicationsPty        OBJECT IDENTIFIER ::= { enterprises 3439 }
borealisTechnology                OBJECT IDENTIFIER ::= { enterprises 3440 }
southCarolinaStatePortsAuthority  OBJECT IDENTIFIER ::= { enterprises 3441 }
advantech                         OBJECT IDENTIFIER ::= { enterprises 3442 }
unitedHealthcare                  OBJECT IDENTIFIER ::= { enterprises 3443 }
egniteSoftwareGmbH                OBJECT IDENTIFIER ::= { enterprises 3444 }
radiantCommunicationsCorp         OBJECT IDENTIFIER ::= { enterprises 3445 }
ridgeTechnologiesDaveHolzer       OBJECT IDENTIFIER ::= { enterprises 3446 }
jgi                               OBJECT IDENTIFIER ::= { enterprises 3447 }
rivkinScienceAndTechnology        OBJECT IDENTIFIER ::= { enterprises 3448 }
fisherBerkeleyCorp                OBJECT IDENTIFIER ::= { enterprises 3449 }
pharLapSoftware                   OBJECT IDENTIFIER ::= { enterprises 3450 }
vitaNuovaLimited                  OBJECT IDENTIFIER ::= { enterprises 3451 }
mobileDataSolutions               OBJECT IDENTIFIER ::= { enterprises 3452 }
comtier                           OBJECT IDENTIFIER ::= { enterprises 3453 }
trustworksSystemsBV               OBJECT IDENTIFIER ::= { enterprises 3454 }
internetFreaksLuxembourgAsbl      OBJECT IDENTIFIER ::= { enterprises 3455 }
adtech                            OBJECT IDENTIFIER ::= { enterprises 3456 }
advancedIntelligentNetworksCorp   OBJECT IDENTIFIER ::= { enterprises 3457 }
transactionNetworkServices        OBJECT IDENTIFIER ::= { enterprises 3458 }
onCommunicationSystemsGmbH        OBJECT IDENTIFIER ::= { enterprises 3459 }
telecommunicationsSpecialistsPte  OBJECT IDENTIFIER ::= { enterprises 3460 }
inferentiaSPA                     OBJECT IDENTIFIER ::= { enterprises 3461 }
makoninConsultingCorp             OBJECT IDENTIFIER ::= { enterprises 3462 }
toucanTechnology                  OBJECT IDENTIFIER ::= { enterprises 3463 }
gimletManagementConsultants       OBJECT IDENTIFIER ::= { enterprises 3464 }
sanyoDenkiCo                      OBJECT IDENTIFIER ::= { enterprises 3465 }
opticalNetworks                   OBJECT IDENTIFIER ::= { enterprises 3466 }
norcomNetworksCorporation         OBJECT IDENTIFIER ::= { enterprises 3467 }
gteInteractive                    OBJECT IDENTIFIER ::= { enterprises 3468 }
schumannUnternehmensberatungAG    OBJECT IDENTIFIER ::= { enterprises 3469 }
atmRAndDCenterOfBUPT              OBJECT IDENTIFIER ::= { enterprises 3470 }
bearStearnsAndCompany             OBJECT IDENTIFIER ::= { enterprises 3471 }
telamon                           OBJECT IDENTIFIER ::= { enterprises 3472 }
microgateCorporation              OBJECT IDENTIFIER ::= { enterprises 3473 }
fujituICLEspanaSA                 OBJECT IDENTIFIER ::= { enterprises 3474 }
networkConcepts                   OBJECT IDENTIFIER ::= { enterprises 3475 }
arepa                             OBJECT IDENTIFIER ::= { enterprises 3476 }
doradoSoftware                    OBJECT IDENTIFIER ::= { enterprises 3477 }
spectraLogic                      OBJECT IDENTIFIER ::= { enterprises 3478 }
viewtouch                         OBJECT IDENTIFIER ::= { enterprises 3479 }
viewsNet                          OBJECT IDENTIFIER ::= { enterprises 3480 }
himelTechnology                   OBJECT IDENTIFIER ::= { enterprises 3481 }
tonAndLichttechnik                OBJECT IDENTIFIER ::= { enterprises 3482 }
marinerNetworks                   OBJECT IDENTIFIER ::= { enterprises 3483 }
alaskaTextiles                    OBJECT IDENTIFIER ::= { enterprises 3484 }
alaskaCleaners                    OBJECT IDENTIFIER ::= { enterprises 3485 }
wellspringsHoldings               OBJECT IDENTIFIER ::= { enterprises 3486 }
allureOfAlaska                    OBJECT IDENTIFIER ::= { enterprises 3487 }
sevenx                            OBJECT IDENTIFIER ::= { enterprises 3488 }
denaliSites                       OBJECT IDENTIFIER ::= { enterprises 3489 }
unitedSystemsBase                 OBJECT IDENTIFIER ::= { enterprises 3490 }
cdconsultants                     OBJECT IDENTIFIER ::= { enterprises 3491 }
comdisco                          OBJECT IDENTIFIER ::= { enterprises 3492 }
broadbandAccessSystems            OBJECT IDENTIFIER ::= { enterprises 3493 }
convergentNetworks                OBJECT IDENTIFIER ::= { enterprises 3494 }
nationalLaboratoryForAppliedNetworkResearch OBJECT IDENTIFIER ::= { enterprises 3495 }
webResumes                        OBJECT IDENTIFIER ::= { enterprises 3496 }
virtualVendor                     OBJECT IDENTIFIER ::= { enterprises 3497 }
businessbuilderTechnologies       OBJECT IDENTIFIER ::= { enterprises 3498 }
cyberServerPark                   OBJECT IDENTIFIER ::= { enterprises 3499 }
comsatLaboratories                OBJECT IDENTIFIER ::= { enterprises 3500 }
vodafoneValueAddedServices        OBJECT IDENTIFIER ::= { enterprises 3501 }
jAndAServices                     OBJECT IDENTIFIER ::= { enterprises 3502 }
blueLance                         OBJECT IDENTIFIER ::= { enterprises 3503 }
sandvikCoromant                   OBJECT IDENTIFIER ::= { enterprises 3504 }
virtualVirginIslands              OBJECT IDENTIFIER ::= { enterprises 3505 }
pagetek                           OBJECT IDENTIFIER ::= { enterprises 3506 }
eNet                              OBJECT IDENTIFIER ::= { enterprises 3507 }
nest                              OBJECT IDENTIFIER ::= { enterprises 3508 }
capitalHoldings                   OBJECT IDENTIFIER ::= { enterprises 3509 }
twoWAYLAUNDRY                     OBJECT IDENTIFIER ::= { enterprises 3510 }
skystream                         OBJECT IDENTIFIER ::= { enterprises 3511 }
portalSoftware                    OBJECT IDENTIFIER ::= { enterprises 3512 }
vstream                           OBJECT IDENTIFIER ::= { enterprises 3514 }
joanneumResearchGesmbH            OBJECT IDENTIFIER ::= { enterprises 3515 }
cybernetica                       OBJECT IDENTIFIER ::= { enterprises 3516 }
tietoTechnologyAS                 OBJECT IDENTIFIER ::= { enterprises 3517 }
pressler                          OBJECT IDENTIFIER ::= { enterprises 3518 }
amplifynet                        OBJECT IDENTIFIER ::= { enterprises 3519 }
tps                               OBJECT IDENTIFIER ::= { enterprises 3520 }
atlasTechnologies                 OBJECT IDENTIFIER ::= { enterprises 3521 }
biodataGmbH                       OBJECT IDENTIFIER ::= { enterprises 3522 }
netcoGmbH                         OBJECT IDENTIFIER ::= { enterprises 3523 }
continium                         OBJECT IDENTIFIER ::= { enterprises 3524 }
silverbackTechnologies            OBJECT IDENTIFIER ::= { enterprises 3525 }
itcGmbH                           OBJECT IDENTIFIER ::= { enterprises 3526 }
intrasoft                         OBJECT IDENTIFIER ::= { enterprises 3527 }
esp                               OBJECT IDENTIFIER ::= { enterprises 3528 }
avtCorporation                    OBJECT IDENTIFIER ::= { enterprises 3529 }
researchInMotion                  OBJECT IDENTIFIER ::= { enterprises 3530 }
mobilixAS                         OBJECT IDENTIFIER ::= { enterprises 3531 }
meiseiSystemServiceCompany        OBJECT IDENTIFIER ::= { enterprises 3532 }
aciesSistemasSC                   OBJECT IDENTIFIER ::= { enterprises 3533 }
ctamPty                           OBJECT IDENTIFIER ::= { enterprises 3534 }
hutchisonAvenueSoftwareCorp       OBJECT IDENTIFIER ::= { enterprises 3535 }
globus                            OBJECT IDENTIFIER ::= { enterprises 3536 }
airfiber                          OBJECT IDENTIFIER ::= { enterprises 3537 }
europeConnection                  OBJECT IDENTIFIER ::= { enterprises 3538 }
nipponSteelCompany                OBJECT IDENTIFIER ::= { enterprises 3539 }
conellyInternational              OBJECT IDENTIFIER ::= { enterprises 3540 }
bindviewDevelopmentCorp           OBJECT IDENTIFIER ::= { enterprises 3541 }
galeaNetworkSecurity              OBJECT IDENTIFIER ::= { enterprises 3542 }
abilisGmbh                        OBJECT IDENTIFIER ::= { enterprises 3543 }
baycorpIDServices                 OBJECT IDENTIFIER ::= { enterprises 3544 }
maddoxBroadcast                   OBJECT IDENTIFIER ::= { enterprises 3545 }
acuteCommunicationsCorporation    OBJECT IDENTIFIER ::= { enterprises 3546 }
tollbridgeTechnologies            OBJECT IDENTIFIER ::= { enterprises 3547 }
oresisCommunications              OBJECT IDENTIFIER ::= { enterprises 3548 }
mliEnterprises                    OBJECT IDENTIFIER ::= { enterprises 3549 }
allstorSoftwareLimited            OBJECT IDENTIFIER ::= { enterprises 3550 }
springTideNetworks                OBJECT IDENTIFIER ::= { enterprises 3551 }
eesTechnology                     OBJECT IDENTIFIER ::= { enterprises 3552 }
cspAG                             OBJECT IDENTIFIER ::= { enterprises 3553 }
sasInstitue                       OBJECT IDENTIFIER ::= { enterprises 3554 }
netlock                           OBJECT IDENTIFIER ::= { enterprises 3555 }
genoRZGmbH                        OBJECT IDENTIFIER ::= { enterprises 3556 }
ms3net                            OBJECT IDENTIFIER ::= { enterprises 3557 }
bgsSystemplanungAG                OBJECT IDENTIFIER ::= { enterprises 3558 }
theDigitalSchoolhouse             OBJECT IDENTIFIER ::= { enterprises 3559 }
sphereLogicCorporation            OBJECT IDENTIFIER ::= { enterprises 3560 }
adslForum                         OBJECT IDENTIFIER ::= { enterprises 3561 }
selwayMooreLimited                OBJECT IDENTIFIER ::= { enterprises 3562 }
nationalNetworkDataServices       OBJECT IDENTIFIER ::= { enterprises 3563 }
ciphernet                         OBJECT IDENTIFIER ::= { enterprises 3564 }
grolierInteractiveEuropeOnLineGroupe OBJECT IDENTIFIER ::= { enterprises 3565 }
midnightTechnologies              OBJECT IDENTIFIER ::= { enterprises 3566 }
scottSupplyService                OBJECT IDENTIFIER ::= { enterprises 3567 }
serviceCoLLC                      OBJECT IDENTIFIER ::= { enterprises 3568 }
electronicPaymentServices         OBJECT IDENTIFIER ::= { enterprises 3569 }
taitElectronics                   OBJECT IDENTIFIER ::= { enterprises 3570 }
giftTrekMalaysiaSdnBhd            OBJECT IDENTIFIER ::= { enterprises 3571 }
hanaSystems                       OBJECT IDENTIFIER ::= { enterprises 3572 }
southAfricanNetworkingPeople      OBJECT IDENTIFIER ::= { enterprises 3573 }
orsypSA                           OBJECT IDENTIFIER ::= { enterprises 3574 }
rkbOnsiteComputerService          OBJECT IDENTIFIER ::= { enterprises 3575 }
mciWorldcom                       OBJECT IDENTIFIER ::= { enterprises 3576 }
himachalFuturisticCommunicationsLimited OBJECT IDENTIFIER ::= { enterprises 3577 }
pixstream                         OBJECT IDENTIFIER ::= { enterprises 3578 }
hurley                            OBJECT IDENTIFIER ::= { enterprises 3579 }
bellEmergis                       OBJECT IDENTIFIER ::= { enterprises 3580 }
seagateTechnology                 OBJECT IDENTIFIER ::= { enterprises 3581 }
americanMegatrends                OBJECT IDENTIFIER ::= { enterprises 3582 }
jetcell                           OBJECT IDENTIFIER ::= { enterprises 3583 }
pacificFiberoptics                OBJECT IDENTIFIER ::= { enterprises 3584 }
omnisecAG                         OBJECT IDENTIFIER ::= { enterprises 3585 }
diebold                           OBJECT IDENTIFIER ::= { enterprises 3586 }
tiwSystems                        OBJECT IDENTIFIER ::= { enterprises 3587 }
novogroupOyj                      OBJECT IDENTIFIER ::= { enterprises 3588 }
sogot                             OBJECT IDENTIFIER ::= { enterprises 3589 }
iaInformationSystemsAG            OBJECT IDENTIFIER ::= { enterprises 3590 }
theCameronCyberneticsCorp         OBJECT IDENTIFIER ::= { enterprises 3591 }
draegerMedizintechnikGmbH         OBJECT IDENTIFIER ::= { enterprises 3592 }
alcatelSistemasDeInformacion      OBJECT IDENTIFIER ::= { enterprises 3593 }
ljlEnterprises                    OBJECT IDENTIFIER ::= { enterprises 3594 }
bcTELAdvancedCommunications       OBJECT IDENTIFIER ::= { enterprises 3595 }
cmltechnologies                   OBJECT IDENTIFIER ::= { enterprises 3596 }
wildthings                        OBJECT IDENTIFIER ::= { enterprises 3597 }
dixieCake                         OBJECT IDENTIFIER ::= { enterprises 3598 }
typeAndGraphicsPtyLimited         OBJECT IDENTIFIER ::= { enterprises 3599 }
teltronics                        OBJECT IDENTIFIER ::= { enterprises 3600 }
crMcGuffinConsultingServices      OBJECT IDENTIFIER ::= { enterprises 3601 }
internationalDatacastingCorporation OBJECT IDENTIFIER ::= { enterprises 3602 }
westpacBankingCorporation         OBJECT IDENTIFIER ::= { enterprises 3603 }
xypiMEDIANETPVTLTD                OBJECT IDENTIFIER ::= { enterprises 3604 }
nesserAndNesserConsulting         OBJECT IDENTIFIER ::= { enterprises 3605 }
incognitoSoftware                 OBJECT IDENTIFIER ::= { enterprises 3606 }
cerentCorporation                 OBJECT IDENTIFIER ::= { enterprises 3607 }
theTillermanGroup                 OBJECT IDENTIFIER ::= { enterprises 3608 }
cequs                             OBJECT IDENTIFIER ::= { enterprises 3609 }
ryanNetWorks                      OBJECT IDENTIFIER ::= { enterprises 3610 }
fooChicken                        OBJECT IDENTIFIER ::= { enterprises 3611 }
marcelEnterprises                 OBJECT IDENTIFIER ::= { enterprises 3612 }
rubiconTechnologies               OBJECT IDENTIFIER ::= { enterprises 3613 }
altorPlc                          OBJECT IDENTIFIER ::= { enterprises 3614 }
softwellAB                        OBJECT IDENTIFIER ::= { enterprises 3615 }
unitedResourceEconomicAndTradingCenterC OBJECT IDENTIFIER ::= { enterprises 3616 }
jsbTechnologiesPlc                OBJECT IDENTIFIER ::= { enterprises 3617 }
flyingCrocodile                   OBJECT IDENTIFIER ::= { enterprises 3618 }
proxymed                          OBJECT IDENTIFIER ::= { enterprises 3619 }
transactSystems                   OBJECT IDENTIFIER ::= { enterprises 3620 }
nuanceCommunications              OBJECT IDENTIFIER ::= { enterprises 3621 }
gefm                              OBJECT IDENTIFIER ::= { enterprises 3622 }
systemintegreringAB               OBJECT IDENTIFIER ::= { enterprises 3623 }
enatorCommunicationsAB            OBJECT IDENTIFIER ::= { enterprises 3624 }
ihighwaynet                       OBJECT IDENTIFIER ::= { enterprises 3625 }
diplIng                           OBJECT IDENTIFIER ::= { enterprises 3626 }
criptolab                         OBJECT IDENTIFIER ::= { enterprises 3627 }
tietokesko                        OBJECT IDENTIFIER ::= { enterprises 3628 }
atos                              OBJECT IDENTIFIER ::= { enterprises 3629 }
deltakabelTelecomCv               OBJECT IDENTIFIER ::= { enterprises 3630 }
bridgewaterSystemsCorp            OBJECT IDENTIFIER ::= { enterprises 3631 }
maxcommTechnologies               OBJECT IDENTIFIER ::= { enterprises 3632 }
id2TechnologiesAB                 OBJECT IDENTIFIER ::= { enterprises 3633 }
alliedRiserCommunications         OBJECT IDENTIFIER ::= { enterprises 3634 }
wavesatTelecom                    OBJECT IDENTIFIER ::= { enterprises 3635 }
dpaDeutschePresseAgenturGmbH      OBJECT IDENTIFIER ::= { enterprises 3636 }
powerAndDataTechnology            OBJECT IDENTIFIER ::= { enterprises 3637 }
intellireachCorporation           OBJECT IDENTIFIER ::= { enterprises 3638 }
wmData                            OBJECT IDENTIFIER ::= { enterprises 3639 }
industrialLogicCorporation        OBJECT IDENTIFIER ::= { enterprises 3640 }
netaphorSoftware                  OBJECT IDENTIFIER ::= { enterprises 3641 }
cryptoconsult                     OBJECT IDENTIFIER ::= { enterprises 3642 }
dirtsa                            OBJECT IDENTIFIER ::= { enterprises 3643 }
cardenEnterprise                  OBJECT IDENTIFIER ::= { enterprises 3644 }
sonz                              OBJECT IDENTIFIER ::= { enterprises 3645 }
askeyComputerCorp                 OBJECT IDENTIFIER ::= { enterprises 3646 }
raidtec                           OBJECT IDENTIFIER ::= { enterprises 3647 }
harcourtBraceAndCompany           OBJECT IDENTIFIER ::= { enterprises 3648 }
rollinsTechnology                 OBJECT IDENTIFIER ::= { enterprises 3649 }
netopsCorp                        OBJECT IDENTIFIER ::= { enterprises 3650 }
knowITAB                          OBJECT IDENTIFIER ::= { enterprises 3651 }
dokProdukteGmbH                   OBJECT IDENTIFIER ::= { enterprises 3652 }
cirqueNetworks                    OBJECT IDENTIFIER ::= { enterprises 3653 }
navinetInternetServices           OBJECT IDENTIFIER ::= { enterprises 3654 }
germanischerLloydAG               OBJECT IDENTIFIER ::= { enterprises 3655 }
forceComputersGmbH                OBJECT IDENTIFIER ::= { enterprises 3656 }
ericssonWirelessLANSystems        OBJECT IDENTIFIER ::= { enterprises 3657 }
dalianFTZTianYangInt              OBJECT IDENTIFIER ::= { enterprises 3658 }
ethercityDesignsAndHostingSolutions OBJECT IDENTIFIER ::= { enterprises 3659 }
g3mCorporation                    OBJECT IDENTIFIER ::= { enterprises 3660 }
secureDataAccess                  OBJECT IDENTIFIER ::= { enterprises 3661 }
qwescom                           OBJECT IDENTIFIER ::= { enterprises 3662 }
megaxess                          OBJECT IDENTIFIER ::= { enterprises 3663 }
polygon                           OBJECT IDENTIFIER ::= { enterprises 3664 }
netoids                           OBJECT IDENTIFIER ::= { enterprises 3665 }
acriterSoftwareBV                 OBJECT IDENTIFIER ::= { enterprises 3666 }
intelenetCommunications           OBJECT IDENTIFIER ::= { enterprises 3667 }
controlModule                     OBJECT IDENTIFIER ::= { enterprises 3668 }
aveo                              OBJECT IDENTIFIER ::= { enterprises 3669 }
mdPREI                            OBJECT IDENTIFIER ::= { enterprises 3670 }
picazoCommunication               OBJECT IDENTIFIER ::= { enterprises 3671 }
scottsdaleSecurities              OBJECT IDENTIFIER ::= { enterprises 3672 }
webmanageTechnologies             OBJECT IDENTIFIER ::= { enterprises 3673 }
infoclubindia                     OBJECT IDENTIFIER ::= { enterprises 3674 }
connorPlumbingAndHeating          OBJECT IDENTIFIER ::= { enterprises 3675 }
sentrylSoftware                   OBJECT IDENTIFIER ::= { enterprises 3676 }
engetronEngenhariaEletronicaIndECom OBJECT IDENTIFIER ::= { enterprises 3677 }
icaro                             OBJECT IDENTIFIER ::= { enterprises 3678 }
unityHealth                       OBJECT IDENTIFIER ::= { enterprises 3679 }
paritySoftwareDevCorp             OBJECT IDENTIFIER ::= { enterprises 3680 }
davidDHartman                     OBJECT IDENTIFIER ::= { enterprises 3681 }
comgatesCommunications            OBJECT IDENTIFIER ::= { enterprises 3682 }
honeywellOy                       OBJECT IDENTIFIER ::= { enterprises 3683 }
interworldCorp                    OBJECT IDENTIFIER ::= { enterprises 3684 }
sentoPty                          OBJECT IDENTIFIER ::= { enterprises 3685 }
wicksByJulie                      OBJECT IDENTIFIER ::= { enterprises 3686 }
hsdHardwareSoftwareDevelopmentGmbH OBJECT IDENTIFIER ::= { enterprises 3687 }
orgaKartensystemeGmbH             OBJECT IDENTIFIER ::= { enterprises 3688 }
newTechnologyDevelopment          OBJECT IDENTIFIER ::= { enterprises 3689 }
tiaaCREF                          OBJECT IDENTIFIER ::= { enterprises 3690 }
team2itCopyLeftSrl                OBJECT IDENTIFIER ::= { enterprises 3691 }
intuit                            OBJECT IDENTIFIER ::= { enterprises 3692 }
hakusanCorporation                OBJECT IDENTIFIER ::= { enterprises 3693 }
thyssenInformatikGmbH             OBJECT IDENTIFIER ::= { enterprises 3694 }
chromatisNetworks                 OBJECT IDENTIFIER ::= { enterprises 3695 }
microprodigy                      OBJECT IDENTIFIER ::= { enterprises 3696 }
quantumCorporation                OBJECT IDENTIFIER ::= { enterprises 3697 }
saraide                           OBJECT IDENTIFIER ::= { enterprises 3698 }
networkTechnologies               OBJECT IDENTIFIER ::= { enterprises 3699 }
stellarOneCorporation             OBJECT IDENTIFIER ::= { enterprises 3700 }
turbonetCommunications            OBJECT IDENTIFIER ::= { enterprises 3701 }
printrakInternational             OBJECT IDENTIFIER ::= { enterprises 3702 }
cyberfax                          OBJECT IDENTIFIER ::= { enterprises 3703 }
amd                               OBJECT IDENTIFIER ::= { enterprises 3704 }
icetSpA                           OBJECT IDENTIFIER ::= { enterprises 3705 }
aditelTelekommunikationNetworkGmbH OBJECT IDENTIFIER ::= { enterprises 3706 }
aditHoldingGmbH                   OBJECT IDENTIFIER ::= { enterprises 3707 }
adlerDATASoftwareGmbH             OBJECT IDENTIFIER ::= { enterprises 3708 }
teracomTelematica                 OBJECT IDENTIFIER ::= { enterprises 3709 }
lanmetrixPty                      OBJECT IDENTIFIER ::= { enterprises 3710 }
sinetica                          OBJECT IDENTIFIER ::= { enterprises 3711 }
giganet2                          OBJECT IDENTIFIER ::= { enterprises 3712 }
flexionSystems                    OBJECT IDENTIFIER ::= { enterprises 3713 }
bellsouthWirelessData             OBJECT IDENTIFIER ::= { enterprises 3714 }
telesteCorporation                OBJECT IDENTIFIER ::= { enterprises 3715 }
brandCommunicationsLimited        OBJECT IDENTIFIER ::= { enterprises 3716 }
genuaMbH                          OBJECT IDENTIFIER ::= { enterprises 3717 }
philipsBroadbandNetworks          OBJECT IDENTIFIER ::= { enterprises 3718 }
exmicro                           OBJECT IDENTIFIER ::= { enterprises 3719 }
visiqn                            OBJECT IDENTIFIER ::= { enterprises 3720 }
otonetSarl                        OBJECT IDENTIFIER ::= { enterprises 3721 }
vulkanCom                         OBJECT IDENTIFIER ::= { enterprises 3722 }
ankey                             OBJECT IDENTIFIER ::= { enterprises 3723 }
interactiveCommunicationsSystems  OBJECT IDENTIFIER ::= { enterprises 3724 }
acAnde                            OBJECT IDENTIFIER ::= { enterprises 3725 }
encommerce                        OBJECT IDENTIFIER ::= { enterprises 3726 }
westernMultiplex                  OBJECT IDENTIFIER ::= { enterprises 3727 }
realmInformationTechnoligies      OBJECT IDENTIFIER ::= { enterprises 3728 }
lucentTechnologies2               OBJECT IDENTIFIER ::= { enterprises 3729 }
westportTechnologies              OBJECT IDENTIFIER ::= { enterprises 3730 }
theSABREGroup2                    OBJECT IDENTIFIER ::= { enterprises 3731 }
dataradio                         OBJECT IDENTIFIER ::= { enterprises 3732 }
datakomAustriaDI                  OBJECT IDENTIFIER ::= { enterprises 3733 }
security7                         OBJECT IDENTIFIER ::= { enterprises 3734 }
telesafeAS                        OBJECT IDENTIFIER ::= { enterprises 3735 }
goodfieldCorp                     OBJECT IDENTIFIER ::= { enterprises 3736 }
pleiadesCommunications            OBJECT IDENTIFIER ::= { enterprises 3737 }
streamsoft                        OBJECT IDENTIFIER ::= { enterprises 3738 }
theEighteenthSoftwareCo           OBJECT IDENTIFIER ::= { enterprises 3739 }
aquilaTechnologiesGroup           OBJECT IDENTIFIER ::= { enterprises 3740 }
foliageSoftwareSystems            OBJECT IDENTIFIER ::= { enterprises 3741 }
via                               OBJECT IDENTIFIER ::= { enterprises 3742 }
pdSystemsInternational            OBJECT IDENTIFIER ::= { enterprises 3743 }
datevEG                           OBJECT IDENTIFIER ::= { enterprises 3744 }
clustraAS                         OBJECT IDENTIFIER ::= { enterprises 3745 }
swisscomAG                        OBJECT IDENTIFIER ::= { enterprises 3746 }
asYegen                           OBJECT IDENTIFIER ::= { enterprises 3747 }
bankOfAmerica                     OBJECT IDENTIFIER ::= { enterprises 3748 }
telehubCommunicationCorp          OBJECT IDENTIFIER ::= { enterprises 3749 }
iscapeSoftware                    OBJECT IDENTIFIER ::= { enterprises 3750 }
dragonIndustries                  OBJECT IDENTIFIER ::= { enterprises 3751 }
thomsonCSFNorcomAS                OBJECT IDENTIFIER ::= { enterprises 3752 }
aitekSrL                          OBJECT IDENTIFIER ::= { enterprises 3753 }
cragTechnologies                  OBJECT IDENTIFIER ::= { enterprises 3754 }
atopTechnologies                  OBJECT IDENTIFIER ::= { enterprises 3755 }
julienDaniel                      OBJECT IDENTIFIER ::= { enterprises 3756 }
ptUsahaMediantaraIntranet         OBJECT IDENTIFIER ::= { enterprises 3757 }
coreNetworks                      OBJECT IDENTIFIER ::= { enterprises 3758 }
omegaMicroSystems                 OBJECT IDENTIFIER ::= { enterprises 3759 }
contentTechnologies               OBJECT IDENTIFIER ::= { enterprises 3760 }
hagerELECTRONICSGmbH              OBJECT IDENTIFIER ::= { enterprises 3761 }
kwangwoonUniversity               OBJECT IDENTIFIER ::= { enterprises 3762 }
veramark                          OBJECT IDENTIFIER ::= { enterprises 3763 }
advancedDigitalInformationCorporation OBJECT IDENTIFIER ::= { enterprises 3764 }
strategiclinkConsulting           OBJECT IDENTIFIER ::= { enterprises 3765 }
hannibalTeknologies               OBJECT IDENTIFIER ::= { enterprises 3766 }
panInternationalIndustrialCorp    OBJECT IDENTIFIER ::= { enterprises 3767 }
departmentOfVeteransAffairs       OBJECT IDENTIFIER ::= { enterprises 3768 }
banyanNetworksPvt                 OBJECT IDENTIFIER ::= { enterprises 3769 }
mckCommunications                 OBJECT IDENTIFIER ::= { enterprises 3770 }
ko6yd                             OBJECT IDENTIFIER ::= { enterprises 3771 }
posResources                      OBJECT IDENTIFIER ::= { enterprises 3772 }
siaraSystems                      OBJECT IDENTIFIER ::= { enterprises 3773 }
wavelink                          OBJECT IDENTIFIER ::= { enterprises 3774 }
agfaCorporation                   OBJECT IDENTIFIER ::= { enterprises 3775 }
milleniumSolutions                OBJECT IDENTIFIER ::= { enterprises 3776 }
hydrawebTechnologies              OBJECT IDENTIFIER ::= { enterprises 3777 }
cpEletronicaIndustrialSA          OBJECT IDENTIFIER ::= { enterprises 3778 }
kingmaxTechnology                 OBJECT IDENTIFIER ::= { enterprises 3779 }
level3Communications              OBJECT IDENTIFIER ::= { enterprises 3780 }
wxn                               OBJECT IDENTIFIER ::= { enterprises 3781 }
universityOfNorthTexas            OBJECT IDENTIFIER ::= { enterprises 3782 }
emrCorporation                    OBJECT IDENTIFIER ::= { enterprises 3783 }
speakerbus                        OBJECT IDENTIFIER ::= { enterprises 3784 }
cirrusLogic                       OBJECT IDENTIFIER ::= { enterprises 3785 }
highlandTechnologyGroup           OBJECT IDENTIFIER ::= { enterprises 3786 }
russelLaneAndAssociates           OBJECT IDENTIFIER ::= { enterprises 3787 }
talktymeTechnologies              OBJECT IDENTIFIER ::= { enterprises 3788 }
wireTerminator                    OBJECT IDENTIFIER ::= { enterprises 3789 }
hamamatsuPhotonicsKK              OBJECT IDENTIFIER ::= { enterprises 3790 }
telecomp                          OBJECT IDENTIFIER ::= { enterprises 3791 }
logecSystems                      OBJECT IDENTIFIER ::= { enterprises 3792 }
lanierWorldwide                   OBJECT IDENTIFIER ::= { enterprises 3793 }
midasCommunicationTechnologies    OBJECT IDENTIFIER ::= { enterprises 3794 }
enact                             OBJECT IDENTIFIER ::= { enterprises 3795 }
imtInformationManagementTechnologyAG OBJECT IDENTIFIER ::= { enterprises 3796 }
siemensTaiwanSystemLimited        OBJECT IDENTIFIER ::= { enterprises 3797 }
jinnyPaging                       OBJECT IDENTIFIER ::= { enterprises 3798 }
liveNetworking                    OBJECT IDENTIFIER ::= { enterprises 3799 }
unisourceItaliaSpA                OBJECT IDENTIFIER ::= { enterprises 3800 }
agranatSystems                    OBJECT IDENTIFIER ::= { enterprises 3801 }
softamed                          OBJECT IDENTIFIER ::= { enterprises 3802 }
praxon                            OBJECT IDENTIFIER ::= { enterprises 3803 }
standardCharteredBank             OBJECT IDENTIFIER ::= { enterprises 3804 }
longhaiYongchuanFoodsCo           OBJECT IDENTIFIER ::= { enterprises 3805 }
shironSatelliteCommunications     OBJECT IDENTIFIER ::= { enterprises 3806 }
wuhanResearchInstituteOfPostsAndTelecommunications OBJECT IDENTIFIER ::= { enterprises 3807 }
cyberPowerSystem                  OBJECT IDENTIFIER ::= { enterprises 3808 }
cyrasSystems                      OBJECT IDENTIFIER ::= { enterprises 3809 }
netline                           OBJECT IDENTIFIER ::= { enterprises 3810 }
spectrasoft                       OBJECT IDENTIFIER ::= { enterprises 3811 }
andaNetworks                      OBJECT IDENTIFIER ::= { enterprises 3812 }
ellacoyaNetworks                  OBJECT IDENTIFIER ::= { enterprises 3813 }
callnetCommunications             OBJECT IDENTIFIER ::= { enterprises 3814 }
controlSolutions                  OBJECT IDENTIFIER ::= { enterprises 3815 }
nominetUK                         OBJECT IDENTIFIER ::= { enterprises 3816 }
monfox                            OBJECT IDENTIFIER ::= { enterprises 3817 }
metratechCorp                     OBJECT IDENTIFIER ::= { enterprises 3818 }
optisystemsSolutions              OBJECT IDENTIFIER ::= { enterprises 3819 }
zigaCorporation                   OBJECT IDENTIFIER ::= { enterprises 3820 }
indianValleyEnterpriseses         OBJECT IDENTIFIER ::= { enterprises 3821 }
edimaxTechnologyCo                OBJECT IDENTIFIER ::= { enterprises 3822 }
touchbaseCommunications           OBJECT IDENTIFIER ::= { enterprises 3823 }
attuneNetworks                    OBJECT IDENTIFIER ::= { enterprises 3824 }
advancedNetworkAndServices        OBJECT IDENTIFIER ::= { enterprises 3825 }
nextpointNetworks                 OBJECT IDENTIFIER ::= { enterprises 3826 }
moscowCentralDepository           OBJECT IDENTIFIER ::= { enterprises 3827 }
stg                               OBJECT IDENTIFIER ::= { enterprises 3828 }
imagingTechnologiesCorporation    OBJECT IDENTIFIER ::= { enterprises 3829 }
cmgTCUBV                          OBJECT IDENTIFIER ::= { enterprises 3830 }
oblix                             OBJECT IDENTIFIER ::= { enterprises 3831 }
tayloredSolutions                 OBJECT IDENTIFIER ::= { enterprises 3832 }
groupeSchneider                   OBJECT IDENTIFIER ::= { enterprises 3833 }
novartisPharmaLTD                 OBJECT IDENTIFIER ::= { enterprises 3834 }
alpsElectric                      OBJECT IDENTIFIER ::= { enterprises 3835 }
tereseBrownRealEstate             OBJECT IDENTIFIER ::= { enterprises 3836 }
hbocImagingSolutionsGroup         OBJECT IDENTIFIER ::= { enterprises 3837 }
gasperCorporation                 OBJECT IDENTIFIER ::= { enterprises 3838 }
neowave                           OBJECT IDENTIFIER ::= { enterprises 3839 }
globeInstituteOfTechnology        OBJECT IDENTIFIER ::= { enterprises 3840 }
flycastCommunicationsCorp         OBJECT IDENTIFIER ::= { enterprises 3841 }
lkis                              OBJECT IDENTIFIER ::= { enterprises 3842 }
pyderionContactTechnologies       OBJECT IDENTIFIER ::= { enterprises 3843 }
grahamTechnologyPlc               OBJECT IDENTIFIER ::= { enterprises 3844 }
citrixSystems                     OBJECT IDENTIFIER ::= { enterprises 3845 }
qmasterSoftwareSolutions          OBJECT IDENTIFIER ::= { enterprises 3846 }
ensembleCommunications            OBJECT IDENTIFIER ::= { enterprises 3847 }
northchurchCommunications         OBJECT IDENTIFIER ::= { enterprises 3848 }
objectIntegration                 OBJECT IDENTIFIER ::= { enterprises 3849 }
xnetCommunicationsGmbH            OBJECT IDENTIFIER ::= { enterprises 3850 }
optika                            OBJECT IDENTIFIER ::= { enterprises 3851 }
softInterTechnologies             OBJECT IDENTIFIER ::= { enterprises 3852 }
viagateTechnologies               OBJECT IDENTIFIER ::= { enterprises 3853 }
kcp                               OBJECT IDENTIFIER ::= { enterprises 3854 }
elasticNetworks                   OBJECT IDENTIFIER ::= { enterprises 3855 }
siebelSystems                     OBJECT IDENTIFIER ::= { enterprises 3856 }
sageResearchFacility              OBJECT IDENTIFIER ::= { enterprises 3857 }
capriconEngineers                 OBJECT IDENTIFIER ::= { enterprises 3858 }
vxlInstruments                    OBJECT IDENTIFIER ::= { enterprises 3859 }
firstInternationalComputer        OBJECT IDENTIFIER ::= { enterprises 3860 }
fujitsuNetworkCommunications      OBJECT IDENTIFIER ::= { enterprises 3861 }
royalBankOfScotland               OBJECT IDENTIFIER ::= { enterprises 3862 }
canadianMarconiCompany            OBJECT IDENTIFIER ::= { enterprises 3863 }
intalk                            OBJECT IDENTIFIER ::= { enterprises 3864 }
thorne                            OBJECT IDENTIFIER ::= { enterprises 3865 }
globalNetCenter                   OBJECT IDENTIFIER ::= { enterprises 3866 }
presenceTechnologyGmbHCoKG        OBJECT IDENTIFIER ::= { enterprises 3867 }
convergysInformationManagementGroup OBJECT IDENTIFIER ::= { enterprises 3868 }
intellilogicNetworks              OBJECT IDENTIFIER ::= { enterprises 3869 }
internetBusinessEmporium          OBJECT IDENTIFIER ::= { enterprises 3870 }
ditechCorporation                 OBJECT IDENTIFIER ::= { enterprises 3871 }
mirandaTechnologies               OBJECT IDENTIFIER ::= { enterprises 3872 }
qlogic                            OBJECT IDENTIFIER ::= { enterprises 3873 }
infovalueComputing                OBJECT IDENTIFIER ::= { enterprises 3874 }
metroComputingConsultants         OBJECT IDENTIFIER ::= { enterprises 3875 }
arinc                             OBJECT IDENTIFIER ::= { enterprises 3876 }
firstAmericanNationalBank         OBJECT IDENTIFIER ::= { enterprises 3877 }
realSoftwareCompany               OBJECT IDENTIFIER ::= { enterprises 3878 }
taiwanTelecommunicationIndustryCo OBJECT IDENTIFIER ::= { enterprises 3879 }
wirelessInformationTransferSystems OBJECT IDENTIFIER ::= { enterprises 3880 }
telefonaktiebolagetLMEricsson     OBJECT IDENTIFIER ::= { enterprises 3881 }
pacomBellPty                      OBJECT IDENTIFIER ::= { enterprises 3882 }
nextPlc                           OBJECT IDENTIFIER ::= { enterprises 3883 }
phobosCorporation                 OBJECT IDENTIFIER ::= { enterprises 3884 }
lifelineSystems                   OBJECT IDENTIFIER ::= { enterprises 3885 }
mimaxInformation                  OBJECT IDENTIFIER ::= { enterprises 3886 }
elderEnterprises                  OBJECT IDENTIFIER ::= { enterprises 3887 }
iapetusSoftware                   OBJECT IDENTIFIER ::= { enterprises 3888 }
ceInfosysGmbH                     OBJECT IDENTIFIER ::= { enterprises 3889 }
acrossWirelessAB                  OBJECT IDENTIFIER ::= { enterprises 3890 }
chicagoBoardOfTrade               OBJECT IDENTIFIER ::= { enterprises 3891 }
ateb                              OBJECT IDENTIFIER ::= { enterprises 3892 }
parksComunicacoesDigitais         OBJECT IDENTIFIER ::= { enterprises 3893 }
pitneyBowes                       OBJECT IDENTIFIER ::= { enterprises 3894 }
adventCommunications              OBJECT IDENTIFIER ::= { enterprises 3895 }
automatedIntegratedSolutions      OBJECT IDENTIFIER ::= { enterprises 3896 }
edisonTechnologySolutions         OBJECT IDENTIFIER ::= { enterprises 3897 }
mitsubishiTelecommunicationsNetworkDivision OBJECT IDENTIFIER ::= { enterprises 3898 }
southChinaMorningPostPublishers   OBJECT IDENTIFIER ::= { enterprises 3899 }
rasterSolutionsPty                OBJECT IDENTIFIER ::= { enterprises 3900 }
managedMessaging                  OBJECT IDENTIFIER ::= { enterprises 3901 }
zteCorporation                    OBJECT IDENTIFIER ::= { enterprises 3902 }
tornadoDevelopment                OBJECT IDENTIFIER ::= { enterprises 3903 }
xlinkInternetServiceGmbH          OBJECT IDENTIFIER ::= { enterprises 3904 }
telenordiaInternet                OBJECT IDENTIFIER ::= { enterprises 3905 }
dataCommunicationTechnologyResearchInstitute OBJECT IDENTIFIER ::= { enterprises 3906 }
californiaIndependentSystemOperator OBJECT IDENTIFIER ::= { enterprises 3907 }
gsp                               OBJECT IDENTIFIER ::= { enterprises 3908 }
nodes                             OBJECT IDENTIFIER ::= { enterprises 3909 }
railtrackPLC                      OBJECT IDENTIFIER ::= { enterprises 3910 }
glasnerConsulting                 OBJECT IDENTIFIER ::= { enterprises 3911 }
gwcom                             OBJECT IDENTIFIER ::= { enterprises 3912 }
arrayTelecomCorp                  OBJECT IDENTIFIER ::= { enterprises 3913 }
tcosoft                           OBJECT IDENTIFIER ::= { enterprises 3914 }
teknisElectronics                 OBJECT IDENTIFIER ::= { enterprises 3915 }
neoCore                           OBJECT IDENTIFIER ::= { enterprises 3916 }
vBits                             OBJECT IDENTIFIER ::= { enterprises 3917 }
watsonWyattWorldwide              OBJECT IDENTIFIER ::= { enterprises 3918 }
montereyNetworks                  OBJECT IDENTIFIER ::= { enterprises 3919 }
csnetConsulting                   OBJECT IDENTIFIER ::= { enterprises 3920 }
aplionNetworks                    OBJECT IDENTIFIER ::= { enterprises 3921 }
operationalResearchConsultants    OBJECT IDENTIFIER ::= { enterprises 3922 }
intrak                            OBJECT IDENTIFIER ::= { enterprises 3923 }
policyManagementSystemsCorp       OBJECT IDENTIFIER ::= { enterprises 3924 }
encompassEnterpriseManagementConsultants OBJECT IDENTIFIER ::= { enterprises 3925 }
newsouthCommunicationsCorp        OBJECT IDENTIFIER ::= { enterprises 3926 }
warpspeedCommunications           OBJECT IDENTIFIER ::= { enterprises 3927 }
sandwichWirelessCommunications    OBJECT IDENTIFIER ::= { enterprises 3928 }
neithCreativeBeauty               OBJECT IDENTIFIER ::= { enterprises 3929 }
nttElectronicsCorporation         OBJECT IDENTIFIER ::= { enterprises 3930 }
easyaccess                        OBJECT IDENTIFIER ::= { enterprises 3931 }
laraTechnology                    OBJECT IDENTIFIER ::= { enterprises 3932 }
nexo                              OBJECT IDENTIFIER ::= { enterprises 3933 }
netWiseCommunications             OBJECT IDENTIFIER ::= { enterprises 3934 }
centroCantonaleD                  OBJECT IDENTIFIER ::= { enterprises 3935 }
sinteca                           OBJECT IDENTIFIER ::= { enterprises 3936 }
emsTechnologiesCanada             OBJECT IDENTIFIER ::= { enterprises 3937 }
deccanTechnologies                OBJECT IDENTIFIER ::= { enterprises 3938 }
internetDevices                   OBJECT IDENTIFIER ::= { enterprises 3939 }
ninetyde                          OBJECT IDENTIFIER ::= { enterprises 3940 }
santakElectronicsCo               OBJECT IDENTIFIER ::= { enterprises 3941 }
aquaProjectGroup                  OBJECT IDENTIFIER ::= { enterprises 3942 }
devanet                           OBJECT IDENTIFIER ::= { enterprises 3943 }
dataSolutionsGroup                OBJECT IDENTIFIER ::= { enterprises 3944 }
sylantroSystems                   OBJECT IDENTIFIER ::= { enterprises 3945 }
conklinCorporation                OBJECT IDENTIFIER ::= { enterprises 3946 }
inverseNetworkTechnology          OBJECT IDENTIFIER ::= { enterprises 3947 }
microlegendTelecomSystems         OBJECT IDENTIFIER ::= { enterprises 3948 }
intrinsixCorporation              OBJECT IDENTIFIER ::= { enterprises 3949 }
tiertwoSystems                    OBJECT IDENTIFIER ::= { enterprises 3950 }
visionikAS                        OBJECT IDENTIFIER ::= { enterprises 3951 }
calyCorporation                   OBJECT IDENTIFIER ::= { enterprises 3952 }
albertAckermannGmbHCoKG           OBJECT IDENTIFIER ::= { enterprises 3953 }
mitraImaging                      OBJECT IDENTIFIER ::= { enterprises 3954 }
linksys                           OBJECT IDENTIFIER ::= { enterprises 3955 }
envox                             OBJECT IDENTIFIER ::= { enterprises 3956 }
globalarchitect                   OBJECT IDENTIFIER ::= { enterprises 3957 }
solutionAssociates                OBJECT IDENTIFIER ::= { enterprises 3958 }
intercallCommunicationsAndConsulting OBJECT IDENTIFIER ::= { enterprises 3959 }
governmentTechnologySolutions     OBJECT IDENTIFIER ::= { enterprises 3960 }
coronaNetworks                    OBJECT IDENTIFIER ::= { enterprises 3961 }
mglGroupeAUBAY                    OBJECT IDENTIFIER ::= { enterprises 3962 }
rcWrightAndAssociates             OBJECT IDENTIFIER ::= { enterprises 3963 }
danetGmbH                         OBJECT IDENTIFIER ::= { enterprises 3964 }
spacebridgeNetworksCorporation    OBJECT IDENTIFIER ::= { enterprises 3965 }
allianzElementarVersicherungsAktiengesellschaften OBJECT IDENTIFIER ::= { enterprises 3966 }
vcsVideoCommunicationSystemsGmbH  OBJECT IDENTIFIER ::= { enterprises 3967 }
weblineCommunicationsCorp         OBJECT IDENTIFIER ::= { enterprises 3968 }
realnetworks                      OBJECT IDENTIFIER ::= { enterprises 3969 }
fragrageNetwork                   OBJECT IDENTIFIER ::= { enterprises 3970 }
imecom                            OBJECT IDENTIFIER ::= { enterprises 3971 }
apsion                            OBJECT IDENTIFIER ::= { enterprises 3972 }
aelitaSoftwareGroup               OBJECT IDENTIFIER ::= { enterprises 3973 }
customInternetworking             OBJECT IDENTIFIER ::= { enterprises 3974 }
bostonCommunicationsGroup         OBJECT IDENTIFIER ::= { enterprises 3975 }
linkdataSolutions                 OBJECT IDENTIFIER ::= { enterprises 3976 }
broadbandNetworks2                OBJECT IDENTIFIER ::= { enterprises 3977 }
ingenieurbueroFuerTelekommunikationsUnd OBJECT IDENTIFIER ::= { enterprises 3978 }
asgaMicroeletronicaSA             OBJECT IDENTIFIER ::= { enterprises 3979 }
homeAccountNetwork                OBJECT IDENTIFIER ::= { enterprises 3980 }
troikaNetworks                    OBJECT IDENTIFIER ::= { enterprises 3981 }
faxnetCorporation                 OBJECT IDENTIFIER ::= { enterprises 3982 }
videoNetworks                     OBJECT IDENTIFIER ::= { enterprises 3983 }
ebscoPublishing                   OBJECT IDENTIFIER ::= { enterprises 3984 }
averyComputerSystems              OBJECT IDENTIFIER ::= { enterprises 3985 }
highwaymaster                     OBJECT IDENTIFIER ::= { enterprises 3986 }
conceptWebcdServicesPvt           OBJECT IDENTIFIER ::= { enterprises 3987 }
finecomCo                         OBJECT IDENTIFIER ::= { enterprises 3988 }
digicommCorporation               OBJECT IDENTIFIER ::= { enterprises 3989 }
innovativeTechnologySoftwareSystems OBJECT IDENTIFIER ::= { enterprises 3990 }
reticom                           OBJECT IDENTIFIER ::= { enterprises 3991 }
ohmegaElectronicProducts          OBJECT IDENTIFIER ::= { enterprises 3992 }
perfectOrder                      OBJECT IDENTIFIER ::= { enterprises 3993 }
virtualResourcesCommunications    OBJECT IDENTIFIER ::= { enterprises 3994 }
vascoDataSecurityInternational    OBJECT IDENTIFIER ::= { enterprises 3995 }
openSystemsAG                     OBJECT IDENTIFIER ::= { enterprises 3996 }
improwareAG                       OBJECT IDENTIFIER ::= { enterprises 3997 }
cherus                            OBJECT IDENTIFIER ::= { enterprises 3998 }
dydx                              OBJECT IDENTIFIER ::= { enterprises 3999 }
hiNetResearchGroup                OBJECT IDENTIFIER ::= { enterprises 4000 }
kadakProducts                     OBJECT IDENTIFIER ::= { enterprises 4001 }
bancoDelBuenAyre                  OBJECT IDENTIFIER ::= { enterprises 4002 }
georgeMasonUniversity             OBJECT IDENTIFIER ::= { enterprises 4003 }
alohaNetworks                     OBJECT IDENTIFIER ::= { enterprises 4004 }
tundoCorporation                  OBJECT IDENTIFIER ::= { enterprises 4005 }
tundoCommunicationAndTelephony    OBJECT IDENTIFIER ::= { enterprises 4006 }
cableAndWirelessCommunicationsPlc OBJECT IDENTIFIER ::= { enterprises 4007 }
ardebilPty                        OBJECT IDENTIFIER ::= { enterprises 4008 }
telephonicsCorporation            OBJECT IDENTIFIER ::= { enterprises 4009 }
dorsaiTechnology                  OBJECT IDENTIFIER ::= { enterprises 4010 }
cnutArchetype                     OBJECT IDENTIFIER ::= { enterprises 4011 }
selectica                         OBJECT IDENTIFIER ::= { enterprises 4012 }
kpmgLLPICETelecomSVO              OBJECT IDENTIFIER ::= { enterprises 4013 }
starburstSoftware                 OBJECT IDENTIFIER ::= { enterprises 4014 }
computerConfigurationsHoldings    OBJECT IDENTIFIER ::= { enterprises 4015 }
iperia                            OBJECT IDENTIFIER ::= { enterprises 4016 }
logisistemSrl                     OBJECT IDENTIFIER ::= { enterprises 4017 }
securityFirstTechnologies         OBJECT IDENTIFIER ::= { enterprises 4018 }
apisSoftwareGmbH                  OBJECT IDENTIFIER ::= { enterprises 4019 }
coopSwitzerland                   OBJECT IDENTIFIER ::= { enterprises 4020 }
ensimCorporation                  OBJECT IDENTIFIER ::= { enterprises 4021 }
aec                               OBJECT IDENTIFIER ::= { enterprises 4022 }
imran                             OBJECT IDENTIFIER ::= { enterprises 4023 }
avantelSA                         OBJECT IDENTIFIER ::= { enterprises 4024 }
lexitech                          OBJECT IDENTIFIER ::= { enterprises 4025 }
internetAccessAG                  OBJECT IDENTIFIER ::= { enterprises 4026 }
gteLaboratories                   OBJECT IDENTIFIER ::= { enterprises 4027 }
decisionNetworks                  OBJECT IDENTIFIER ::= { enterprises 4028 }
nsiCommunicationsSystems          OBJECT IDENTIFIER ::= { enterprises 4029 }
mitsubishiElectricAutomation      OBJECT IDENTIFIER ::= { enterprises 4030 }
orillionCompanies                 OBJECT IDENTIFIER ::= { enterprises 4031 }
datakinetics                      OBJECT IDENTIFIER ::= { enterprises 4032 }
signalCore                        OBJECT IDENTIFIER ::= { enterprises 4033 }
intranet                          OBJECT IDENTIFIER ::= { enterprises 4034 }
ignitusCommunications             OBJECT IDENTIFIER ::= { enterprises 4035 }
enatorTelubAB                     OBJECT IDENTIFIER ::= { enterprises 4036 }
presbyterianChurch                OBJECT IDENTIFIER ::= { enterprises 4037 }
softovAdvancedSystems             OBJECT IDENTIFIER ::= { enterprises 4038 }
mayanNetworksCorporation          OBJECT IDENTIFIER ::= { enterprises 4039 }
microsignalsGroup                 OBJECT IDENTIFIER ::= { enterprises 4040 }
nomuraInternationalPlc            OBJECT IDENTIFIER ::= { enterprises 4041 }
digicommerce                      OBJECT IDENTIFIER ::= { enterprises 4042 }
qnxSoftwareSystems                OBJECT IDENTIFIER ::= { enterprises 4043 }
eloquenceLimited                  OBJECT IDENTIFIER ::= { enterprises 4044 }
thomsonCSFCommunications          OBJECT IDENTIFIER ::= { enterprises 4045 }
scort                             OBJECT IDENTIFIER ::= { enterprises 4046 }
hunanComputerCO                   OBJECT IDENTIFIER ::= { enterprises 4047 }
kinko                             OBJECT IDENTIFIER ::= { enterprises 4048 }
opusComunicacaoDeDados            OBJECT IDENTIFIER ::= { enterprises 4049 }
infuntainmentLimited              OBJECT IDENTIFIER ::= { enterprises 4050 }
sowsearSolutionDesignGroup        OBJECT IDENTIFIER ::= { enterprises 4051 }
vanguardSecurityTechnologies      OBJECT IDENTIFIER ::= { enterprises 4052 }
switchcoreAB                      OBJECT IDENTIFIER ::= { enterprises 4053 }
abatisSystemsCorporation          OBJECT IDENTIFIER ::= { enterprises 4054 }
nimbusSoftwareAS                  OBJECT IDENTIFIER ::= { enterprises 4055 }
streamcore                        OBJECT IDENTIFIER ::= { enterprises 4056 }
controlnet                        OBJECT IDENTIFIER ::= { enterprises 4057 }
generaliOfficeServiceUndConsultingAG OBJECT IDENTIFIER ::= { enterprises 4058 }
broadlogic                        OBJECT IDENTIFIER ::= { enterprises 4059 }
jfaxcom                           OBJECT IDENTIFIER ::= { enterprises 4060 }
technologyControlServices         OBJECT IDENTIFIER ::= { enterprises 4061 }
astralPointCommunications         OBJECT IDENTIFIER ::= { enterprises 4062 }
ascTelecomAG                      OBJECT IDENTIFIER ::= { enterprises 4063 }
elmaOyElectronicTrading           OBJECT IDENTIFIER ::= { enterprises 4064 }
infraservGmbHAndCoGendorfKG       OBJECT IDENTIFIER ::= { enterprises 4065 }
carioliConsulting                 OBJECT IDENTIFIER ::= { enterprises 4066 }
fivemere                          OBJECT IDENTIFIER ::= { enterprises 4067 }
pathway                           OBJECT IDENTIFIER ::= { enterprises 4068 }
ellisonSoftwareConsulting         OBJECT IDENTIFIER ::= { enterprises 4069 }
usWestInternetServices            OBJECT IDENTIFIER ::= { enterprises 4070 }
praimSpA                          OBJECT IDENTIFIER ::= { enterprises 4071 }
qeytonSystemsAB                   OBJECT IDENTIFIER ::= { enterprises 4072 }
telediffusionDeFrance             OBJECT IDENTIFIER ::= { enterprises 4073 }
krutulisEnterprises               OBJECT IDENTIFIER ::= { enterprises 4074 }
sedonaNetworks                    OBJECT IDENTIFIER ::= { enterprises 4075 }
noveraSoftware                    OBJECT IDENTIFIER ::= { enterprises 4076 }
theLimited                        OBJECT IDENTIFIER ::= { enterprises 4077 }
symonCommunications               OBJECT IDENTIFIER ::= { enterprises 4078 }
--                                OBJECT IDENTIFIER ::= { enterprises 4079 }
archangelsRealty                  OBJECT IDENTIFIER ::= { enterprises 4080 }
zelea                             OBJECT IDENTIFIER ::= { enterprises 4081 }
timkoEnterprises                  OBJECT IDENTIFIER ::= { enterprises 4082 }
telecomNewZealand                 OBJECT IDENTIFIER ::= { enterprises 4083 }
trilogyDevelopmentGroup           OBJECT IDENTIFIER ::= { enterprises 4084 }
dibGesFuerStandortbetreiberdiensteMbH OBJECT IDENTIFIER ::= { enterprises 4085 }
ericssonResearchMontreal          OBJECT IDENTIFIER ::= { enterprises 4086 }
uswebCKS                          OBJECT IDENTIFIER ::= { enterprises 4087 }
akuAwekkuAndCo                    OBJECT IDENTIFIER ::= { enterprises 4088 }
salutel                           OBJECT IDENTIFIER ::= { enterprises 4089 }
consorteTeleAS                    OBJECT IDENTIFIER ::= { enterprises 4090 }
infitelItaliaSrl                  OBJECT IDENTIFIER ::= { enterprises 4091 }
computel                          OBJECT IDENTIFIER ::= { enterprises 4092 }
merlotCommunications              OBJECT IDENTIFIER ::= { enterprises 4093 }
qualityTankAndConstructionCo      OBJECT IDENTIFIER ::= { enterprises 4094 }
axentTechnologies2                OBJECT IDENTIFIER ::= { enterprises 4095 }
racalSecurityAndPayments          OBJECT IDENTIFIER ::= { enterprises 4096 }
elanTextToSpeech                  OBJECT IDENTIFIER ::= { enterprises 4097 }
signaalCommunications             OBJECT IDENTIFIER ::= { enterprises 4098 }
tristrata                         OBJECT IDENTIFIER ::= { enterprises 4099 }
wavetekWandelGoltermann           OBJECT IDENTIFIER ::= { enterprises 4100 }
johnHancockFinancialServices      OBJECT IDENTIFIER ::= { enterprises 4101 }
shymTechnology                    OBJECT IDENTIFIER ::= { enterprises 4102 }
cnn                               OBJECT IDENTIFIER ::= { enterprises 4103 }
redwoodTechnologyBV               OBJECT IDENTIFIER ::= { enterprises 4104 }
layerzero                         OBJECT IDENTIFIER ::= { enterprises 4105 }
astrophysikalischesInstitutPotsdam OBJECT IDENTIFIER ::= { enterprises 4106 }
beijingTelecomAdministration      OBJECT IDENTIFIER ::= { enterprises 4107 }
serendip                          OBJECT IDENTIFIER ::= { enterprises 4108 }
durangoSecurityGroup              OBJECT IDENTIFIER ::= { enterprises 4109 }
softstartServices                 OBJECT IDENTIFIER ::= { enterprises 4110 }
teltrend                          OBJECT IDENTIFIER ::= { enterprises 4111 }
tunitasGroup                      OBJECT IDENTIFIER ::= { enterprises 4112 }
tenorNetworks                     OBJECT IDENTIFIER ::= { enterprises 4113 }
t10net                            OBJECT IDENTIFIER ::= { enterprises 4114 }
arrisInteractiveLLC               OBJECT IDENTIFIER ::= { enterprises 4115 }
infointeractive                   OBJECT IDENTIFIER ::= { enterprises 4116 }
entertainmentSystemsTechnology    OBJECT IDENTIFIER ::= { enterprises 4117 }
teslaLiptovskyHradokAs            OBJECT IDENTIFIER ::= { enterprises 4118 }
remoteManagementSystemsPty        OBJECT IDENTIFIER ::= { enterprises 4119 }
sonikTechnologiesCorp             OBJECT IDENTIFIER ::= { enterprises 4120 }
digitalChicagonet                 OBJECT IDENTIFIER ::= { enterprises 4121 }
theUniversityOfTexasHealthScienceCenterAtHouston OBJECT IDENTIFIER ::= { enterprises 4122 }
hitachiAmerica                    OBJECT IDENTIFIER ::= { enterprises 4123 }
unifyConsultingGroup              OBJECT IDENTIFIER ::= { enterprises 4124 }
siemensAGICPKorneliusNehling      OBJECT IDENTIFIER ::= { enterprises 4125 }
responseNetworks                  OBJECT IDENTIFIER ::= { enterprises 4126 }
mercuryComputerSystems            OBJECT IDENTIFIER ::= { enterprises 4127 }
arm                               OBJECT IDENTIFIER ::= { enterprises 4128 }
mnaccari                          OBJECT IDENTIFIER ::= { enterprises 4129 }
microwaveDataSystems              OBJECT IDENTIFIER ::= { enterprises 4130 }
tridium                           OBJECT IDENTIFIER ::= { enterprises 4131 }
connecticutHospitalAssociation    OBJECT IDENTIFIER ::= { enterprises 4132 }
philipjeddycpas                   OBJECT IDENTIFIER ::= { enterprises 4133 }
philipJEddyAndPartnersPty         OBJECT IDENTIFIER ::= { enterprises 4134 }
nicetecGmbH                       OBJECT IDENTIFIER ::= { enterprises 4135 }
uqam                              OBJECT IDENTIFIER ::= { enterprises 4136 }
gauriInfoComm                     OBJECT IDENTIFIER ::= { enterprises 4137 }
sychron                           OBJECT IDENTIFIER ::= { enterprises 4138 }
wapit                             OBJECT IDENTIFIER ::= { enterprises 4139 }
computerAndTelephonySystemsAB     OBJECT IDENTIFIER ::= { enterprises 4140 }
imrWorldwidePty                   OBJECT IDENTIFIER ::= { enterprises 4141 }
fdsNetworksLimited                OBJECT IDENTIFIER ::= { enterprises 4142 }
mAndiDataServices                 OBJECT IDENTIFIER ::= { enterprises 4143 }
pricewaterhousecoopersFP5         OBJECT IDENTIFIER ::= { enterprises 4144 }
cristieDataProductsLimited        OBJECT IDENTIFIER ::= { enterprises 4145 }
globalsignNVSA                    OBJECT IDENTIFIER ::= { enterprises 4146 }
zuercherKantonalbank              OBJECT IDENTIFIER ::= { enterprises 4147 }
dewitt                            OBJECT IDENTIFIER ::= { enterprises 4148 }
accrueSoftware                    OBJECT IDENTIFIER ::= { enterprises 4149 }
northwesternMutualLifeInsuranceCompany OBJECT IDENTIFIER ::= { enterprises 4150 }
impathNetworks                    OBJECT IDENTIFIER ::= { enterprises 4151 }
twoWayTV                          OBJECT IDENTIFIER ::= { enterprises 4152 }
simpleNetworks                    OBJECT IDENTIFIER ::= { enterprises 4153 }
versaTechnology                   OBJECT IDENTIFIER ::= { enterprises 4154 }
cemoc                             OBJECT IDENTIFIER ::= { enterprises 4155 }
newAccessCommunications           OBJECT IDENTIFIER ::= { enterprises 4156 }
bceEmergis                        OBJECT IDENTIFIER ::= { enterprises 4157 }
milmanConsulting                  OBJECT IDENTIFIER ::= { enterprises 4158 }
electronicTheatreControls         OBJECT IDENTIFIER ::= { enterprises 4159 }
viveSynergies                     OBJECT IDENTIFIER ::= { enterprises 4160 }
qteraCorporation                  OBJECT IDENTIFIER ::= { enterprises 4161 }
inputOutput                       OBJECT IDENTIFIER ::= { enterprises 4162 }
quarryTechnologies                OBJECT IDENTIFIER ::= { enterprises 4163 }
seElectronics                     OBJECT IDENTIFIER ::= { enterprises 4165 }
theMercyFoundation                OBJECT IDENTIFIER ::= { enterprises 4166 }
markusLauerEDVEntwicklung         OBJECT IDENTIFIER ::= { enterprises 4167 }
systemsManagementSpecialists      OBJECT IDENTIFIER ::= { enterprises 4168 }
syzygySolutions                   OBJECT IDENTIFIER ::= { enterprises 4169 }
universityOfWisconsinMilwaukee    OBJECT IDENTIFIER ::= { enterprises 4170 }
bosungDataCommunicationCo         OBJECT IDENTIFIER ::= { enterprises 4171 }
naraeInformationAndCommunicationEnterprise OBJECT IDENTIFIER ::= { enterprises 4172 }
dassaultAT                        OBJECT IDENTIFIER ::= { enterprises 4173 }
criticalDevices                   OBJECT IDENTIFIER ::= { enterprises 4174 }
tessler                           OBJECT IDENTIFIER ::= { enterprises 4175 }
newtonSolutions                   OBJECT IDENTIFIER ::= { enterprises 4176 }
reddingEnterprises                OBJECT IDENTIFIER ::= { enterprises 4177 }
aspectSoftware                    OBJECT IDENTIFIER ::= { enterprises 4178 }
commercialTechnologiesCorp        OBJECT IDENTIFIER ::= { enterprises 4179 }
talkstarcom                       OBJECT IDENTIFIER ::= { enterprises 4180 }
genericTelecom                    OBJECT IDENTIFIER ::= { enterprises 4181 }
leningradNuclearPowerPlant        OBJECT IDENTIFIER ::= { enterprises 4182 }
hammerTechnologies                OBJECT IDENTIFIER ::= { enterprises 4183 }
smsSharedMedicalSystems           OBJECT IDENTIFIER ::= { enterprises 4184 }
synchronixSoftware                OBJECT IDENTIFIER ::= { enterprises 4185 }
akaConsulting                     OBJECT IDENTIFIER ::= { enterprises 4186 }
storageAreaNetworks               OBJECT IDENTIFIER ::= { enterprises 4187 }
realizeCommunications             OBJECT IDENTIFIER ::= { enterprises 4188 }
egisKK                            OBJECT IDENTIFIER ::= { enterprises 4189 }
etradeSecurities                  OBJECT IDENTIFIER ::= { enterprises 4190 }
sigosSystemintegrationGmbH        OBJECT IDENTIFIER ::= { enterprises 4191 }
tennesseeValleyAuthority          OBJECT IDENTIFIER ::= { enterprises 4192 }
vutBRNO                           OBJECT IDENTIFIER ::= { enterprises 4193 }
leoniaPlc                         OBJECT IDENTIFIER ::= { enterprises 4194 }
telesoft                          OBJECT IDENTIFIER ::= { enterprises 4195 }
siemensAGAutomationAndDrives      OBJECT IDENTIFIER ::= { enterprises 4196 }
capGeminiDenmarkAS                OBJECT IDENTIFIER ::= { enterprises 4197 }
vpnConsortium                     OBJECT IDENTIFIER ::= { enterprises 4198 }
cellnetDataSystems                OBJECT IDENTIFIER ::= { enterprises 4199 }
fastSearchAndTransfer             OBJECT IDENTIFIER ::= { enterprises 4200 }
tonnaElectronique                 OBJECT IDENTIFIER ::= { enterprises 4201 }
samwooTelecommunicationsCo        OBJECT IDENTIFIER ::= { enterprises 4202 }
theOpenLDAPFoundation             OBJECT IDENTIFIER ::= { enterprises 4203 }
adtecCo                           OBJECT IDENTIFIER ::= { enterprises 4204 }
durakUnlimited                    OBJECT IDENTIFIER ::= { enterprises 4205 }
mitaIndustrialCo                  OBJECT IDENTIFIER ::= { enterprises 4206 }
daydreamPromotions                OBJECT IDENTIFIER ::= { enterprises 4207 }
tantivyCommunications             OBJECT IDENTIFIER ::= { enterprises 4208 }
cdvs                              OBJECT IDENTIFIER ::= { enterprises 4209 }
assumptionUniversity              OBJECT IDENTIFIER ::= { enterprises 4210 }
corillian                         OBJECT IDENTIFIER ::= { enterprises 4211 }
spmSystementwicklungUndProjektmanagementGmbH OBJECT IDENTIFIER ::= { enterprises 4212 }
infrax                            OBJECT IDENTIFIER ::= { enterprises 4213 }
sunquestInformationSystems        OBJECT IDENTIFIER ::= { enterprises 4214 }
silkroad                          OBJECT IDENTIFIER ::= { enterprises 4215 }
tritonNetworkSystems              OBJECT IDENTIFIER ::= { enterprises 4216 }
opalis                            OBJECT IDENTIFIER ::= { enterprises 4217 }
geckoSoftwareLimited              OBJECT IDENTIFIER ::= { enterprises 4218 }
regioconnectGmbH                  OBJECT IDENTIFIER ::= { enterprises 4219 }
arcanvs                           OBJECT IDENTIFIER ::= { enterprises 4220 }
soundscaipe                       OBJECT IDENTIFIER ::= { enterprises 4221 }
ondisplay                         OBJECT IDENTIFIER ::= { enterprises 4222 }
milgoSolutions                    OBJECT IDENTIFIER ::= { enterprises 4223 }
johnHHarlandCompany               OBJECT IDENTIFIER ::= { enterprises 4224 }
peachNetworks                     OBJECT IDENTIFIER ::= { enterprises 4225 }
compositCommunications            OBJECT IDENTIFIER ::= { enterprises 4226 }
sixtraChileSA                     OBJECT IDENTIFIER ::= { enterprises 4227 }
dascom                            OBJECT IDENTIFIER ::= { enterprises 4228 }
westfairFoods                     OBJECT IDENTIFIER ::= { enterprises 4229 }
pirouette                         OBJECT IDENTIFIER ::= { enterprises 4230 }
obTelematics                      OBJECT IDENTIFIER ::= { enterprises 4231 }
ctxOptoElectronicsCorp            OBJECT IDENTIFIER ::= { enterprises 4232 }
dalianDaxianNetworkSystemColtd    OBJECT IDENTIFIER ::= { enterprises 4233 }
pragma                            OBJECT IDENTIFIER ::= { enterprises 4234 }
cultureshockMultimedia            OBJECT IDENTIFIER ::= { enterprises 4235 }
spectel                           OBJECT IDENTIFIER ::= { enterprises 4236 }
busbySoftware                     OBJECT IDENTIFIER ::= { enterprises 4237 }
mediaStation                      OBJECT IDENTIFIER ::= { enterprises 4238 }
kommunedataAS                     OBJECT IDENTIFIER ::= { enterprises 4239 }
mannesmannDatenverarbeitungGmbH   OBJECT IDENTIFIER ::= { enterprises 4240 }
peakstoneCorporation              OBJECT IDENTIFIER ::= { enterprises 4241 }
theCloroxCompany                  OBJECT IDENTIFIER ::= { enterprises 4242 }
npoInfoservice                    OBJECT IDENTIFIER ::= { enterprises 4243 }
cinnabarNetworks                  OBJECT IDENTIFIER ::= { enterprises 4244 }
postenSDSAS                       OBJECT IDENTIFIER ::= { enterprises 4245 }
comverseNetworkSystems            OBJECT IDENTIFIER ::= { enterprises 4246 }
theUniversityOfEdinburgh          OBJECT IDENTIFIER ::= { enterprises 4247 }
interconexionElectricaSA          OBJECT IDENTIFIER ::= { enterprises 4248 }
nateks                            OBJECT IDENTIFIER ::= { enterprises 4249 }
hitIndustriesSales                OBJECT IDENTIFIER ::= { enterprises 4250 }
systemDesignRepair                OBJECT IDENTIFIER ::= { enterprises 4251 }
highSpeedAccess                   OBJECT IDENTIFIER ::= { enterprises 4252 }
luxn                              OBJECT IDENTIFIER ::= { enterprises 4253 }
bertelsmannMedaiSystems           OBJECT IDENTIFIER ::= { enterprises 4254 }
perfectoTechnologies              OBJECT IDENTIFIER ::= { enterprises 4255 }
kiplingInformationTechnologyAB    OBJECT IDENTIFIER ::= { enterprises 4256 }
cyberstation                      OBJECT IDENTIFIER ::= { enterprises 4257 }
open4rent                         OBJECT IDENTIFIER ::= { enterprises 4258 }
fdp                               OBJECT IDENTIFIER ::= { enterprises 4259 }
threeRdMillenniumConsulting       OBJECT IDENTIFIER ::= { enterprises 4260 }
globolSolutions                   OBJECT IDENTIFIER ::= { enterprises 4261 }
jeanclaudeMetalCraft              OBJECT IDENTIFIER ::= { enterprises 4262 }
drAndreasMuller                   OBJECT IDENTIFIER ::= { enterprises 4263 }
worldRamp                         OBJECT IDENTIFIER ::= { enterprises 4264 }
tachionNetworkTechnologies        OBJECT IDENTIFIER ::= { enterprises 4265 }
fernuniversitaetHagen             OBJECT IDENTIFIER ::= { enterprises 4266 }
transcend                         OBJECT IDENTIFIER ::= { enterprises 4267 }
banctecComputerAndNetworkServices OBJECT IDENTIFIER ::= { enterprises 4268 }
worldportCommunications           OBJECT IDENTIFIER ::= { enterprises 4269 }
edvBeratungBlechschmidt           OBJECT IDENTIFIER ::= { enterprises 4270 }
nevexSoftwareTechnologies         OBJECT IDENTIFIER ::= { enterprises 4271 }
exactSolutions                    OBJECT IDENTIFIER ::= { enterprises 4272 }
leroyAUTOMATIQUEINDUSTRIELLE      OBJECT IDENTIFIER ::= { enterprises 4273 }
pangolinUK                        OBJECT IDENTIFIER ::= { enterprises 4274 }
dukeUniversity                    OBJECT IDENTIFIER ::= { enterprises 4275 }
pcsInnovations                    OBJECT IDENTIFIER ::= { enterprises 4276 }
telocityCommunications            OBJECT IDENTIFIER ::= { enterprises 4277 }
yahoo                             OBJECT IDENTIFIER ::= { enterprises 4278 }
siroccoSystems                    OBJECT IDENTIFIER ::= { enterprises 4279 }
artemGmbH                         OBJECT IDENTIFIER ::= { enterprises 4280 }
assumption                        OBJECT IDENTIFIER ::= { enterprises 4281 }
kencast                           OBJECT IDENTIFIER ::= { enterprises 4282 }
dualZentrumnGmbH                  OBJECT IDENTIFIER ::= { enterprises 4283 }
norwebInternettTjenester          OBJECT IDENTIFIER ::= { enterprises 4284 }
ruslanCommunications              OBJECT IDENTIFIER ::= { enterprises 4285 }
eSecurity                         OBJECT IDENTIFIER ::= { enterprises 4286 }
philipsConsumerElectronics        OBJECT IDENTIFIER ::= { enterprises 4287 }
forgeResearchPty                  OBJECT IDENTIFIER ::= { enterprises 4288 }
vbrickSystems                     OBJECT IDENTIFIER ::= { enterprises 4289 }
logicInnovations                  OBJECT IDENTIFIER ::= { enterprises 4290 }
chordiantSoftware                 OBJECT IDENTIFIER ::= { enterprises 4291 }
entera                            OBJECT IDENTIFIER ::= { enterprises 4292 }
bensons                           OBJECT IDENTIFIER ::= { enterprises 4293 }
salbu                             OBJECT IDENTIFIER ::= { enterprises 4294 }
kalkiCommunicationTechnologiesPvt OBJECT IDENTIFIER ::= { enterprises 4295 }
cenforSL                          OBJECT IDENTIFIER ::= { enterprises 4296 }
finisarCorporation                OBJECT IDENTIFIER ::= { enterprises 4297 }
etc                               OBJECT IDENTIFIER ::= { enterprises 4298 }
openSolutionProviders             OBJECT IDENTIFIER ::= { enterprises 4299 }
inmonCorp                         OBJECT IDENTIFIER ::= { enterprises 4300 }
uniserveConsultingLimited         OBJECT IDENTIFIER ::= { enterprises 4301 }
cybexComputerProductsCorporation  OBJECT IDENTIFIER ::= { enterprises 4302 }
camart                            OBJECT IDENTIFIER ::= { enterprises 4303 }
csiroDivOfAnimalHealth            OBJECT IDENTIFIER ::= { enterprises 4304 }
universityOfMaryland              OBJECT IDENTIFIER ::= { enterprises 4305 }
jmdelSystems                      OBJECT IDENTIFIER ::= { enterprises 4306 }
officeConnect                     OBJECT IDENTIFIER ::= { enterprises 4307 }
consejoSuperiorDeCamaras          OBJECT IDENTIFIER ::= { enterprises 4308 }
ipTechnologies                    OBJECT IDENTIFIER ::= { enterprises 4309 }
uniqueComputerServices            OBJECT IDENTIFIER ::= { enterprises 4310 }
equinix                           OBJECT IDENTIFIER ::= { enterprises 4311 }
vitaSystems                       OBJECT IDENTIFIER ::= { enterprises 4312 }
allayerTechnologies               OBJECT IDENTIFIER ::= { enterprises 4313 }
xilinx                            OBJECT IDENTIFIER ::= { enterprises 4314 }
xacctTechnologies                 OBJECT IDENTIFIER ::= { enterprises 4315 }
brandeisUniversity                OBJECT IDENTIFIER ::= { enterprises 4316 }
javelinTechnologyCorp             OBJECT IDENTIFIER ::= { enterprises 4317 }
edixia                            OBJECT IDENTIFIER ::= { enterprises 4318 }
ennovateNetworks                  OBJECT IDENTIFIER ::= { enterprises 4319 }
freshwaterSoftware                OBJECT IDENTIFIER ::= { enterprises 4320 }
riverbedTechnologies              OBJECT IDENTIFIER ::= { enterprises 4321 }
murataMachinery                   OBJECT IDENTIFIER ::= { enterprises 4322 }
quantumBridge                     OBJECT IDENTIFIER ::= { enterprises 4323 }
saejinTAndMCo                     OBJECT IDENTIFIER ::= { enterprises 4324 }
apertoNetworks                    OBJECT IDENTIFIER ::= { enterprises 4325 }
crownInternational                OBJECT IDENTIFIER ::= { enterprises 4326 }
tradingWorldCom                   OBJECT IDENTIFIER ::= { enterprises 4327 }
miSystems                         OBJECT IDENTIFIER ::= { enterprises 4328 }
siemens                           OBJECT IDENTIFIER ::= { enterprises 4329 }
pmcSierra                         OBJECT IDENTIFIER ::= { enterprises 4330 }
aventailCorporation               OBJECT IDENTIFIER ::= { enterprises 4331 }
instituteOfSystemsAndInformationTechnologiesKYUSHU OBJECT IDENTIFIER ::= { enterprises 4332 }
insightTechnology                 OBJECT IDENTIFIER ::= { enterprises 4333 }
ampersandChantillyCommunications  OBJECT IDENTIFIER ::= { enterprises 4334 }
techworld                         OBJECT IDENTIFIER ::= { enterprises 4335 }
expertechPty                      OBJECT IDENTIFIER ::= { enterprises 4336 }
radisysCorp                       OBJECT IDENTIFIER ::= { enterprises 4337 }
caseCorporation                   OBJECT IDENTIFIER ::= { enterprises 4338 }
rhodeIslandEconomicDevelopmentCorporation OBJECT IDENTIFIER ::= { enterprises 4339 }
bacteriophageLambda               OBJECT IDENTIFIER ::= { enterprises 4340 }
spiderInternetServices            OBJECT IDENTIFIER ::= { enterprises 4341 }
ushealthRealEstate                OBJECT IDENTIFIER ::= { enterprises 4342 }
boundlessTechnologies             OBJECT IDENTIFIER ::= { enterprises 4343 }
postIndustrialTrainingInstitute   OBJECT IDENTIFIER ::= { enterprises 4344 }
thomasAndBetts                    OBJECT IDENTIFIER ::= { enterprises 4345 }
phoenixContactGmbHAndCo           OBJECT IDENTIFIER ::= { enterprises 4346 }
messagewise                       OBJECT IDENTIFIER ::= { enterprises 4347 }
dominoComputersNigeria            OBJECT IDENTIFIER ::= { enterprises 4348 }
lxcoTechnologiesAG                OBJECT IDENTIFIER ::= { enterprises 4349 }
maxpertAG                         OBJECT IDENTIFIER ::= { enterprises 4350 }
networkSystemsGroup               OBJECT IDENTIFIER ::= { enterprises 4351 }
urgle                             OBJECT IDENTIFIER ::= { enterprises 4352 }
buildersNetwork                   OBJECT IDENTIFIER ::= { enterprises 4353 }
netdragon                         OBJECT IDENTIFIER ::= { enterprises 4354 }
rapidstream                       OBJECT IDENTIFIER ::= { enterprises 4355 }
informGmbHAndCoKG                 OBJECT IDENTIFIER ::= { enterprises 4356 }
coteng                            OBJECT IDENTIFIER ::= { enterprises 4357 }
ziatechCorporation                OBJECT IDENTIFIER ::= { enterprises 4358 }
telgenCorporation                 OBJECT IDENTIFIER ::= { enterprises 4359 }
tumbleweedCommunications          OBJECT IDENTIFIER ::= { enterprises 4360 }
amgen                             OBJECT IDENTIFIER ::= { enterprises 4361 }
nyloracSoftware                   OBJECT IDENTIFIER ::= { enterprises 4362 }
universityOfBristol               OBJECT IDENTIFIER ::= { enterprises 4363 }
bvSolutionsGroup                  OBJECT IDENTIFIER ::= { enterprises 4364 }
myowngig                          OBJECT IDENTIFIER ::= { enterprises 4365 }
locusCorp                         OBJECT IDENTIFIER ::= { enterprises 4366 }
electronicLaboratoryServicesCC    OBJECT IDENTIFIER ::= { enterprises 4367 }
handGmbH                          OBJECT IDENTIFIER ::= { enterprises 4368 }
nishanSystems                     OBJECT IDENTIFIER ::= { enterprises 4369 }
tokyoDisneySea                    OBJECT IDENTIFIER ::= { enterprises 4370 }
digitalUnited                     OBJECT IDENTIFIER ::= { enterprises 4371 }
softlinkSro                       OBJECT IDENTIFIER ::= { enterprises 4372 }
rivereCorporation                 OBJECT IDENTIFIER ::= { enterprises 4373 }
motiveCommunications              OBJECT IDENTIFIER ::= { enterprises 4374 }
dtResearch                        OBJECT IDENTIFIER ::= { enterprises 4375 }
nettechSystems                    OBJECT IDENTIFIER ::= { enterprises 4376 }
xPointCommunications              OBJECT IDENTIFIER ::= { enterprises 4377 }
hitzFMBroadcasters                OBJECT IDENTIFIER ::= { enterprises 4378 }
alienInternetServices             OBJECT IDENTIFIER ::= { enterprises 4379 }
elipseSoftware                    OBJECT IDENTIFIER ::= { enterprises 4380 }
astracon                          OBJECT IDENTIFIER ::= { enterprises 4381 }
aladdinKnowledgeSystems           OBJECT IDENTIFIER ::= { enterprises 4382 }
glasseycom                        OBJECT IDENTIFIER ::= { enterprises 4383 }
meridianus                        OBJECT IDENTIFIER ::= { enterprises 4384 }
stimeorgWG                        OBJECT IDENTIFIER ::= { enterprises 4385 }
teleDanmarkInternet               OBJECT IDENTIFIER ::= { enterprises 4386 }
ubique                            OBJECT IDENTIFIER ::= { enterprises 4387 }
alcatelAltechTelecoms             OBJECT IDENTIFIER ::= { enterprises 4388 }
sysDis                            OBJECT IDENTIFIER ::= { enterprises 4389 }
kemperInsurance                   OBJECT IDENTIFIER ::= { enterprises 4390 }
texasAAndMUniversity              OBJECT IDENTIFIER ::= { enterprises 4391 }
northbrookServices                OBJECT IDENTIFIER ::= { enterprises 4392 }
pentacom                          OBJECT IDENTIFIER ::= { enterprises 4393 }
softfx                            OBJECT IDENTIFIER ::= { enterprises 4394 }
unifiedTechnologiesSverigeHB      OBJECT IDENTIFIER ::= { enterprises 4395 }
theOpenGroup                      OBJECT IDENTIFIER ::= { enterprises 4396 }
opentradeTechnologies             OBJECT IDENTIFIER ::= { enterprises 4397 }
bAndlAssociates                   OBJECT IDENTIFIER ::= { enterprises 4398 }
johnsonControls                   OBJECT IDENTIFIER ::= { enterprises 4399 }
cypressCorporation                OBJECT IDENTIFIER ::= { enterprises 4400 }
moonvine                          OBJECT IDENTIFIER ::= { enterprises 4401 }
netpredict                        OBJECT IDENTIFIER ::= { enterprises 4402 }
visualBrain                       OBJECT IDENTIFIER ::= { enterprises 4403 }
networkManagementSolutions        OBJECT IDENTIFIER ::= { enterprises 4404 }
ansid                             OBJECT IDENTIFIER ::= { enterprises 4405 }
toyoInformationSystemsCo          OBJECT IDENTIFIER ::= { enterprises 4406 }
dracom                            OBJECT IDENTIFIER ::= { enterprises 4407 }
edsl                              OBJECT IDENTIFIER ::= { enterprises 4408 }
campusPipeline                    OBJECT IDENTIFIER ::= { enterprises 4409 }
earthStarGroup                    OBJECT IDENTIFIER ::= { enterprises 4410 }
swinburnecom                      OBJECT IDENTIFIER ::= { enterprises 4411 }
wroxPress                         OBJECT IDENTIFIER ::= { enterprises 4412 }
broadcomCorporation               OBJECT IDENTIFIER ::= { enterprises 4413 }
scandinavianSoftlineTechnologyOy  OBJECT IDENTIFIER ::= { enterprises 4414 }
floridaDepartmentOfLawEnforcement OBJECT IDENTIFIER ::= { enterprises 4415 }
starfireExperts                   OBJECT IDENTIFIER ::= { enterprises 4416 }
alidianNetworks                   OBJECT IDENTIFIER ::= { enterprises 4417 }
megasysComputerTechnologies       OBJECT IDENTIFIER ::= { enterprises 4418 }
sonyOnlineEntertainment           OBJECT IDENTIFIER ::= { enterprises 4419 }
westicaLimited                    OBJECT IDENTIFIER ::= { enterprises 4420 }
santeraSystems                    OBJECT IDENTIFIER ::= { enterprises 4421 }
gteIT                             OBJECT IDENTIFIER ::= { enterprises 4422 }
garnetSystemsCo                   OBJECT IDENTIFIER ::= { enterprises 4423 }
rapidLogic                        OBJECT IDENTIFIER ::= { enterprises 4424 }
metaGymnastics                    OBJECT IDENTIFIER ::= { enterprises 4425 }
fujitsuAustraliaSoftwareTechnologyPty OBJECT IDENTIFIER ::= { enterprises 4426 }
pironetIntranetAG                 OBJECT IDENTIFIER ::= { enterprises 4427 }
supercomputingSystemsAG           OBJECT IDENTIFIER ::= { enterprises 4428 }
megachipsCorporation              OBJECT IDENTIFIER ::= { enterprises 4429 }
siliconAutomationSystems          OBJECT IDENTIFIER ::= { enterprises 4430 }
netia                             OBJECT IDENTIFIER ::= { enterprises 4431 }
netlockTechnologies               OBJECT IDENTIFIER ::= { enterprises 4432 }
strategicFinancialPlanning        OBJECT IDENTIFIER ::= { enterprises 4433 }
bluestoneSoftware                 OBJECT IDENTIFIER ::= { enterprises 4434 }
suedtirolerInformatikAG           OBJECT IDENTIFIER ::= { enterprises 4435 }
missionCritical                   OBJECT IDENTIFIER ::= { enterprises 4436 }
canadianImperialBankOfCommerce    OBJECT IDENTIFIER ::= { enterprises 4437 }
goteborgEnergiAB                  OBJECT IDENTIFIER ::= { enterprises 4438 }
enzaneEnterprise                  OBJECT IDENTIFIER ::= { enterprises 4439 }
purdueUniversity                  OBJECT IDENTIFIER ::= { enterprises 4440 }
geCapitalFleetServices            OBJECT IDENTIFIER ::= { enterprises 4441 }
kara                              OBJECT IDENTIFIER ::= { enterprises 4442 }
nedBoddieAndAssoc                 OBJECT IDENTIFIER ::= { enterprises 4443 }
sainco                            OBJECT IDENTIFIER ::= { enterprises 4444 }
interSarl                         OBJECT IDENTIFIER ::= { enterprises 4445 }
prairieDevelopment                OBJECT IDENTIFIER ::= { enterprises 4446 }
rochesterInstituteOfTechnology    OBJECT IDENTIFIER ::= { enterprises 4447 }
eLockTechnologies                 OBJECT IDENTIFIER ::= { enterprises 4448 }
sshCommunicationsSecurity         OBJECT IDENTIFIER ::= { enterprises 4449 }
icConsult                         OBJECT IDENTIFIER ::= { enterprises 4450 }
morion                            OBJECT IDENTIFIER ::= { enterprises 4451 }
telenor4tel                       OBJECT IDENTIFIER ::= { enterprises 4452 }
infonetServicesCorp               OBJECT IDENTIFIER ::= { enterprises 4453 }
gottfriedWebAndComputerConsulting OBJECT IDENTIFIER ::= { enterprises 4454 }
iBusCorporation                   OBJECT IDENTIFIER ::= { enterprises 4455 }
qualimetrics                      OBJECT IDENTIFIER ::= { enterprises 4456 }
amenamencom                       OBJECT IDENTIFIER ::= { enterprises 4457 }
radwin                            OBJECT IDENTIFIER ::= { enterprises 4458 }
industreeBV                       OBJECT IDENTIFIER ::= { enterprises 4459 }
firstworldCommunications          OBJECT IDENTIFIER ::= { enterprises 4460 }
opennetworkTechnologies           OBJECT IDENTIFIER ::= { enterprises 4461 }
svmMicrowaves                     OBJECT IDENTIFIER ::= { enterprises 4462 }
taonet                            OBJECT IDENTIFIER ::= { enterprises 4463 }
mpbCommunications                 OBJECT IDENTIFIER ::= { enterprises 4464 }
viewcastcom                       OBJECT IDENTIFIER ::= { enterprises 4465 }
tadiranScopus                     OBJECT IDENTIFIER ::= { enterprises 4466 }
fibrolan                          OBJECT IDENTIFIER ::= { enterprises 4467 }
telkoorQPS                        OBJECT IDENTIFIER ::= { enterprises 4468 }
diversinetCorp                    OBJECT IDENTIFIER ::= { enterprises 4469 }
teledream                         OBJECT IDENTIFIER ::= { enterprises 4470 }
networkSecurityWizards            OBJECT IDENTIFIER ::= { enterprises 4471 }
montageITServices                 OBJECT IDENTIFIER ::= { enterprises 4472 }
opto22                            OBJECT IDENTIFIER ::= { enterprises 4473 }
paxcomm                           OBJECT IDENTIFIER ::= { enterprises 4474 }
rainbowSoftwareSolutions          OBJECT IDENTIFIER ::= { enterprises 4475 }
lightrealm                        OBJECT IDENTIFIER ::= { enterprises 4476 }
infocomSystemsServices            OBJECT IDENTIFIER ::= { enterprises 4477 }
alacritech                        OBJECT IDENTIFIER ::= { enterprises 4478 }
spectrapointWirelessLLC           OBJECT IDENTIFIER ::= { enterprises 4479 }
fastforwardNetworks               OBJECT IDENTIFIER ::= { enterprises 4480 }
ciaEurope                         OBJECT IDENTIFIER ::= { enterprises 4481 }
rweAG                             OBJECT IDENTIFIER ::= { enterprises 4482 }
ibiCo                             OBJECT IDENTIFIER ::= { enterprises 4483 }
pacificSoftworks                  OBJECT IDENTIFIER ::= { enterprises 4484 }
dataportCommunications            OBJECT IDENTIFIER ::= { enterprises 4485 }
verioWebHosting                   OBJECT IDENTIFIER ::= { enterprises 4486 }
johnsonAndJohnsonNCS              OBJECT IDENTIFIER ::= { enterprises 4487 }
mediahouseSoftware                OBJECT IDENTIFIER ::= { enterprises 4488 }
sierraNetworks                    OBJECT IDENTIFIER ::= { enterprises 4489 }
polygonConsultantsInInformatics   OBJECT IDENTIFIER ::= { enterprises 4490 }
cableTelevisionLaboratories       OBJECT IDENTIFIER ::= { enterprises 4491 }
solutionsoftSystems               OBJECT IDENTIFIER ::= { enterprises 4492 }
unirelSistemiSrlMauroFantechi     OBJECT IDENTIFIER ::= { enterprises 4493 }
novartisAG                        OBJECT IDENTIFIER ::= { enterprises 4494 }
taimaCorp                         OBJECT IDENTIFIER ::= { enterprises 4495 }
siemensCanada                     OBJECT IDENTIFIER ::= { enterprises 4496 }
availNetworks                     OBJECT IDENTIFIER ::= { enterprises 4497 }
netqos                            OBJECT IDENTIFIER ::= { enterprises 4498 }
safefundscom                      OBJECT IDENTIFIER ::= { enterprises 4499 }
jordanTech                        OBJECT IDENTIFIER ::= { enterprises 4500 }
efornetCorporation                OBJECT IDENTIFIER ::= { enterprises 4501 }
playbeingorg                      OBJECT IDENTIFIER ::= { enterprises 4502 }
corporateInformationTechnologies  OBJECT IDENTIFIER ::= { enterprises 4503 }
seamlessKludgeInternetworkingLabs OBJECT IDENTIFIER ::= { enterprises 4504 }
caltexAustraliaPetroleumPty       OBJECT IDENTIFIER ::= { enterprises 4505 }
channelsMeasurementServices       OBJECT IDENTIFIER ::= { enterprises 4506 }
theMiamiHerald                    OBJECT IDENTIFIER ::= { enterprises 4507 }
geeksLikeUs                       OBJECT IDENTIFIER ::= { enterprises 4508 }
nakayoTelecommunications          OBJECT IDENTIFIER ::= { enterprises 4509 }
dracom2                           OBJECT IDENTIFIER ::= { enterprises 4510 }
concordEracomComputerSecurityGmbH OBJECT IDENTIFIER ::= { enterprises 4511 }
sofreavia                         OBJECT IDENTIFIER ::= { enterprises 4512 }
terawaveCommunications            OBJECT IDENTIFIER ::= { enterprises 4513 }
bankAmerica                       OBJECT IDENTIFIER ::= { enterprises 4514 }
packetlightNetworks               OBJECT IDENTIFIER ::= { enterprises 4515 }
sias                              OBJECT IDENTIFIER ::= { enterprises 4516 }
helius                            OBJECT IDENTIFIER ::= { enterprises 4517 }
kmzConsultingGroup                OBJECT IDENTIFIER ::= { enterprises 4518 }
veroElectronics                   OBJECT IDENTIFIER ::= { enterprises 4519 }
joohongInformationAndCommunications OBJECT IDENTIFIER ::= { enterprises 4520 }
globalADSISoltuions               OBJECT IDENTIFIER ::= { enterprises 4521 }
ontarioPowerGeneration            OBJECT IDENTIFIER ::= { enterprises 4522 }
exalink                           OBJECT IDENTIFIER ::= { enterprises 4523 }
storagesoft                       OBJECT IDENTIFIER ::= { enterprises 4524 }
micronTechnology                  OBJECT IDENTIFIER ::= { enterprises 4525 }
netgear                           OBJECT IDENTIFIER ::= { enterprises 4526 }
zeitgeistY2k01                    OBJECT IDENTIFIER ::= { enterprises 4527 }
x8                                OBJECT IDENTIFIER ::= { enterprises 4528 }
internetServiceDept               OBJECT IDENTIFIER ::= { enterprises 4529 }
tunbridgeWellsEquitableFriendlySociety OBJECT IDENTIFIER ::= { enterprises 4530 }
onTechnologyCorporation           OBJECT IDENTIFIER ::= { enterprises 4531 }
gvctwCorporation                  OBJECT IDENTIFIER ::= { enterprises 4532 }
atcommCorporation                 OBJECT IDENTIFIER ::= { enterprises 4533 }
oneboxcom                         OBJECT IDENTIFIER ::= { enterprises 4534 }
javelinxCorporation               OBJECT IDENTIFIER ::= { enterprises 4535 }
digitech                          OBJECT IDENTIFIER ::= { enterprises 4536 }
planexCommunications              OBJECT IDENTIFIER ::= { enterprises 4537 }
easybuy                           OBJECT IDENTIFIER ::= { enterprises 4538 }
remarqCommunities                 OBJECT IDENTIFIER ::= { enterprises 4539 }
intelectNetworkTechnologies       OBJECT IDENTIFIER ::= { enterprises 4540 }
outreachTechnologies              OBJECT IDENTIFIER ::= { enterprises 4541 }
alertingSpecificationsForum       OBJECT IDENTIFIER ::= { enterprises 4542 }
digitellum                        OBJECT IDENTIFIER ::= { enterprises 4543 }
gjensidigeForsikring              OBJECT IDENTIFIER ::= { enterprises 4544 }
atlantisSoftware                  OBJECT IDENTIFIER ::= { enterprises 4545 }
astEngineeringServices            OBJECT IDENTIFIER ::= { enterprises 4546 }
attoTechnology                    OBJECT IDENTIFIER ::= { enterprises 4547 }
quickstartConsulting              OBJECT IDENTIFIER ::= { enterprises 4548 }
webgear                           OBJECT IDENTIFIER ::= { enterprises 4549 }
theJapanElectricalManufacturers   OBJECT IDENTIFIER ::= { enterprises 4550 }
rswSoftware                       OBJECT IDENTIFIER ::= { enterprises 4551 }
wayport                           OBJECT IDENTIFIER ::= { enterprises 4552 }
nextcomKK                         OBJECT IDENTIFIER ::= { enterprises 4553 }
trisolTechnologies                OBJECT IDENTIFIER ::= { enterprises 4554 }
socomecSiconUps                   OBJECT IDENTIFIER ::= { enterprises 4555 }
scali                             OBJECT IDENTIFIER ::= { enterprises 4556 }
qwest                             OBJECT IDENTIFIER ::= { enterprises 4557 }
euromoveSro                       OBJECT IDENTIFIER ::= { enterprises 4558 }
nvision                           OBJECT IDENTIFIER ::= { enterprises 4559 }
shebangNetworking                 OBJECT IDENTIFIER ::= { enterprises 4560 }
emware                            OBJECT IDENTIFIER ::= { enterprises 4561 }
centermarkEngineeringLC           OBJECT IDENTIFIER ::= { enterprises 4562 }
syllogi                           OBJECT IDENTIFIER ::= { enterprises 4563 }
diverseNetworks                   OBJECT IDENTIFIER ::= { enterprises 4564 }
cedelbank                         OBJECT IDENTIFIER ::= { enterprises 4566 }
cedelGlobalServices               OBJECT IDENTIFIER ::= { enterprises 4567 }
cedelInternational                OBJECT IDENTIFIER ::= { enterprises 4568 }
ensigma                           OBJECT IDENTIFIER ::= { enterprises 4569 }
netenterprise                     OBJECT IDENTIFIER ::= { enterprises 4570 }
jmcs                              OBJECT IDENTIFIER ::= { enterprises 4571 }
daedalusCorporation               OBJECT IDENTIFIER ::= { enterprises 4572 }
securesoft                        OBJECT IDENTIFIER ::= { enterprises 4573 }
compuAlvarado                     OBJECT IDENTIFIER ::= { enterprises 4574 }
maniNetworkCo                     OBJECT IDENTIFIER ::= { enterprises 4575 }
corporacionZIGORSA                OBJECT IDENTIFIER ::= { enterprises 4576 }
internetResearch                  OBJECT IDENTIFIER ::= { enterprises 4577 }
sseTelecom                        OBJECT IDENTIFIER ::= { enterprises 4578 }
vestInternett                     OBJECT IDENTIFIER ::= { enterprises 4579 }
diversifiedBusinessGroup          OBJECT IDENTIFIER ::= { enterprises 4580 }
seeburgerGmbH                     OBJECT IDENTIFIER ::= { enterprises 4581 }
worldTelecomPlc                   OBJECT IDENTIFIER ::= { enterprises 4582 }
netstar                           OBJECT IDENTIFIER ::= { enterprises 4583 }
headhuntersLondonLimited          OBJECT IDENTIFIER ::= { enterprises 4584 }
eelValleyInternet                 OBJECT IDENTIFIER ::= { enterprises 4585 }
enterpriseConsultingGroup         OBJECT IDENTIFIER ::= { enterprises 4586 }
diamondMultimediaSystems          OBJECT IDENTIFIER ::= { enterprises 4587 }
criticalPath                      OBJECT IDENTIFIER ::= { enterprises 4588 }
datapSystems                      OBJECT IDENTIFIER ::= { enterprises 4589 }
zoomTelephonics                   OBJECT IDENTIFIER ::= { enterprises 4590 }
spacecomSystems                   OBJECT IDENTIFIER ::= { enterprises 4591 }
frontierCommunications            OBJECT IDENTIFIER ::= { enterprises 4592 }
saetISSpA                         OBJECT IDENTIFIER ::= { enterprises 4593 }
saritelSpA                        OBJECT IDENTIFIER ::= { enterprises 4594 }
isProduction                      OBJECT IDENTIFIER ::= { enterprises 4595 }
videoframeSystems                 OBJECT IDENTIFIER ::= { enterprises 4596 }
fiberviewTechnologies             OBJECT IDENTIFIER ::= { enterprises 4597 }
jcampus                           OBJECT IDENTIFIER ::= { enterprises 4598 }
mimsoft                           OBJECT IDENTIFIER ::= { enterprises 4599 }
cybertimeInformatikGmbH           OBJECT IDENTIFIER ::= { enterprises 4601 }
beaSystems2                       OBJECT IDENTIFIER ::= { enterprises 4602 }
ters                              OBJECT IDENTIFIER ::= { enterprises 4603 }
becaCarterHollingsAndFerner       OBJECT IDENTIFIER ::= { enterprises 4604 }
torontoSchoolOfBusiness           OBJECT IDENTIFIER ::= { enterprises 4605 }
informationSecurityAgency         OBJECT IDENTIFIER ::= { enterprises 4606 }
softwareShelfTechnologies         OBJECT IDENTIFIER ::= { enterprises 4607 }
harcoTechnology                   OBJECT IDENTIFIER ::= { enterprises 4608 }
seamlessTechnologies              OBJECT IDENTIFIER ::= { enterprises 4609 }
strategicTechnologies             OBJECT IDENTIFIER ::= { enterprises 4610 }
digitalWirelessCorporation        OBJECT IDENTIFIER ::= { enterprises 4611 }
bakerStreetTechnologies           OBJECT IDENTIFIER ::= { enterprises 4612 }
sphereCommunications              OBJECT IDENTIFIER ::= { enterprises 4613 }
luminousNetworks                  OBJECT IDENTIFIER ::= { enterprises 4614 }
iODataDevice                      OBJECT IDENTIFIER ::= { enterprises 4615 }
computerjobscom                   OBJECT IDENTIFIER ::= { enterprises 4616 }
marcomputer                       OBJECT IDENTIFIER ::= { enterprises 4617 }
arbosTechnologies                 OBJECT IDENTIFIER ::= { enterprises 4618 }
eremindercom                      OBJECT IDENTIFIER ::= { enterprises 4619 }
progressiveSystems                OBJECT IDENTIFIER ::= { enterprises 4620 }
nstopTechnologies                 OBJECT IDENTIFIER ::= { enterprises 4621 }
legianConsultancyAndNetworkServices OBJECT IDENTIFIER ::= { enterprises 4622 }
lifixSystemsOy                    OBJECT IDENTIFIER ::= { enterprises 4623 }
trainingForTomorrow               OBJECT IDENTIFIER ::= { enterprises 4624 }
mazoneSystems                     OBJECT IDENTIFIER ::= { enterprises 4625 }
westlb                            OBJECT IDENTIFIER ::= { enterprises 4626 }
saetISSrl                         OBJECT IDENTIFIER ::= { enterprises 4627 }
xtraOnLine                        OBJECT IDENTIFIER ::= { enterprises 4628 }
ipverse                           OBJECT IDENTIFIER ::= { enterprises 4629 }
filetek                           OBJECT IDENTIFIER ::= { enterprises 4630 }
homeloandotcom                    OBJECT IDENTIFIER ::= { enterprises 4631 }
freemarkets                       OBJECT IDENTIFIER ::= { enterprises 4632 }
cqos                              OBJECT IDENTIFIER ::= { enterprises 4633 }
vconTelecommunications            OBJECT IDENTIFIER ::= { enterprises 4634 }
theVEGroup                        OBJECT IDENTIFIER ::= { enterprises 4635 }
intrustSoftware                   OBJECT IDENTIFIER ::= { enterprises 4636 }
rge                               OBJECT IDENTIFIER ::= { enterprises 4637 }
sgiSolucionesGlobalesInternet     OBJECT IDENTIFIER ::= { enterprises 4638 }
tetragoneSA                       OBJECT IDENTIFIER ::= { enterprises 4639 }
eckerdCollege                     OBJECT IDENTIFIER ::= { enterprises 4640 }
vivaceNetworks                    OBJECT IDENTIFIER ::= { enterprises 4641 }
belStudioHSager                   OBJECT IDENTIFIER ::= { enterprises 4642 }
nworks                            OBJECT IDENTIFIER ::= { enterprises 4643 }
wincomTechnology                  OBJECT IDENTIFIER ::= { enterprises 4644 }
dataDuctusAB                      OBJECT IDENTIFIER ::= { enterprises 4645 }
netconvergence                    OBJECT IDENTIFIER ::= { enterprises 4646 }
internetChessClub                 OBJECT IDENTIFIER ::= { enterprises 4647 }
theGratefulNet                    OBJECT IDENTIFIER ::= { enterprises 4648 }
cplane                            OBJECT IDENTIFIER ::= { enterprises 4649 }
marcAugustInternational           OBJECT IDENTIFIER ::= { enterprises 4650 }
aztecRadiomedia                   OBJECT IDENTIFIER ::= { enterprises 4651 }
technicalUniversityOfIlmenau      OBJECT IDENTIFIER ::= { enterprises 4652 }
preciseSoftwareTechnologies       OBJECT IDENTIFIER ::= { enterprises 4653 }
oclcOnlineComputerLibraryCenter   OBJECT IDENTIFIER ::= { enterprises 4654 }
telecheckInternational            OBJECT IDENTIFIER ::= { enterprises 4655 }
bancoDeGaliciaYBuenosAires        OBJECT IDENTIFIER ::= { enterprises 4656 }
goodallSecureServices             OBJECT IDENTIFIER ::= { enterprises 4657 }
entertainmentInternational        OBJECT IDENTIFIER ::= { enterprises 4658 }
tecoImageSystemsCo                OBJECT IDENTIFIER ::= { enterprises 4659 }
rcms                              OBJECT IDENTIFIER ::= { enterprises 4660 }
spazioRAndD                       OBJECT IDENTIFIER ::= { enterprises 4661 }
frankMatthiess                    OBJECT IDENTIFIER ::= { enterprises 4662 }
decorMetallGmbHCOKG               OBJECT IDENTIFIER ::= { enterprises 4663 }
arkResearchCorporation            OBJECT IDENTIFIER ::= { enterprises 4664 }
performanceDesignLimited          OBJECT IDENTIFIER ::= { enterprises 4665 }
itchigoCommunicationsGmbH         OBJECT IDENTIFIER ::= { enterprises 4666 }
telperionNetworkSystems           OBJECT IDENTIFIER ::= { enterprises 4667 }
turningPointTechnologies          OBJECT IDENTIFIER ::= { enterprises 4668 }
muroEnterprises                   OBJECT IDENTIFIER ::= { enterprises 4669 }
nationalComputationalScienceAlliance OBJECT IDENTIFIER ::= { enterprises 4670 }
advancedTelecomSystems            OBJECT IDENTIFIER ::= { enterprises 4671 }
usHealthcarePKI                   OBJECT IDENTIFIER ::= { enterprises 4672 }
waveResearchNV                    OBJECT IDENTIFIER ::= { enterprises 4673 }
crunchTechnologiesBV              OBJECT IDENTIFIER ::= { enterprises 4674 }
wkAudiosystemsBV                  OBJECT IDENTIFIER ::= { enterprises 4675 }
healthaxiscom                     OBJECT IDENTIFIER ::= { enterprises 4676 }
concertTechnologies               OBJECT IDENTIFIER ::= { enterprises 4677 }
informationDevelopersUnlimited    OBJECT IDENTIFIER ::= { enterprises 4678 }
opicom                            OBJECT IDENTIFIER ::= { enterprises 4679 }
telecommunicationsSystemsGroupUCL OBJECT IDENTIFIER ::= { enterprises 4680 }
dvgHannoverDatenverarbeitungsgesellschaftMbH OBJECT IDENTIFIER ::= { enterprises 4681 }
linuxHAProject                    OBJECT IDENTIFIER ::= { enterprises 4682 }
tradingTechnologiesInternational  OBJECT IDENTIFIER ::= { enterprises 4683 }
ambitMicrosystemsCorporation      OBJECT IDENTIFIER ::= { enterprises 4684 }
tontruInformationIndustryGroupCo  OBJECT IDENTIFIER ::= { enterprises 4685 }
vegastream                        OBJECT IDENTIFIER ::= { enterprises 4686 }
digitroTecnologia                 OBJECT IDENTIFIER ::= { enterprises 4687 }
luimesComputerConsulting          OBJECT IDENTIFIER ::= { enterprises 4688 }
urbisnet                          OBJECT IDENTIFIER ::= { enterprises 4689 }
mbcEurope                         OBJECT IDENTIFIER ::= { enterprises 4690 }
vawAluminumTechnologieGmbH        OBJECT IDENTIFIER ::= { enterprises 4691 }
digitalTechnics                   OBJECT IDENTIFIER ::= { enterprises 4692 }
creativeDesignSolutions           OBJECT IDENTIFIER ::= { enterprises 4693 }
willametteUniversity              OBJECT IDENTIFIER ::= { enterprises 4694 }
extricitySoftware                 OBJECT IDENTIFIER ::= { enterprises 4695 }
webbStudios                       OBJECT IDENTIFIER ::= { enterprises 4696 }
atlantel                          OBJECT IDENTIFIER ::= { enterprises 4697 }
connectivitySoftwareSystems       OBJECT IDENTIFIER ::= { enterprises 4698 }
burningDoor                       OBJECT IDENTIFIER ::= { enterprises 4699 }
internetpiratecom                 OBJECT IDENTIFIER ::= { enterprises 4700 }
syskoplanGmbH                     OBJECT IDENTIFIER ::= { enterprises 4701 }
speechworksInternational          OBJECT IDENTIFIER ::= { enterprises 4702 }
sanfordCBernsteinAndCo            OBJECT IDENTIFIER ::= { enterprises 4703 }
visualMediaTechnologies           OBJECT IDENTIFIER ::= { enterprises 4704 }
gabrielCommunications             OBJECT IDENTIFIER ::= { enterprises 4705 }
zero7com                          OBJECT IDENTIFIER ::= { enterprises 4706 }
aldeaInternet                     OBJECT IDENTIFIER ::= { enterprises 4707 }
imedium                           OBJECT IDENTIFIER ::= { enterprises 4708 }
oxydianSA                         OBJECT IDENTIFIER ::= { enterprises 4709 }
safelayerSA                       OBJECT IDENTIFIER ::= { enterprises 4710 }
mailcom                           OBJECT IDENTIFIER ::= { enterprises 4711 }
entropic                          OBJECT IDENTIFIER ::= { enterprises 4712 }
wherenet                          OBJECT IDENTIFIER ::= { enterprises 4713 }
centerpointBroadbandTechnologies  OBJECT IDENTIFIER ::= { enterprises 4714 }
adviceNetbusiness                 OBJECT IDENTIFIER ::= { enterprises 4715 }
arbortext                         OBJECT IDENTIFIER ::= { enterprises 4716 }
mediaManagementConsulting         OBJECT IDENTIFIER ::= { enterprises 4717 }
mdlInformationSystems             OBJECT IDENTIFIER ::= { enterprises 4718 }
montagnaleaderScarl               OBJECT IDENTIFIER ::= { enterprises 4719 }
lunatechResearch                  OBJECT IDENTIFIER ::= { enterprises 4720 }
cositel                           OBJECT IDENTIFIER ::= { enterprises 4721 }
jacksonvilleUniversity            OBJECT IDENTIFIER ::= { enterprises 4722 }
mockingbirdNetworks               OBJECT IDENTIFIER ::= { enterprises 4723 }
technosoft                        OBJECT IDENTIFIER ::= { enterprises 4724 }
bestnetInternet                   OBJECT IDENTIFIER ::= { enterprises 4725 }
capitalComputerServices           OBJECT IDENTIFIER ::= { enterprises 4726 }
langtangJVCompany                 OBJECT IDENTIFIER ::= { enterprises 4727 }
nsiTechnology                     OBJECT IDENTIFIER ::= { enterprises 4728 }
crannogSoftware                   OBJECT IDENTIFIER ::= { enterprises 4729 }
epita                             OBJECT IDENTIFIER ::= { enterprises 4730 }
socketware                        OBJECT IDENTIFIER ::= { enterprises 4731 }
cvf                               OBJECT IDENTIFIER ::= { enterprises 4732 }
middlesexUniversity               OBJECT IDENTIFIER ::= { enterprises 4733 }
zarakSystemsCorporation           OBJECT IDENTIFIER ::= { enterprises 4734 }
somaNetworks                      OBJECT IDENTIFIER ::= { enterprises 4735 }
appliant                          OBJECT IDENTIFIER ::= { enterprises 4736 }
crosswalkcom                      OBJECT IDENTIFIER ::= { enterprises 4737 }
shanghaiEWayComputerNetworkTechnology OBJECT IDENTIFIER ::= { enterprises 4738 }
oldeDiscountCorporation           OBJECT IDENTIFIER ::= { enterprises 4739 }
votehere                          OBJECT IDENTIFIER ::= { enterprises 4740 }
amberNetworks                     OBJECT IDENTIFIER ::= { enterprises 4741 }
operationalTechnologiesServices   OBJECT IDENTIFIER ::= { enterprises 4742 }
nextnet                           OBJECT IDENTIFIER ::= { enterprises 4743 }
internalnetwork                   OBJECT IDENTIFIER ::= { enterprises 4744 }
digisafePte                       OBJECT IDENTIFIER ::= { enterprises 4745 }
ptInovacao                        OBJECT IDENTIFIER ::= { enterprises 4746 }
serviceTechniqueDeLaNavigationAerienne OBJECT IDENTIFIER ::= { enterprises 4747 }
dobitNv                           OBJECT IDENTIFIER ::= { enterprises 4748 }
ePlaza                            OBJECT IDENTIFIER ::= { enterprises 4749 }
lykonConsulting                   OBJECT IDENTIFIER ::= { enterprises 4750 }
sarlK1                            OBJECT IDENTIFIER ::= { enterprises 4751 }
crescentNetworks                  OBJECT IDENTIFIER ::= { enterprises 4752 }
montavistaSoftware                OBJECT IDENTIFIER ::= { enterprises 4753 }
symasCorp                         OBJECT IDENTIFIER ::= { enterprises 4754 }
directoryWorks                    OBJECT IDENTIFIER ::= { enterprises 4755 }
ctcUnionTechnologiesCo            OBJECT IDENTIFIER ::= { enterprises 4756 }
ibs                               OBJECT IDENTIFIER ::= { enterprises 4757 }
anixGroup                         OBJECT IDENTIFIER ::= { enterprises 4758 }
pecoII                            OBJECT IDENTIFIER ::= { enterprises 4759 }
viditec                           OBJECT IDENTIFIER ::= { enterprises 4760 }
nudesignTeam                      OBJECT IDENTIFIER ::= { enterprises 4761 }
gricCommunication                 OBJECT IDENTIFIER ::= { enterprises 4762 }
teddybearComputerServices         OBJECT IDENTIFIER ::= { enterprises 4763 }
frontierGlobalCenter              OBJECT IDENTIFIER ::= { enterprises 4764 }
tomorrowFactory                   OBJECT IDENTIFIER ::= { enterprises 4765 }
fachhochschuleHeilbronn           OBJECT IDENTIFIER ::= { enterprises 4766 }
trafficmasterPLC                  OBJECT IDENTIFIER ::= { enterprises 4767 }
eonAG                             OBJECT IDENTIFIER ::= { enterprises 4768 }
tsiInternationalSoftware          OBJECT IDENTIFIER ::= { enterprises 4769 }
ol                                OBJECT IDENTIFIER ::= { enterprises 4770 }
narus                             OBJECT IDENTIFIER ::= { enterprises 4771 }
cybersourceCorporation            OBJECT IDENTIFIER ::= { enterprises 4772 }
realnamesCorporation              OBJECT IDENTIFIER ::= { enterprises 4773 }
netpliancenet                     OBJECT IDENTIFIER ::= { enterprises 4774 }
networkICE                        OBJECT IDENTIFIER ::= { enterprises 4775 }
knightFisk                        OBJECT IDENTIFIER ::= { enterprises 4776 }
cuperusConsultants                OBJECT IDENTIFIER ::= { enterprises 4777 }
biscom                            OBJECT IDENTIFIER ::= { enterprises 4778 }
bayTechnicalAssociates            OBJECT IDENTIFIER ::= { enterprises 4779 }
vadem                             OBJECT IDENTIFIER ::= { enterprises 4780 }
epiphany                          OBJECT IDENTIFIER ::= { enterprises 4781 }
threeCube                         OBJECT IDENTIFIER ::= { enterprises 4782 }
crosstorSoftware                  OBJECT IDENTIFIER ::= { enterprises 4783 }
telexisCorporation                OBJECT IDENTIFIER ::= { enterprises 4784 }
appianCommunications              OBJECT IDENTIFIER ::= { enterprises 4785 }
sierraPartners                    OBJECT IDENTIFIER ::= { enterprises 4786 }
hiLinkInformationSystemsCo        OBJECT IDENTIFIER ::= { enterprises 4787 }
dTrustGmbH                        OBJECT IDENTIFIER ::= { enterprises 4788 }
telica                            OBJECT IDENTIFIER ::= { enterprises 4789 }
securelogixCorporation            OBJECT IDENTIFIER ::= { enterprises 4790 }
dresdnerBankAG                    OBJECT IDENTIFIER ::= { enterprises 4791 }
wavefront                         OBJECT IDENTIFIER ::= { enterprises 4792 }
levi                              OBJECT IDENTIFIER ::= { enterprises 4793 }
ecoin                             OBJECT IDENTIFIER ::= { enterprises 4794 }
unifiedProductions                OBJECT IDENTIFIER ::= { enterprises 4795 }
joeChapa                          OBJECT IDENTIFIER ::= { enterprises 4796 }
cityGroup                         OBJECT IDENTIFIER ::= { enterprises 4797 }
vigilTechnologies                 OBJECT IDENTIFIER ::= { enterprises 4798 }
leaselogix                        OBJECT IDENTIFIER ::= { enterprises 4799 }
jensleyPty                        OBJECT IDENTIFIER ::= { enterprises 4800 }
compassCorporateSystems           OBJECT IDENTIFIER ::= { enterprises 4801 }
systematicSoftwareEngineeringAS   OBJECT IDENTIFIER ::= { enterprises 4802 }
powwow                            OBJECT IDENTIFIER ::= { enterprises 4803 }
castelloCitiesInternetNetwork     OBJECT IDENTIFIER ::= { enterprises 4804 }
inovaCorporation                  OBJECT IDENTIFIER ::= { enterprises 4805 }
rossleaAssociatesLLC              OBJECT IDENTIFIER ::= { enterprises 4806 }
controlZCorporation               OBJECT IDENTIFIER ::= { enterprises 4807 }
lantechComputerCompany            OBJECT IDENTIFIER ::= { enterprises 4808 }
bswTelecoms                       OBJECT IDENTIFIER ::= { enterprises 4809 }
bloemenveilingHolland             OBJECT IDENTIFIER ::= { enterprises 4810 }
networkFlightRecorder             OBJECT IDENTIFIER ::= { enterprises 4811 }
shanghaiRadioCommunicationEquipmentManufactureCompany OBJECT IDENTIFIER ::= { enterprises 4812 }
glenevin                          OBJECT IDENTIFIER ::= { enterprises 4813 }
alexTemexMultimediaSA             OBJECT IDENTIFIER ::= { enterprises 4814 }
hbFullerCompany                   OBJECT IDENTIFIER ::= { enterprises 4815 }
pacificGasAndElectricCompany      OBJECT IDENTIFIER ::= { enterprises 4816 }
innovativeTechnologiesAndConsulting OBJECT IDENTIFIER ::= { enterprises 4817 }
sinclairInternetworkingServices   OBJECT IDENTIFIER ::= { enterprises 4818 }
rmsTechnologyIntegration          OBJECT IDENTIFIER ::= { enterprises 4819 }
quicknetTechnologies              OBJECT IDENTIFIER ::= { enterprises 4820 }
sn2ai                             OBJECT IDENTIFIER ::= { enterprises 4821 }
fialComputer                      OBJECT IDENTIFIER ::= { enterprises 4822 }
shanghaiHuaLongInformationTechnologyDevelopmentCenter OBJECT IDENTIFIER ::= { enterprises 4823 }
dslCommunications                 OBJECT IDENTIFIER ::= { enterprises 4824 }
goldenScreensInteractiveTechnologies OBJECT IDENTIFIER ::= { enterprises 4825 }
theEuropeanClearingHouse          OBJECT IDENTIFIER ::= { enterprises 4826 }
interouteTelecommunications       OBJECT IDENTIFIER ::= { enterprises 4827 }
intelidataTechnologiesCorp        OBJECT IDENTIFIER ::= { enterprises 4828 }
aToZPestControl                   OBJECT IDENTIFIER ::= { enterprises 4829 }
gloablMediaCorp                   OBJECT IDENTIFIER ::= { enterprises 4830 }
banchile                          OBJECT IDENTIFIER ::= { enterprises 4831 }
networkPhenomena                  OBJECT IDENTIFIER ::= { enterprises 4832 }
sdni                              OBJECT IDENTIFIER ::= { enterprises 4833 }
factumElectronicsAB               OBJECT IDENTIFIER ::= { enterprises 4834 }
opnetTechnologiesCo               OBJECT IDENTIFIER ::= { enterprises 4835 }
lhsGroup                          OBJECT IDENTIFIER ::= { enterprises 4836 }
trrripplerrrdesigns               OBJECT IDENTIFIER ::= { enterprises 4837 }
newImageCompany                   OBJECT IDENTIFIER ::= { enterprises 4838 }
wire                              OBJECT IDENTIFIER ::= { enterprises 4839 }
bedetInformationTechnologies      OBJECT IDENTIFIER ::= { enterprises 4840 }
ifacecom                          OBJECT IDENTIFIER ::= { enterprises 4841 }
secureagent                       OBJECT IDENTIFIER ::= { enterprises 4842 }
amazoncom                         OBJECT IDENTIFIER ::= { enterprises 4843 }
neopoint                          OBJECT IDENTIFIER ::= { enterprises 4844 }
miralinkCorp                      OBJECT IDENTIFIER ::= { enterprises 4845 }
lucentINS                         OBJECT IDENTIFIER ::= { enterprises 4846 }
vikramKulkarni                    OBJECT IDENTIFIER ::= { enterprises 4847 }
interphiz                         OBJECT IDENTIFIER ::= { enterprises 4848 }
diplPhysPeerStritzinger           OBJECT IDENTIFIER ::= { enterprises 4849 }
eddieGeorgeLimited                OBJECT IDENTIFIER ::= { enterprises 4850 }
kroneTelecellGmbH                 OBJECT IDENTIFIER ::= { enterprises 4851 }
cmaSmallSystemsAB                 OBJECT IDENTIFIER ::= { enterprises 4852 }
syndeoCorporation                 OBJECT IDENTIFIER ::= { enterprises 4853 }
mk1Design                         OBJECT IDENTIFIER ::= { enterprises 4854 }
addpacTechnologyCo                OBJECT IDENTIFIER ::= { enterprises 4855 }
veraluzInternationalCorporation   OBJECT IDENTIFIER ::= { enterprises 4856 }
cisco                             OBJECT IDENTIFIER ::= { enterprises 4857 }
fortech                           OBJECT IDENTIFIER ::= { enterprises 4858 }
gems                              OBJECT IDENTIFIER ::= { enterprises 4859 }
boocomGroupLTD                    OBJECT IDENTIFIER ::= { enterprises 4860 }
powercomTechnologies              OBJECT IDENTIFIER ::= { enterprises 4861 }
redwoodMarketing                  OBJECT IDENTIFIER ::= { enterprises 4862 }
parion                            OBJECT IDENTIFIER ::= { enterprises 4863 }
johDATAAS                         OBJECT IDENTIFIER ::= { enterprises 4864 }
ergGroup                          OBJECT IDENTIFIER ::= { enterprises 4865 }
moseleyAssociate                  OBJECT IDENTIFIER ::= { enterprises 4866 }
vietMarketing                     OBJECT IDENTIFIER ::= { enterprises 4867 }
nextra                            OBJECT IDENTIFIER ::= { enterprises 4868 }
sitEurope                         OBJECT IDENTIFIER ::= { enterprises 4869 }
fritzEggerGmbHAndCo               OBJECT IDENTIFIER ::= { enterprises 4870 }
discoverycom                      OBJECT IDENTIFIER ::= { enterprises 4871 }
bouyguesTelecom                   OBJECT IDENTIFIER ::= { enterprises 4872 }
seaySystems                       OBJECT IDENTIFIER ::= { enterprises 4873 }
unisphereNetworks                 OBJECT IDENTIFIER ::= { enterprises 4874 }
doubleclick                       OBJECT IDENTIFIER ::= { enterprises 4875 }
eyestreetSoftware                 OBJECT IDENTIFIER ::= { enterprises 4876 }
salonPress                        OBJECT IDENTIFIER ::= { enterprises 4877 }
villageNetworks                   OBJECT IDENTIFIER ::= { enterprises 4878 }
technologyCenter                  OBJECT IDENTIFIER ::= { enterprises 4879 }
standardAndPoorsCompustat         OBJECT IDENTIFIER ::= { enterprises 4880 }
startNetworkTechnologyCo          OBJECT IDENTIFIER ::= { enterprises 4881 }
root                              OBJECT IDENTIFIER ::= { enterprises 4882 }
saatchAndSaatchi                  OBJECT IDENTIFIER ::= { enterprises 4883 }
protek                            OBJECT IDENTIFIER ::= { enterprises 4884 }
photonTechnologyCo                OBJECT IDENTIFIER ::= { enterprises 4885 }
westwaveCommunications            OBJECT IDENTIFIER ::= { enterprises 4886 }
iqWirelessGmbH                    OBJECT IDENTIFIER ::= { enterprises 4887 }
multidataGmbH                     OBJECT IDENTIFIER ::= { enterprises 4888 }
inflow                            OBJECT IDENTIFIER ::= { enterprises 4889 }
skinnersComputerCenter            OBJECT IDENTIFIER ::= { enterprises 4890 }
networkAddressSolutions           OBJECT IDENTIFIER ::= { enterprises 4891 }
theChineseUniversityOfHongKong    OBJECT IDENTIFIER ::= { enterprises 4892 }
atshawTechnologies                OBJECT IDENTIFIER ::= { enterprises 4893 }
kleinwortBenson                   OBJECT IDENTIFIER ::= { enterprises 4894 }
woodwindCommunicationsSystems     OBJECT IDENTIFIER ::= { enterprises 4895 }
telesoftInternational             OBJECT IDENTIFIER ::= { enterprises 4896 }
dobusinessonlineServices          OBJECT IDENTIFIER ::= { enterprises 4897 }
time                              OBJECT IDENTIFIER ::= { enterprises 4898 }
walkerSystemsCorporation          OBJECT IDENTIFIER ::= { enterprises 4899 }
conexantSystems                   OBJECT IDENTIFIER ::= { enterprises 4900 }
usaa                              OBJECT IDENTIFIER ::= { enterprises 4901 }
beijingHuaguangElectronicsCo      OBJECT IDENTIFIER ::= { enterprises 4902 }
gccTechnologies                   OBJECT IDENTIFIER ::= { enterprises 4903 }
sdf                               OBJECT IDENTIFIER ::= { enterprises 4904 }
webdialogs                        OBJECT IDENTIFIER ::= { enterprises 4905 }
edgixCorporation                  OBJECT IDENTIFIER ::= { enterprises 4906 }
appworxCorporation                OBJECT IDENTIFIER ::= { enterprises 4907 }
ats                               OBJECT IDENTIFIER ::= { enterprises 4908 }
expertsExchange                   OBJECT IDENTIFIER ::= { enterprises 4909 }
ubizen                            OBJECT IDENTIFIER ::= { enterprises 4910 }
pcordercom                        OBJECT IDENTIFIER ::= { enterprises 4911 }
oneWorldInformationSystem         OBJECT IDENTIFIER ::= { enterprises 4912 }
holeInThenet                      OBJECT IDENTIFIER ::= { enterprises 4914 }
sipherInternetTechnology          OBJECT IDENTIFIER ::= { enterprises 4915 }
blacksoundSA                      OBJECT IDENTIFIER ::= { enterprises 4916 }
sistemasTecnicosDeLoterias        OBJECT IDENTIFIER ::= { enterprises 4917 }
taurusentTechnologies             OBJECT IDENTIFIER ::= { enterprises 4918 }
luminateSoftwareCorporation       OBJECT IDENTIFIER ::= { enterprises 4919 }
bostonGlobe                       OBJECT IDENTIFIER ::= { enterprises 4920 }
networkSolutions                  OBJECT IDENTIFIER ::= { enterprises 4921 }
telcordiaTechnologies             OBJECT IDENTIFIER ::= { enterprises 4922 }
audiocodes                        OBJECT IDENTIFIER ::= { enterprises 4923 }
sanValleySystems                  OBJECT IDENTIFIER ::= { enterprises 4924 }
zumaNetworks                      OBJECT IDENTIFIER ::= { enterprises 4925 }
touchtunesDigitalJukebox          OBJECT IDENTIFIER ::= { enterprises 4926 }
time4youGmbH                      OBJECT IDENTIFIER ::= { enterprises 4927 }
xrosstech                         OBJECT IDENTIFIER ::= { enterprises 4928 }
lanCrypto                         OBJECT IDENTIFIER ::= { enterprises 4929 }
concordTechnologies               OBJECT IDENTIFIER ::= { enterprises 4930 }
standardAndPoor                   OBJECT IDENTIFIER ::= { enterprises 4931 }
foglightSoftware                  OBJECT IDENTIFIER ::= { enterprises 4932 }
shunraSoftware                    OBJECT IDENTIFIER ::= { enterprises 4933 }
webdialogs2                       OBJECT IDENTIFIER ::= { enterprises 4934 }
mediatrixTelecom                  OBJECT IDENTIFIER ::= { enterprises 4935 }
firstAmericanFinancialCorporation OBJECT IDENTIFIER ::= { enterprises 4936 }
stormbreakerNetworkServices       OBJECT IDENTIFIER ::= { enterprises 4937 }
daeyoungElectronicIndCO           OBJECT IDENTIFIER ::= { enterprises 4938 }
procterAndGamble                  OBJECT IDENTIFIER ::= { enterprises 4939 }
convergentCommunicationsServices  OBJECT IDENTIFIER ::= { enterprises 4940 }
echelonCorporation                OBJECT IDENTIFIER ::= { enterprises 4941 }
libertyPressAndLetterService      OBJECT IDENTIFIER ::= { enterprises 4942 }
novellGmbH                        OBJECT IDENTIFIER ::= { enterprises 4943 }
futureNetworks                    OBJECT IDENTIFIER ::= { enterprises 4944 }
logicon                           OBJECT IDENTIFIER ::= { enterprises 4945 }
psychedelicIlluminationsMagazine  OBJECT IDENTIFIER ::= { enterprises 4946 }
grassValleyGroup                  OBJECT IDENTIFIER ::= { enterprises 4947 }
andreasBrodmann                   OBJECT IDENTIFIER ::= { enterprises 4948 }
fortressTechnologies              OBJECT IDENTIFIER ::= { enterprises 4949 }
luxorSoftware                     OBJECT IDENTIFIER ::= { enterprises 4950 }
stateFarmInsurance                OBJECT IDENTIFIER ::= { enterprises 4951 }
thinking                          OBJECT IDENTIFIER ::= { enterprises 4952 }
tecnetTeleinformatica             OBJECT IDENTIFIER ::= { enterprises 4953 }
wroxPressItd                      OBJECT IDENTIFIER ::= { enterprises 4954 }
asgardTechnologies                OBJECT IDENTIFIER ::= { enterprises 4955 }
graphicsFIVE                      OBJECT IDENTIFIER ::= { enterprises 4956 }
cnetComputerSystemeNetzwerkGmbH   OBJECT IDENTIFIER ::= { enterprises 4957 }
terralinkTechnologies             OBJECT IDENTIFIER ::= { enterprises 4958 }
uForce                            OBJECT IDENTIFIER ::= { enterprises 4959 }
chromisys                         OBJECT IDENTIFIER ::= { enterprises 4960 }
ardentTechnologies                OBJECT IDENTIFIER ::= { enterprises 4961 }
artelVideoSystems                 OBJECT IDENTIFIER ::= { enterprises 4962 }
wbLoveEnterprises                 OBJECT IDENTIFIER ::= { enterprises 4964 }
greenwichMeanTime                 OBJECT IDENTIFIER ::= { enterprises 4965 }
aacom                             OBJECT IDENTIFIER ::= { enterprises 4966 }
starwoodHotelsAndResorts          OBJECT IDENTIFIER ::= { enterprises 4967 }
universtiyOfNorthTexas            OBJECT IDENTIFIER ::= { enterprises 4968 }
naviaAviation                     OBJECT IDENTIFIER ::= { enterprises 4969 }
nationalGridForLearning           OBJECT IDENTIFIER ::= { enterprises 4970 }
anglersClub                       OBJECT IDENTIFIER ::= { enterprises 4971 }
losAlamosNationalLaboratory       OBJECT IDENTIFIER ::= { enterprises 4972 }
setnetCorporation                 OBJECT IDENTIFIER ::= { enterprises 4973 }
eatm                              OBJECT IDENTIFIER ::= { enterprises 4974 }
intervu                           OBJECT IDENTIFIER ::= { enterprises 4975 }
agent                             OBJECT IDENTIFIER ::= { enterprises 4976 }
tiesseSpA                         OBJECT IDENTIFIER ::= { enterprises 4977 }
direkcijaRSZaPoslovnoInformacijskoSredisce OBJECT IDENTIFIER ::= { enterprises 4978 }
licerSolutions                    OBJECT IDENTIFIER ::= { enterprises 4979 }
softwareBuilders                  OBJECT IDENTIFIER ::= { enterprises 4980 }
riverdeltaNetworks                OBJECT IDENTIFIER ::= { enterprises 4981 }
persistenceSoftware               OBJECT IDENTIFIER ::= { enterprises 4982 }
innomedialogic                    OBJECT IDENTIFIER ::= { enterprises 4983 }
pinnacleSystems                   OBJECT IDENTIFIER ::= { enterprises 4984 }
vigilantNetworks                  OBJECT IDENTIFIER ::= { enterprises 4985 }
kbTel                             OBJECT IDENTIFIER ::= { enterprises 4986 }
simplerNetworks                   OBJECT IDENTIFIER ::= { enterprises 4987 }
ronningenConsulting               OBJECT IDENTIFIER ::= { enterprises 4988 }
connectAustriaGmbH                OBJECT IDENTIFIER ::= { enterprises 4989 }
ttiTelecom                        OBJECT IDENTIFIER ::= { enterprises 4990 }
stonebridgeTechnologies           OBJECT IDENTIFIER ::= { enterprises 4991 }
thyssenKruppInformationSystemsGmbH OBJECT IDENTIFIER ::= { enterprises 4992 }
ctuPrague                         OBJECT IDENTIFIER ::= { enterprises 4993 }
cutTHROATTRAVELOUTLET             OBJECT IDENTIFIER ::= { enterprises 4994 }
universtiyOfCalifornia            OBJECT IDENTIFIER ::= { enterprises 4995 }
forestNetworksLLC                 OBJECT IDENTIFIER ::= { enterprises 4996 }
inetdcomConsulting                OBJECT IDENTIFIER ::= { enterprises 4997 }
cadant                            OBJECT IDENTIFIER ::= { enterprises 4998 }
personalBusiness                  OBJECT IDENTIFIER ::= { enterprises 5000 }
logicmedia                        OBJECT IDENTIFIER ::= { enterprises 5001 }
rcNetworks                        OBJECT IDENTIFIER ::= { enterprises 5002 }
audiocodesLTD                     OBJECT IDENTIFIER ::= { enterprises 5003 }
predictiveNetworks                OBJECT IDENTIFIER ::= { enterprises 5004 }
ncvision                          OBJECT IDENTIFIER ::= { enterprises 5005 }
vishwnetIndia                     OBJECT IDENTIFIER ::= { enterprises 5006 }
effectiveComputerSolutions        OBJECT IDENTIFIER ::= { enterprises 5007 }
drugstorecom                      OBJECT IDENTIFIER ::= { enterprises 5008 }
schiano                           OBJECT IDENTIFIER ::= { enterprises 5009 }
splashTechnology                  OBJECT IDENTIFIER ::= { enterprises 5010 }
scaldis                           OBJECT IDENTIFIER ::= { enterprises 5011 }
lottomaticaSpa                    OBJECT IDENTIFIER ::= { enterprises 5012 }
maverickInternetTechnology        OBJECT IDENTIFIER ::= { enterprises 5013 }
viacast                           OBJECT IDENTIFIER ::= { enterprises 5014 }
verbind                           OBJECT IDENTIFIER ::= { enterprises 5015 }
oregonStateUniversity             OBJECT IDENTIFIER ::= { enterprises 5016 }
universityOfAkron                 OBJECT IDENTIFIER ::= { enterprises 5017 }
ameritradeTechnologyGroup         OBJECT IDENTIFIER ::= { enterprises 5018 }
ebusinessInteractive              OBJECT IDENTIFIER ::= { enterprises 5019 }
sekwangEngCo                      OBJECT IDENTIFIER ::= { enterprises 5020 }
televisionInternacionalSADeCV     OBJECT IDENTIFIER ::= { enterprises 5021 }
equipeCommunicationsCorporation   OBJECT IDENTIFIER ::= { enterprises 5022 }
bitByBitSolutions                 OBJECT IDENTIFIER ::= { enterprises 5023 }
threeDomes                        OBJECT IDENTIFIER ::= { enterprises 5024 }
opus2RevenueTechnologies          OBJECT IDENTIFIER ::= { enterprises 5025 }
aspiroAB                          OBJECT IDENTIFIER ::= { enterprises 5026 }
orebroKommun                      OBJECT IDENTIFIER ::= { enterprises 5027 }
lightbridge                       OBJECT IDENTIFIER ::= { enterprises 5028 }
commaSoftAG                       OBJECT IDENTIFIER ::= { enterprises 5029 }
universityOfUlm                   OBJECT IDENTIFIER ::= { enterprises 5030 }
recovery                          OBJECT IDENTIFIER ::= { enterprises 5031 }
norscanInstruments                OBJECT IDENTIFIER ::= { enterprises 5032 }
echargeCorporation                OBJECT IDENTIFIER ::= { enterprises 5033 }
logicalsolutionsnet               OBJECT IDENTIFIER ::= { enterprises 5034 }
interNationalResearchInstitute    OBJECT IDENTIFIER ::= { enterprises 5035 }
inputSoftware                     OBJECT IDENTIFIER ::= { enterprises 5036 }
briLinkTechnologies               OBJECT IDENTIFIER ::= { enterprises 5037 }
tAndsSoftwareAssociates           OBJECT IDENTIFIER ::= { enterprises 5038 }
xstreamisPlc                      OBJECT IDENTIFIER ::= { enterprises 5039 }
wiesemannAndTheisGmbH             OBJECT IDENTIFIER ::= { enterprises 5040 }
menicxInternationalCo             OBJECT IDENTIFIER ::= { enterprises 5041 }
broadwing                         OBJECT IDENTIFIER ::= { enterprises 5042 }
merantInternational               OBJECT IDENTIFIER ::= { enterprises 5043 }
velocitySoftwareSystems           OBJECT IDENTIFIER ::= { enterprises 5044 }
bithopSystems                     OBJECT IDENTIFIER ::= { enterprises 5045 }
csSI                              OBJECT IDENTIFIER ::= { enterprises 5046 }
kimleyHornAndAssociates           OBJECT IDENTIFIER ::= { enterprises 5047 }
kudale                            OBJECT IDENTIFIER ::= { enterprises 5048 }
equifax                           OBJECT IDENTIFIER ::= { enterprises 5049 }
nordmarkNorLanConsult             OBJECT IDENTIFIER ::= { enterprises 5050 }
brixNetworks                      OBJECT IDENTIFIER ::= { enterprises 5051 }
interminePty                      OBJECT IDENTIFIER ::= { enterprises 5052 }
agilentTechnologies               OBJECT IDENTIFIER ::= { enterprises 5053 }
will                              OBJECT IDENTIFIER ::= { enterprises 5054 }
eolring                           OBJECT IDENTIFIER ::= { enterprises 5055 }
frankLima                         OBJECT IDENTIFIER ::= { enterprises 5056 }
giffordHesketh                    OBJECT IDENTIFIER ::= { enterprises 5057 }
avistarSystems                    OBJECT IDENTIFIER ::= { enterprises 5058 }
carmonaEngineeringServices        OBJECT IDENTIFIER ::= { enterprises 5059 }
singaporePressHoldings            OBJECT IDENTIFIER ::= { enterprises 5060 }
swisskey                          OBJECT IDENTIFIER ::= { enterprises 5061 }
dfnDirectoryServices              OBJECT IDENTIFIER ::= { enterprises 5062 }
telesta                           OBJECT IDENTIFIER ::= { enterprises 5063 }
deutschePostAG                    OBJECT IDENTIFIER ::= { enterprises 5064 }
privateexpresscom                 OBJECT IDENTIFIER ::= { enterprises 5065 }
netvision2                        OBJECT IDENTIFIER ::= { enterprises 5066 }
openSocietyFundBH                 OBJECT IDENTIFIER ::= { enterprises 5067 }
jewsihCommunityOfBosniaAndHerzegovina OBJECT IDENTIFIER ::= { enterprises 5068 }
callConnect                       OBJECT IDENTIFIER ::= { enterprises 5069 }
gannaConstruction                 OBJECT IDENTIFIER ::= { enterprises 5070 }
hiqNetworks                       OBJECT IDENTIFIER ::= { enterprises 5071 }
ditechCommunicationsCorporation   OBJECT IDENTIFIER ::= { enterprises 5072 }
knowhere                          OBJECT IDENTIFIER ::= { enterprises 5073 }
mivaCorporation                   OBJECT IDENTIFIER ::= { enterprises 5074 }
cnlCentralNetGmbH                 OBJECT IDENTIFIER ::= { enterprises 5075 }
longviewInternational             OBJECT IDENTIFIER ::= { enterprises 5076 }
clicknetSoftware                  OBJECT IDENTIFIER ::= { enterprises 5077 }
mediaVisionComputerTechnologies   OBJECT IDENTIFIER ::= { enterprises 5078 }
crosskeysSystemsCorporation       OBJECT IDENTIFIER ::= { enterprises 5079 }
powerSystems                      OBJECT IDENTIFIER ::= { enterprises 5080 }
empowermentGroup                  OBJECT IDENTIFIER ::= { enterprises 5081 }
moreMagicSoftwareMMSOy            OBJECT IDENTIFIER ::= { enterprises 5082 }
daktronics                        OBJECT IDENTIFIER ::= { enterprises 5083 }
sierracom                         OBJECT IDENTIFIER ::= { enterprises 5084 }
smartmove                         OBJECT IDENTIFIER ::= { enterprises 5085 }
icsAdvent                         OBJECT IDENTIFIER ::= { enterprises 5086 }
greatDragonTelecom                OBJECT IDENTIFIER ::= { enterprises 5087 }
digitalBurro                      OBJECT IDENTIFIER ::= { enterprises 5088 }
enternetSweden                    OBJECT IDENTIFIER ::= { enterprises 5089 }
carumba                           OBJECT IDENTIFIER ::= { enterprises 5090 }
norskeTrollAS                     OBJECT IDENTIFIER ::= { enterprises 5091 }
informationstechnologieAUSTRIAGESMBH OBJECT IDENTIFIER ::= { enterprises 5092 }
sdfEnterprise                     OBJECT IDENTIFIER ::= { enterprises 5093 }
theUniversityOfTulsa              OBJECT IDENTIFIER ::= { enterprises 5094 }
creditSuisseFirstBoston           OBJECT IDENTIFIER ::= { enterprises 5095 }
computerScienceAndEngineering     OBJECT IDENTIFIER ::= { enterprises 5096 }
rockMarketing                     OBJECT IDENTIFIER ::= { enterprises 5097 }
opuswaveNetworks                  OBJECT IDENTIFIER ::= { enterprises 5098 }
tricastMultimedia                 OBJECT IDENTIFIER ::= { enterprises 5100 }
novalabs                          OBJECT IDENTIFIER ::= { enterprises 5101 }
integroACS                        OBJECT IDENTIFIER ::= { enterprises 5102 }
foxcom                            OBJECT IDENTIFIER ::= { enterprises 5103 }
sarangnet                         OBJECT IDENTIFIER ::= { enterprises 5104 }
datangTelecomTechnologyCO         OBJECT IDENTIFIER ::= { enterprises 5105 }
elephantProject                   OBJECT IDENTIFIER ::= { enterprises 5106 }
pinklConsultingServices           OBJECT IDENTIFIER ::= { enterprises 5107 }
netbrowserCommunications          OBJECT IDENTIFIER ::= { enterprises 5108 }
chinaGREATDRAGONTELECOMMUNICATION OBJECT IDENTIFIER ::= { enterprises 5109 }
healthBusinessSystems             OBJECT IDENTIFIER ::= { enterprises 5110 }
medeaCorporation                  OBJECT IDENTIFIER ::= { enterprises 5111 }
corviaNetworks                    OBJECT IDENTIFIER ::= { enterprises 5112 }
gridware                          OBJECT IDENTIFIER ::= { enterprises 5113 }
futureFibreTechnologies           OBJECT IDENTIFIER ::= { enterprises 5114 }
powercomTechnologyCo              OBJECT IDENTIFIER ::= { enterprises 5115 }
ibm                               OBJECT IDENTIFIER ::= { enterprises 5116 }
kaelinColclasure                  OBJECT IDENTIFIER ::= { enterprises 5117 }
dantel                            OBJECT IDENTIFIER ::= { enterprises 5118 }
sycorAG                           OBJECT IDENTIFIER ::= { enterprises 5119 }
emfHomeInspection                 OBJECT IDENTIFIER ::= { enterprises 5120 }
leagueScoring                     OBJECT IDENTIFIER ::= { enterprises 5121 }
everestECommerce                  OBJECT IDENTIFIER ::= { enterprises 5122 }
lucentTechTaiwanTelco             OBJECT IDENTIFIER ::= { enterprises 5123 }
phoneticSystems                   OBJECT IDENTIFIER ::= { enterprises 5124 }
celesticaPower                    OBJECT IDENTIFIER ::= { enterprises 5125 }
symtrex                           OBJECT IDENTIFIER ::= { enterprises 5126 }
westernDigitalCorporation         OBJECT IDENTIFIER ::= { enterprises 5127 }
saitamaUniversityFarLaboratory    OBJECT IDENTIFIER ::= { enterprises 5128 }
macquarieUniversity               OBJECT IDENTIFIER ::= { enterprises 5129 }
omronCanada                       OBJECT IDENTIFIER ::= { enterprises 5130 }
lotzde                            OBJECT IDENTIFIER ::= { enterprises 5131 }
mammutNet                         OBJECT IDENTIFIER ::= { enterprises 5132 }
halfdomeSystems                   OBJECT IDENTIFIER ::= { enterprises 5133 }
ipUnity                           OBJECT IDENTIFIER ::= { enterprises 5134 }
cybersafeCorporation              OBJECT IDENTIFIER ::= { enterprises 5135 }
electronicMediaService            OBJECT IDENTIFIER ::= { enterprises 5136 }
dfc                               OBJECT IDENTIFIER ::= { enterprises 5137 }
easynetGroupPlc                   OBJECT IDENTIFIER ::= { enterprises 5138 }
arescom                           OBJECT IDENTIFIER ::= { enterprises 5139 }
compudiskSystems                  OBJECT IDENTIFIER ::= { enterprises 5140 }
hartEdwardsCorporation            OBJECT IDENTIFIER ::= { enterprises 5141 }
ivans                             OBJECT IDENTIFIER ::= { enterprises 5142 }
cerevaNetworks                    OBJECT IDENTIFIER ::= { enterprises 5143 }
ictElectronicsSA                  OBJECT IDENTIFIER ::= { enterprises 5145 }
eclipsysCorporation               OBJECT IDENTIFIER ::= { enterprises 5146 }
micex                             OBJECT IDENTIFIER ::= { enterprises 5147 }
ctcComputerTechnikCzakayGmbH      OBJECT IDENTIFIER ::= { enterprises 5148 }
managedObjectSolutions            OBJECT IDENTIFIER ::= { enterprises 5149 }
loudcloud                         OBJECT IDENTIFIER ::= { enterprises 5150 }
netgain2                          OBJECT IDENTIFIER ::= { enterprises 5151 }
cableAML                          OBJECT IDENTIFIER ::= { enterprises 5152 }
theUniversityOfAkron              OBJECT IDENTIFIER ::= { enterprises 5153 }
incytePharamaceuticals            OBJECT IDENTIFIER ::= { enterprises 5154 }
csAndSGHComputerSystemTechCo      OBJECT IDENTIFIER ::= { enterprises 5155 }
newproductshowroomcom             OBJECT IDENTIFIER ::= { enterprises 5156 }
theUniversityOfQueensland         OBJECT IDENTIFIER ::= { enterprises 5157 }
computechServices                 OBJECT IDENTIFIER ::= { enterprises 5158 }
ultraDoo                          OBJECT IDENTIFIER ::= { enterprises 5159 }
dainTelecomCo                     OBJECT IDENTIFIER ::= { enterprises 5160 }
moreheadStateUniversity           OBJECT IDENTIFIER ::= { enterprises 5161 }
societeEuropeenneDesSatellites    OBJECT IDENTIFIER ::= { enterprises 5162 }
digitalMarketplace                OBJECT IDENTIFIER ::= { enterprises 5163 }
cygnetTechnologies                OBJECT IDENTIFIER ::= { enterprises 5164 }
sassafrasSoftware                 OBJECT IDENTIFIER ::= { enterprises 5165 }
mercomSystems                     OBJECT IDENTIFIER ::= { enterprises 5166 }
orchestream                       OBJECT IDENTIFIER ::= { enterprises 5167 }
levitteProgramming                OBJECT IDENTIFIER ::= { enterprises 5168 }
netCONSULTINGSRL                  OBJECT IDENTIFIER ::= { enterprises 5169 }
aegisDataSystems                  OBJECT IDENTIFIER ::= { enterprises 5170 }
whizbangLabs                      OBJECT IDENTIFIER ::= { enterprises 5171 }
protocomDevelopmentSystems        OBJECT IDENTIFIER ::= { enterprises 5172 }
taquaSystems                      OBJECT IDENTIFIER ::= { enterprises 5173 }
privateexpressCom                 OBJECT IDENTIFIER ::= { enterprises 5174 }
lindsayElectronics                OBJECT IDENTIFIER ::= { enterprises 5175 }
winInformationSystems             OBJECT IDENTIFIER ::= { enterprises 5176 }
privateExpressTechnologiesPte     OBJECT IDENTIFIER ::= { enterprises 5177 }
telephonyExperts                  OBJECT IDENTIFIER ::= { enterprises 5178 }
arimaComputerCorp                 OBJECT IDENTIFIER ::= { enterprises 5179 }
theDocSpaceCompany                OBJECT IDENTIFIER ::= { enterprises 5180 }
firatUniversites                  OBJECT IDENTIFIER ::= { enterprises 5181 }
iThetaCorp                        OBJECT IDENTIFIER ::= { enterprises 5182 }
--                                 OBJECT IDENTIFIER ::= { enterprises 5183 }
cAndnTouristicAG                  OBJECT IDENTIFIER ::= { enterprises 5184 }
sungmiTelecomElectronicsCo        OBJECT IDENTIFIER ::= { enterprises 5185 }
--                                OBJECT IDENTIFIER ::= { enterprises 5186 }
bytware                           OBJECT IDENTIFIER ::= { enterprises 5187 }
bithopSYSTEMS                     OBJECT IDENTIFIER ::= { enterprises 5188 }
telefonicaID                      OBJECT IDENTIFIER ::= { enterprises 5189 }
organic                           OBJECT IDENTIFIER ::= { enterprises 5190 }
dekraAG                           OBJECT IDENTIFIER ::= { enterprises 5191 }
gothamNetworks                    OBJECT IDENTIFIER ::= { enterprises 5192 }
chemicalAbstractsService          OBJECT IDENTIFIER ::= { enterprises 5193 }
okanaganSpringBrewery             OBJECT IDENTIFIER ::= { enterprises 5194 }
adremSoftware                     OBJECT IDENTIFIER ::= { enterprises 5195 }
eTech                             OBJECT IDENTIFIER ::= { enterprises 5196 }
startupCom                        OBJECT IDENTIFIER ::= { enterprises 5197 }
--                                 OBJECT IDENTIFIER ::= { enterprises 5198 }
odeticsITS                        OBJECT IDENTIFIER ::= { enterprises 5199 }
enflexCorp                        OBJECT IDENTIFIER ::= { enterprises 5200 }
helsinkiUniversityOfTechnologyCSLaboratory OBJECT IDENTIFIER ::= { enterprises 5202 }
theNaqviGroup                     OBJECT IDENTIFIER ::= { enterprises 5203 }
clicknetSoftwareCorporation       OBJECT IDENTIFIER ::= { enterprises 5204 }
rubyTechCorp                      OBJECT IDENTIFIER ::= { enterprises 5205 }
voltaire                          OBJECT IDENTIFIER ::= { enterprises 5206 }
usaNETCORPORATIONS                OBJECT IDENTIFIER ::= { enterprises 5207 }
upmacsCommunications              OBJECT IDENTIFIER ::= { enterprises 5208 }
profoundRationalOrganization      OBJECT IDENTIFIER ::= { enterprises 5209 }
linklineFreegates                 OBJECT IDENTIFIER ::= { enterprises 5210 }
ncvision2                         OBJECT IDENTIFIER ::= { enterprises 5211 }
placeware                         OBJECT IDENTIFIER ::= { enterprises 5212 }
greylink                          OBJECT IDENTIFIER ::= { enterprises 5213 }
athensChamber                     OBJECT IDENTIFIER ::= { enterprises 5214 }
unitedConnections                 OBJECT IDENTIFIER ::= { enterprises 5215 }
seniorInformatica                 OBJECT IDENTIFIER ::= { enterprises 5216 }
sofhaGmbH                         OBJECT IDENTIFIER ::= { enterprises 5217 }
networksExperts                   OBJECT IDENTIFIER ::= { enterprises 5218 }
bevocal                           OBJECT IDENTIFIER ::= { enterprises 5219 }
worldTelecomLabs                  OBJECT IDENTIFIER ::= { enterprises 5220 }
wirelessSystemsInternational      OBJECT IDENTIFIER ::= { enterprises 5221 }
dantel2                           OBJECT IDENTIFIER ::= { enterprises 5222 }
koreaElectronicsTechnologyInstitute OBJECT IDENTIFIER ::= { enterprises 5223 }
hitachiDataSystems                OBJECT IDENTIFIER ::= { enterprises 5224 }
universidadDeCantabriaATC         OBJECT IDENTIFIER ::= { enterprises 5225 }
harmonixLimited                   OBJECT IDENTIFIER ::= { enterprises 5226 }
melcoINC                          OBJECT IDENTIFIER ::= { enterprises 5227 }
littlefeet                        OBJECT IDENTIFIER ::= { enterprises 5228 }
bigFishCommunications             OBJECT IDENTIFIER ::= { enterprises 5229 }
comroes                           OBJECT IDENTIFIER ::= { enterprises 5230 }
oswegoStateUniversity             OBJECT IDENTIFIER ::= { enterprises 5231 }
counterpaneInternetSecurity       OBJECT IDENTIFIER ::= { enterprises 5232 }
mercuryInteractiveCorp            OBJECT IDENTIFIER ::= { enterprises 5233 }
shenzhenSEDInfoTechCorp           OBJECT IDENTIFIER ::= { enterprises 5234 }
persistentSystemsPrivateLimited   OBJECT IDENTIFIER ::= { enterprises 5235 }
greatDragonTelecom2               OBJECT IDENTIFIER ::= { enterprises 5236 }
trustisLimited                    OBJECT IDENTIFIER ::= { enterprises 5237 }
societaGEneraleDiInformatica      OBJECT IDENTIFIER ::= { enterprises 5238 }
feste                             OBJECT IDENTIFIER ::= { enterprises 5239 }
rand                              OBJECT IDENTIFIER ::= { enterprises 5240 }
techmathAG                        OBJECT IDENTIFIER ::= { enterprises 5241 }
enviloggAB                        OBJECT IDENTIFIER ::= { enterprises 5242 }
icis                              OBJECT IDENTIFIER ::= { enterprises 5243 }
casey                             OBJECT IDENTIFIER ::= { enterprises 5244 }
quarterstoneCommunications        OBJECT IDENTIFIER ::= { enterprises 5245 }
ss8Networks                       OBJECT IDENTIFIER ::= { enterprises 5246 }
zinniaDesign                      OBJECT IDENTIFIER ::= { enterprises 5247 }
michaelBrehm                      OBJECT IDENTIFIER ::= { enterprises 5248 }
warnerLambert                     OBJECT IDENTIFIER ::= { enterprises 5249 }
center7                           OBJECT IDENTIFIER ::= { enterprises 5250 }
donaldEBynum                      OBJECT IDENTIFIER ::= { enterprises 5251 }
cisTechnology                     OBJECT IDENTIFIER ::= { enterprises 5252 }
aldebaran                         OBJECT IDENTIFIER ::= { enterprises 5253 }
datangTelecomTechnologyCO2        OBJECT IDENTIFIER ::= { enterprises 5254 }
europki                           OBJECT IDENTIFIER ::= { enterprises 5255 }
freeonlineComAuPty                OBJECT IDENTIFIER ::= { enterprises 5256 }
axusMicrosystems                  OBJECT IDENTIFIER ::= { enterprises 5257 }
zetaTechnologiesCo                OBJECT IDENTIFIER ::= { enterprises 5258 }
matraSYSTEMESAndINFORMATION       OBJECT IDENTIFIER ::= { enterprises 5259 }
digitalEngineering                OBJECT IDENTIFIER ::= { enterprises 5260 }
lutherDANIEL                      OBJECT IDENTIFIER ::= { enterprises 5261 }
qwikwireNET                       OBJECT IDENTIFIER ::= { enterprises 5262 }
caisINTERNET                      OBJECT IDENTIFIER ::= { enterprises 5263 }
varianMedicalSystems              OBJECT IDENTIFIER ::= { enterprises 5264 }
teledanmarkErhverv                OBJECT IDENTIFIER ::= { enterprises 5265 }
johannesGutenbergUniversitaetMainz OBJECT IDENTIFIER ::= { enterprises 5266 }
hongKongUniversityOfScienceAndTechnology OBJECT IDENTIFIER ::= { enterprises 5267 }
ikeaITCENTERAB                    OBJECT IDENTIFIER ::= { enterprises 5268 }
theFantasticCorporation           OBJECT IDENTIFIER ::= { enterprises 5269 }
da6dTechnologies                  OBJECT IDENTIFIER ::= { enterprises 5270 }
comverseNetworkSystems2           OBJECT IDENTIFIER ::= { enterprises 5271 }
wTradeTechnologies                OBJECT IDENTIFIER ::= { enterprises 5272 }
unistraTechnologies               OBJECT IDENTIFIER ::= { enterprises 5273 }
unifX                             OBJECT IDENTIFIER ::= { enterprises 5274 }
malibuNetworks                    OBJECT IDENTIFIER ::= { enterprises 5275 }
hearmecom                         OBJECT IDENTIFIER ::= { enterprises 5276 }
sarangnet2                        OBJECT IDENTIFIER ::= { enterprises 5277 }
swisscomAG2                       OBJECT IDENTIFIER ::= { enterprises 5278 }
supportDirectorySolutions         OBJECT IDENTIFIER ::= { enterprises 5279 }
citi                              OBJECT IDENTIFIER ::= { enterprises 5280 }
graeffetCommunications            OBJECT IDENTIFIER ::= { enterprises 5281 }
connectedSystems                  OBJECT IDENTIFIER ::= { enterprises 5282 }
checkfreeCorporation              OBJECT IDENTIFIER ::= { enterprises 5283 }
filanetCorporation                OBJECT IDENTIFIER ::= { enterprises 5284 }
networkExperts                    OBJECT IDENTIFIER ::= { enterprises 5285 }
calence                           OBJECT IDENTIFIER ::= { enterprises 5286 }
persistentSystemsPrivateLimited2  OBJECT IDENTIFIER ::= { enterprises 5287 }
aPlusNetworks                     OBJECT IDENTIFIER ::= { enterprises 5288 }
vidyawebCom                       OBJECT IDENTIFIER ::= { enterprises 5289 }
guide                             OBJECT IDENTIFIER ::= { enterprises 5290 }
bloemenveilingAalsmeer            OBJECT IDENTIFIER ::= { enterprises 5291 }
pirusNetworks                     OBJECT IDENTIFIER ::= { enterprises 5292 }
hyosungCORPORATION                OBJECT IDENTIFIER ::= { enterprises 5293 }
infinityTrade                     OBJECT IDENTIFIER ::= { enterprises 5294 }
digitalthink                      OBJECT IDENTIFIER ::= { enterprises 5295 }
ipcellTechnologies                OBJECT IDENTIFIER ::= { enterprises 5296 }
baxworks                          OBJECT IDENTIFIER ::= { enterprises 5297 }
xputercom                         OBJECT IDENTIFIER ::= { enterprises 5298 }
audemat                           OBJECT IDENTIFIER ::= { enterprises 5299 }
jetstreamCommunications           OBJECT IDENTIFIER ::= { enterprises 5300 }
pentasafe                         OBJECT IDENTIFIER ::= { enterprises 5301 }
advancedHealthTechnologies        OBJECT IDENTIFIER ::= { enterprises 5302 }
ipmobile                          OBJECT IDENTIFIER ::= { enterprises 5303 }
airslideSystems                   OBJECT IDENTIFIER ::= { enterprises 5304 }
iitKANPUR                         OBJECT IDENTIFIER ::= { enterprises 5305 }
xesystems                         OBJECT IDENTIFIER ::= { enterprises 5306 }
ciprico                           OBJECT IDENTIFIER ::= { enterprises 5307 }
siemens2                          OBJECT IDENTIFIER ::= { enterprises 5308 }
edelwebSA                         OBJECT IDENTIFIER ::= { enterprises 5309 }
depositoryTrustAndClearingCorporation OBJECT IDENTIFIER ::= { enterprises 5310 }
fAndf                             OBJECT IDENTIFIER ::= { enterprises 5311 }
digicertSDN                       OBJECT IDENTIFIER ::= { enterprises 5312 }
revlis                            OBJECT IDENTIFIER ::= { enterprises 5313 }
baunwallAS                        OBJECT IDENTIFIER ::= { enterprises 5314 }
ccit                              OBJECT IDENTIFIER ::= { enterprises 5315 }
guideUnusual                      OBJECT IDENTIFIER ::= { enterprises 5316 }
adaptiveComputerDevelopmentCorp   OBJECT IDENTIFIER ::= { enterprises 5317 }
robertBoschGmbH                   OBJECT IDENTIFIER ::= { enterprises 5318 }
earthwatch                        OBJECT IDENTIFIER ::= { enterprises 5319 }
suretyTechnologies                OBJECT IDENTIFIER ::= { enterprises 5320 }
burritoorg                        OBJECT IDENTIFIER ::= { enterprises 5321 }
padlSoftwarePty                   OBJECT IDENTIFIER ::= { enterprises 5322 }
telrad                            OBJECT IDENTIFIER ::= { enterprises 5323 }
deltaNetworks                     OBJECT IDENTIFIER ::= { enterprises 5324 }
cmgi                              OBJECT IDENTIFIER ::= { enterprises 5325 }
lightchip                         OBJECT IDENTIFIER ::= { enterprises 5326 }
kimComputing                      OBJECT IDENTIFIER ::= { enterprises 5327 }
northCommunications               OBJECT IDENTIFIER ::= { enterprises 5328 }
shorelineTeleworks                OBJECT IDENTIFIER ::= { enterprises 5329 }
spacelinkSystems                  OBJECT IDENTIFIER ::= { enterprises 5330 }
oiELECTRICCO                      OBJECT IDENTIFIER ::= { enterprises 5331 }
informationFreeway                OBJECT IDENTIFIER ::= { enterprises 5332 }
celeraGenomics                    OBJECT IDENTIFIER ::= { enterprises 5333 }
start                             OBJECT IDENTIFIER ::= { enterprises 5334 }
multifunctionProductsAssociation  OBJECT IDENTIFIER ::= { enterprises 5335 }
bluekitecom                       OBJECT IDENTIFIER ::= { enterprises 5336 }
ciprico2                          OBJECT IDENTIFIER ::= { enterprises 5337 }
eldecCorporation                  OBJECT IDENTIFIER ::= { enterprises 5338 }
visiowave                         OBJECT IDENTIFIER ::= { enterprises 5339 }
citi2                             OBJECT IDENTIFIER ::= { enterprises 5340 }
pcNetworkDesign                   OBJECT IDENTIFIER ::= { enterprises 5341 }
sensormatic                       OBJECT IDENTIFIER ::= { enterprises 5342 }
loneWolfComputing                 OBJECT IDENTIFIER ::= { enterprises 5343 }
originativeSolutions              OBJECT IDENTIFIER ::= { enterprises 5344 }
sungmiTELECOMELECTRONICSCO        OBJECT IDENTIFIER ::= { enterprises 5345 }
ssmHealthCare                     OBJECT IDENTIFIER ::= { enterprises 5346 }
geHarrisAviationInformationSolutions OBJECT IDENTIFIER ::= { enterprises 5347 }
timespaceRadioAB                  OBJECT IDENTIFIER ::= { enterprises 5348 }
inalpNetworks                     OBJECT IDENTIFIER ::= { enterprises 5349 }
infotronSystemCorp                OBJECT IDENTIFIER ::= { enterprises 5350 }
atmSA                             OBJECT IDENTIFIER ::= { enterprises 5351 }
maelstrom                         OBJECT IDENTIFIER ::= { enterprises 5352 }
evsBroadcastEquipment             OBJECT IDENTIFIER ::= { enterprises 5353 }
simplement                        OBJECT IDENTIFIER ::= { enterprises 5354 }
elandTechnologies                 OBJECT IDENTIFIER ::= { enterprises 5355 }
objectOrientedPty                 OBJECT IDENTIFIER ::= { enterprises 5356 }
evansComputerConsulting           OBJECT IDENTIFIER ::= { enterprises 5357 }
enhancedGlobalConvergenceServices OBJECT IDENTIFIER ::= { enterprises 5358 }
innoventry                        OBJECT IDENTIFIER ::= { enterprises 5359 }
haedong                           OBJECT IDENTIFIER ::= { enterprises 5360 }
westbridgeDesign                  OBJECT IDENTIFIER ::= { enterprises 5361 }
qasysCORP                         OBJECT IDENTIFIER ::= { enterprises 5362 }
rSmithEngineeringCo               OBJECT IDENTIFIER ::= { enterprises 5363 }
certallFinlandOY                  OBJECT IDENTIFIER ::= { enterprises 5364 }
neartek                           OBJECT IDENTIFIER ::= { enterprises 5365 }
charlotte                         OBJECT IDENTIFIER ::= { enterprises 5366 }
telenaSpA                         OBJECT IDENTIFIER ::= { enterprises 5367 }
coreexpress                       OBJECT IDENTIFIER ::= { enterprises 5368 }
apdCommunicationsLimited          OBJECT IDENTIFIER ::= { enterprises 5369 }
bancoZARAGOZANOSA                 OBJECT IDENTIFIER ::= { enterprises 5370 }
netsubjectCanada                  OBJECT IDENTIFIER ::= { enterprises 5371 }
mycfo                             OBJECT IDENTIFIER ::= { enterprises 5372 }
openTelecommunicationsLimited     OBJECT IDENTIFIER ::= { enterprises 5373 }
dirigo                            OBJECT IDENTIFIER ::= { enterprises 5374 }
baeSYSTEMS2                       OBJECT IDENTIFIER ::= { enterprises 5375 }
oleane                            OBJECT IDENTIFIER ::= { enterprises 5376 }
trinexus                          OBJECT IDENTIFIER ::= { enterprises 5377 }
prairiefyreSoftware               OBJECT IDENTIFIER ::= { enterprises 5378 }
colonialStateBank                 OBJECT IDENTIFIER ::= { enterprises 5379 }
cdot                              OBJECT IDENTIFIER ::= { enterprises 5380 }
supernova                         OBJECT IDENTIFIER ::= { enterprises 5381 }
irisTechnologies                  OBJECT IDENTIFIER ::= { enterprises 5382 }
ifleet                            OBJECT IDENTIFIER ::= { enterprises 5383 }
tsurukiPromotions                 OBJECT IDENTIFIER ::= { enterprises 5384 }
cityNETCZ                         OBJECT IDENTIFIER ::= { enterprises 5385 }
mSTechnologyConsultants           OBJECT IDENTIFIER ::= { enterprises 5386 }
hyperfeed                         OBJECT IDENTIFIER ::= { enterprises 5387 }
networkAlchemy2                   OBJECT IDENTIFIER ::= { enterprises 5388 }
interTel                          OBJECT IDENTIFIER ::= { enterprises 5389 }
opnetTechnologiesCo2              OBJECT IDENTIFIER ::= { enterprises 5390 }
tycoSubmarineSystems              OBJECT IDENTIFIER ::= { enterprises 5391 }
onlineCreations                   OBJECT IDENTIFIER ::= { enterprises 5392 }
renault                           OBJECT IDENTIFIER ::= { enterprises 5393 }
gateway                           OBJECT IDENTIFIER ::= { enterprises 5394 }
laurelNetworks                    OBJECT IDENTIFIER ::= { enterprises 5395 }
bigchalkcom                       OBJECT IDENTIFIER ::= { enterprises 5396 }
standardAndPoor2                  OBJECT IDENTIFIER ::= { enterprises 5397 }
elephantx                         OBJECT IDENTIFIER ::= { enterprises 5398 }
extremis                          OBJECT IDENTIFIER ::= { enterprises 5399 }
evercomSystemsInternational       OBJECT IDENTIFIER ::= { enterprises 5400 }
masterSoft                        OBJECT IDENTIFIER ::= { enterprises 5401 }
idf                               OBJECT IDENTIFIER ::= { enterprises 5402 }
vircom                            OBJECT IDENTIFIER ::= { enterprises 5403 }
econvergencePty                   OBJECT IDENTIFIER ::= { enterprises 5404 }
startPrinterEquipmentCo           OBJECT IDENTIFIER ::= { enterprises 5405 }
nickConte                         OBJECT IDENTIFIER ::= { enterprises 5406 }
netsupportGmbH                    OBJECT IDENTIFIER ::= { enterprises 5407 }
intellitelCommunications          OBJECT IDENTIFIER ::= { enterprises 5408 }
eastWestConsultingKK              OBJECT IDENTIFIER ::= { enterprises 5409 }
lesHoward                         OBJECT IDENTIFIER ::= { enterprises 5410 }
signalsoftCorporation             OBJECT IDENTIFIER ::= { enterprises 5411 }
zantazcom                         OBJECT IDENTIFIER ::= { enterprises 5412 }
peoplewebCommunications           OBJECT IDENTIFIER ::= { enterprises 5413 }
johnAndAssociate                  OBJECT IDENTIFIER ::= { enterprises 5414 }
fujitsuSingaporePte               OBJECT IDENTIFIER ::= { enterprises 5415 }
nesral                            OBJECT IDENTIFIER ::= { enterprises 5416 }
absaGroupLTD                      OBJECT IDENTIFIER ::= { enterprises 5417 }
fortis                            OBJECT IDENTIFIER ::= { enterprises 5418 }
cambridgeBroadband                OBJECT IDENTIFIER ::= { enterprises 5419 }
spiderTechnologies                OBJECT IDENTIFIER ::= { enterprises 5420 }
mariettaDodge                     OBJECT IDENTIFIER ::= { enterprises 5421 }
rhcEnterprises                    OBJECT IDENTIFIER ::= { enterprises 5422 }
mcleodusa                         OBJECT IDENTIFIER ::= { enterprises 5423 }
columbiaDiversifiedServices       OBJECT IDENTIFIER ::= { enterprises 5424 }
netspaceOnlineSystems             OBJECT IDENTIFIER ::= { enterprises 5425 }
gadline                           OBJECT IDENTIFIER ::= { enterprises 5426 }
michaelStroederSoftwareentwicklung OBJECT IDENTIFIER ::= { enterprises 5427 }
smartpipes                        OBJECT IDENTIFIER ::= { enterprises 5428 }
propackDataSoftUndHardwareEntwicklungsGmbH OBJECT IDENTIFIER ::= { enterprises 5429 }
masterguardKG                     OBJECT IDENTIFIER ::= { enterprises 5430 }
lmDigital                         OBJECT IDENTIFIER ::= { enterprises 5431 }
sightpath                         OBJECT IDENTIFIER ::= { enterprises 5432 }
netonomy                          OBJECT IDENTIFIER ::= { enterprises 5433 }
advancedHiTechCorporation         OBJECT IDENTIFIER ::= { enterprises 5434 }
ovislinkCorp                      OBJECT IDENTIFIER ::= { enterprises 5435 }
open                              OBJECT IDENTIFIER ::= { enterprises 5436 }
pensarCorporation                 OBJECT IDENTIFIER ::= { enterprises 5437 }
utrechtSchoolOfArts               OBJECT IDENTIFIER ::= { enterprises 5438 }
parallel                          OBJECT IDENTIFIER ::= { enterprises 5439 }
primeon                           OBJECT IDENTIFIER ::= { enterprises 5440 }
theTimkenCompany                  OBJECT IDENTIFIER ::= { enterprises 5441 }
newZealandPostLimited             OBJECT IDENTIFIER ::= { enterprises 5442 }
nekemacom                         OBJECT IDENTIFIER ::= { enterprises 5443 }
joeMinineri                       OBJECT IDENTIFIER ::= { enterprises 5444 }
metrostatTechnologies             OBJECT IDENTIFIER ::= { enterprises 5445 }
skygateTechnology                 OBJECT IDENTIFIER ::= { enterprises 5446 }
aeolonResearch                    OBJECT IDENTIFIER ::= { enterprises 5447 }
kykinkCommunicationsCorp          OBJECT IDENTIFIER ::= { enterprises 5448 }
onenetpluscom                     OBJECT IDENTIFIER ::= { enterprises 5449 }
iLink                             OBJECT IDENTIFIER ::= { enterprises 5450 }
segaintersettleAG                 OBJECT IDENTIFIER ::= { enterprises 5451 }
businessLayers                    OBJECT IDENTIFIER ::= { enterprises 5452 }
intelis                           OBJECT IDENTIFIER ::= { enterprises 5453 }
trangoSystems                     OBJECT IDENTIFIER ::= { enterprises 5454 }
artemisManagementSystems          OBJECT IDENTIFIER ::= { enterprises 5455 }
focusOnlineGmbH                   OBJECT IDENTIFIER ::= { enterprises 5456 }
castlenetTechnology               OBJECT IDENTIFIER ::= { enterprises 5457 }
gupta                             OBJECT IDENTIFIER ::= { enterprises 5458 }
santoolscom                       OBJECT IDENTIFIER ::= { enterprises 5459 }
broadlinkCommunications           OBJECT IDENTIFIER ::= { enterprises 5460 }
ksi                               OBJECT IDENTIFIER ::= { enterprises 5461 }
resumecom                         OBJECT IDENTIFIER ::= { enterprises 5462 }
eduardoFermin                     OBJECT IDENTIFIER ::= { enterprises 5463 }
manukauInstituteOfTechnology      OBJECT IDENTIFIER ::= { enterprises 5464 }
ebusinessTechnologies             OBJECT IDENTIFIER ::= { enterprises 5465 }
internationalBiometricSociety     OBJECT IDENTIFIER ::= { enterprises 5466 }
telefonicaINVESTIGACIONYDESARROLLO OBJECT IDENTIFIER ::= { enterprises 5467 }
actelisNetworks                   OBJECT IDENTIFIER ::= { enterprises 5468 }
codebase                          OBJECT IDENTIFIER ::= { enterprises 5469 }
transparityLimited                OBJECT IDENTIFIER ::= { enterprises 5470 }
dieSchweizerischePost             OBJECT IDENTIFIER ::= { enterprises 5471 }
timeproof                         OBJECT IDENTIFIER ::= { enterprises 5472 }
algacom                           OBJECT IDENTIFIER ::= { enterprises 5473 }
ericssonAheadCommunicationsSystemsGmbH OBJECT IDENTIFIER ::= { enterprises 5474 }
thysysEngineering                 OBJECT IDENTIFIER ::= { enterprises 5475 }
apex                              OBJECT IDENTIFIER ::= { enterprises 5476 }
netattach                         OBJECT IDENTIFIER ::= { enterprises 5477 }
criticalPathBerlinLEM             OBJECT IDENTIFIER ::= { enterprises 5478 }
pinnacleDataSystems               OBJECT IDENTIFIER ::= { enterprises 5479 }
tSqware                           OBJECT IDENTIFIER ::= { enterprises 5480 }
agenciaDeCertificionElectronica   OBJECT IDENTIFIER ::= { enterprises 5481 }
murakamiElectroCommunicationLaboratories OBJECT IDENTIFIER ::= { enterprises 5482 }
netensity                         OBJECT IDENTIFIER ::= { enterprises 5483 }
universityOfTheAegean             OBJECT IDENTIFIER ::= { enterprises 5484 }
theOPENGroup                      OBJECT IDENTIFIER ::= { enterprises 5485 }
chinaMerchantsBank                OBJECT IDENTIFIER ::= { enterprises 5486 }
multitradeSpa                     OBJECT IDENTIFIER ::= { enterprises 5487 }
temblast                          OBJECT IDENTIFIER ::= { enterprises 5488 }
alsInternational                  OBJECT IDENTIFIER ::= { enterprises 5489 }
commnav                           OBJECT IDENTIFIER ::= { enterprises 5490 }
upsManufacturing                  OBJECT IDENTIFIER ::= { enterprises 5491 }
telephia                          OBJECT IDENTIFIER ::= { enterprises 5492 }
palmComputing                     OBJECT IDENTIFIER ::= { enterprises 5493 }
marathonInnovations               OBJECT IDENTIFIER ::= { enterprises 5494 }
convergenceEquipmentCompany       OBJECT IDENTIFIER ::= { enterprises 5495 }
gemplus                           OBJECT IDENTIFIER ::= { enterprises 5496 }
trondentDevelopmentCorp           OBJECT IDENTIFIER ::= { enterprises 5497 }
kardiniaSoftwarePty               OBJECT IDENTIFIER ::= { enterprises 5498 }
yhkimCo                           OBJECT IDENTIFIER ::= { enterprises 5499 }
gemeentelijkHavenbedrijfRotterdam OBJECT IDENTIFIER ::= { enterprises 5500 }
nttPCCommunications               OBJECT IDENTIFIER ::= { enterprises 5501 }
canonAptex                        OBJECT IDENTIFIER ::= { enterprises 5502 }
orindaTechnologyGroup             OBJECT IDENTIFIER ::= { enterprises 5503 }
zhoneTechnologies                 OBJECT IDENTIFIER ::= { enterprises 5504 }
metrostatTechnologies2            OBJECT IDENTIFIER ::= { enterprises 5505 }
digitalX                          OBJECT IDENTIFIER ::= { enterprises 5506 }
tightInformatics                  OBJECT IDENTIFIER ::= { enterprises 5507 }
swodOrg                           OBJECT IDENTIFIER ::= { enterprises 5508 }
bAndeConstructionCoDennisMulder   OBJECT IDENTIFIER ::= { enterprises 5509 }
prismtech                         OBJECT IDENTIFIER ::= { enterprises 5510 }
syscall                           OBJECT IDENTIFIER ::= { enterprises 5511 }
gmdFIRST                          OBJECT IDENTIFIER ::= { enterprises 5512 }
ixl                               OBJECT IDENTIFIER ::= { enterprises 5513 }
timelineTechnology                OBJECT IDENTIFIER ::= { enterprises 5514 }
directoryToolsAndApplicationServices OBJECT IDENTIFIER ::= { enterprises 5515 }
secureworks                       OBJECT IDENTIFIER ::= { enterprises 5516 }
rapid5Networks                    OBJECT IDENTIFIER ::= { enterprises 5517 }
tdsTelecom                        OBJECT IDENTIFIER ::= { enterprises 5518 }
lsitec                            OBJECT IDENTIFIER ::= { enterprises 5519 }
alfredWegenerInstituteForPolarAndMarineResearch OBJECT IDENTIFIER ::= { enterprises 5520 }
stJohnHealthSystem                OBJECT IDENTIFIER ::= { enterprises 5521 }
cybernetCorporation               OBJECT IDENTIFIER ::= { enterprises 5522 }
grcp                              OBJECT IDENTIFIER ::= { enterprises 5523 }
emoryUniversity                   OBJECT IDENTIFIER ::= { enterprises 5524 }
ssf                               OBJECT IDENTIFIER ::= { enterprises 5525 }
adero                             OBJECT IDENTIFIER ::= { enterprises 5526 }
contextSystemsGroup               OBJECT IDENTIFIER ::= { enterprises 5527 }
netbotz                           OBJECT IDENTIFIER ::= { enterprises 5528 }
neoformacom                       OBJECT IDENTIFIER ::= { enterprises 5529 }
cescom                            OBJECT IDENTIFIER ::= { enterprises 5530 }
mienInformationSolutions          OBJECT IDENTIFIER ::= { enterprises 5531 }
qTelecellGmbH                     OBJECT IDENTIFIER ::= { enterprises 5532 }
wideawake                         OBJECT IDENTIFIER ::= { enterprises 5533 }
vogonAB                           OBJECT IDENTIFIER ::= { enterprises 5534 }
threeRdGenerationPartnershipProject2 OBJECT IDENTIFIER ::= { enterprises 5535 }
quintusCorporation                OBJECT IDENTIFIER ::= { enterprises 5536 }
comdialCorporation                OBJECT IDENTIFIER ::= { enterprises 5537 }
micronTechInformationCoKr         OBJECT IDENTIFIER ::= { enterprises 5538 }
cybertekHoldings                  OBJECT IDENTIFIER ::= { enterprises 5539 }
aachenUniversityOfTechnology      OBJECT IDENTIFIER ::= { enterprises 5540 }
parageaCommunications             OBJECT IDENTIFIER ::= { enterprises 5541 }
eonCommunicationsCorporation      OBJECT IDENTIFIER ::= { enterprises 5542 }
iniempHOLDINGSCORPORATIONSL       OBJECT IDENTIFIER ::= { enterprises 5543 }
thomsonCSFSystemsCanada           OBJECT IDENTIFIER ::= { enterprises 5544 }
tantauSoftware                    OBJECT IDENTIFIER ::= { enterprises 5545 }
mailvision                        OBJECT IDENTIFIER ::= { enterprises 5546 }
bsquareCorporation                OBJECT IDENTIFIER ::= { enterprises 5547 }
cobaltNetworks                    OBJECT IDENTIFIER ::= { enterprises 5548 }
timestenPerformanceSoftware       OBJECT IDENTIFIER ::= { enterprises 5549 }
monggo                            OBJECT IDENTIFIER ::= { enterprises 5550 }
oscilloquartz                     OBJECT IDENTIFIER ::= { enterprises 5551 }
airAtlantaIcelandic               OBJECT IDENTIFIER ::= { enterprises 5552 }
macromediaEBusinessSolutions      OBJECT IDENTIFIER ::= { enterprises 5553 }
spotcastCommunications            OBJECT IDENTIFIER ::= { enterprises 5554 }
authentic8Pty                     OBJECT IDENTIFIER ::= { enterprises 5555 }
serviceFactory                    OBJECT IDENTIFIER ::= { enterprises 5556 }
onemaincom                        OBJECT IDENTIFIER ::= { enterprises 5557 }
sLinkCorporation                  OBJECT IDENTIFIER ::= { enterprises 5558 }
vitriaTechnology                  OBJECT IDENTIFIER ::= { enterprises 5559 }
theColorRegistry                  OBJECT IDENTIFIER ::= { enterprises 5560 }
ndWave                            OBJECT IDENTIFIER ::= { enterprises 5561 }
redkneecom                        OBJECT IDENTIFIER ::= { enterprises 5562 }
olaInternet                       OBJECT IDENTIFIER ::= { enterprises 5563 }
omegaEnterprise                   OBJECT IDENTIFIER ::= { enterprises 5564 }
syswaveCo                         OBJECT IDENTIFIER ::= { enterprises 5565 }
visionglobalNetworkCorporation    OBJECT IDENTIFIER ::= { enterprises 5566 }
riverstoneNetworks                OBJECT IDENTIFIER ::= { enterprises 5567 }
southviewTechnologies             OBJECT IDENTIFIER ::= { enterprises 5568 }
soluzioniTecnologicheBancarieSrl  OBJECT IDENTIFIER ::= { enterprises 5569 }
sonyPicturesEntertainment         OBJECT IDENTIFIER ::= { enterprises 5570 }
gettherecom                       OBJECT IDENTIFIER ::= { enterprises 5571 }
hotekTechnology                   OBJECT IDENTIFIER ::= { enterprises 5572 }
tong                              OBJECT IDENTIFIER ::= { enterprises 5573 }
bankengine                        OBJECT IDENTIFIER ::= { enterprises 5574 }
certengine                        OBJECT IDENTIFIER ::= { enterprises 5575 }
tillPhotonicsGmbH                 OBJECT IDENTIFIER ::= { enterprises 5576 }
persimmonDevelopment              OBJECT IDENTIFIER ::= { enterprises 5577 }
newMexicoStateUniversity          OBJECT IDENTIFIER ::= { enterprises 5578 }
mercata                           OBJECT IDENTIFIER ::= { enterprises 5579 }
exe                               OBJECT IDENTIFIER ::= { enterprises 5580 }
communicationsNetworksOfAfrica    OBJECT IDENTIFIER ::= { enterprises 5581 }
itrustSolutionsAG                 OBJECT IDENTIFIER ::= { enterprises 5582 }
mdInformationSystems              OBJECT IDENTIFIER ::= { enterprises 5583 }
generalBandwidth                  OBJECT IDENTIFIER ::= { enterprises 5584 }
veryCleverSoftware                OBJECT IDENTIFIER ::= { enterprises 5585 }
ipwireless                        OBJECT IDENTIFIER ::= { enterprises 5586 }
flughafenMuenchenGmbH             OBJECT IDENTIFIER ::= { enterprises 5587 }
thomcastCommunication             OBJECT IDENTIFIER ::= { enterprises 5588 }
synopsys                          OBJECT IDENTIFIER ::= { enterprises 5589 }
marimba2                          OBJECT IDENTIFIER ::= { enterprises 5590 }
societyOfCableTelecommunicationsEngineers OBJECT IDENTIFIER ::= { enterprises 5591 }
wilsonAndSanders                  OBJECT IDENTIFIER ::= { enterprises 5592 }
magnumTechnologies                OBJECT IDENTIFIER ::= { enterprises 5593 }
koankeisoCo                       OBJECT IDENTIFIER ::= { enterprises 5594 }
ingrianSystems                    OBJECT IDENTIFIER ::= { enterprises 5595 }
tandbergASA                       OBJECT IDENTIFIER ::= { enterprises 5596 }
meinbergFunkuhren                 OBJECT IDENTIFIER ::= { enterprises 5597 }
submarineWarfareSystemsCentre     OBJECT IDENTIFIER ::= { enterprises 5598 }
compSciAndEng                     OBJECT IDENTIFIER ::= { enterprises 5599 }
clearstreamServices               OBJECT IDENTIFIER ::= { enterprises 5600 }
clearstreamBanking                OBJECT IDENTIFIER ::= { enterprises 5601 }
tRSystems                         OBJECT IDENTIFIER ::= { enterprises 5602 }
capitalOneFinancialServices       OBJECT IDENTIFIER ::= { enterprises 5603 }
digitSafe                         OBJECT IDENTIFIER ::= { enterprises 5604 }
williamDataSystems                OBJECT IDENTIFIER ::= { enterprises 5605 }
cerplusSA                         OBJECT IDENTIFIER ::= { enterprises 5606 }
erwannABALEA                      OBJECT IDENTIFIER ::= { enterprises 5607 }
redPlanetTechnologies             OBJECT IDENTIFIER ::= { enterprises 5608 }
smartleaf                         OBJECT IDENTIFIER ::= { enterprises 5609 }
exbitTechnology                   OBJECT IDENTIFIER ::= { enterprises 5610 }
vmunixorg                         OBJECT IDENTIFIER ::= { enterprises 5611 }
koreaDataCommunications           OBJECT IDENTIFIER ::= { enterprises 5612 }
primusServicesGroup               OBJECT IDENTIFIER ::= { enterprises 5613 }
sonybpeSPD                        OBJECT IDENTIFIER ::= { enterprises 5614 }
inheritSAB                        OBJECT IDENTIFIER ::= { enterprises 5615 }
tekops                            OBJECT IDENTIFIER ::= { enterprises 5616 }
trioCommunications2000Pty         OBJECT IDENTIFIER ::= { enterprises 5617 }
warenet                           OBJECT IDENTIFIER ::= { enterprises 5618 }
amaranthNetworks                  OBJECT IDENTIFIER ::= { enterprises 5619 }
cfxCommunications                 OBJECT IDENTIFIER ::= { enterprises 5620 }
heriotWattUniversity              OBJECT IDENTIFIER ::= { enterprises 5621 }
dregisGmbH                        OBJECT IDENTIFIER ::= { enterprises 5622 }
kpmg2                             OBJECT IDENTIFIER ::= { enterprises 5623 }
enterasysNetworks                 OBJECT IDENTIFIER ::= { enterprises 5624 }
aGell                             OBJECT IDENTIFIER ::= { enterprises 5625 }
internetBarter                    OBJECT IDENTIFIER ::= { enterprises 5626 }
hitachiProcessComputerEngineering OBJECT IDENTIFIER ::= { enterprises 5627 }
xoSoft                            OBJECT IDENTIFIER ::= { enterprises 5628 }
continuusSoftwareCorporation      OBJECT IDENTIFIER ::= { enterprises 5629 }
exioCommunications                OBJECT IDENTIFIER ::= { enterprises 5630 }
allianceSystems                   OBJECT IDENTIFIER ::= { enterprises 5631 }
telepassportHellasSA              OBJECT IDENTIFIER ::= { enterprises 5632 }
basfComputerServicesGmbH          OBJECT IDENTIFIER ::= { enterprises 5633 }
universiteitVanAmsterdam          OBJECT IDENTIFIER ::= { enterprises 5634 }
daleWLiu                          OBJECT IDENTIFIER ::= { enterprises 5635 }
dignosEDVGmbH                     OBJECT IDENTIFIER ::= { enterprises 5636 }
idnTechnology                     OBJECT IDENTIFIER ::= { enterprises 5637 }
pkElectronics                     OBJECT IDENTIFIER ::= { enterprises 5638 }
deptOfBiologyWesternKYUniversity  OBJECT IDENTIFIER ::= { enterprises 5639 }
lamaLawFirm                       OBJECT IDENTIFIER ::= { enterprises 5640 }
anthem                            OBJECT IDENTIFIER ::= { enterprises 5641 }
microcast                         OBJECT IDENTIFIER ::= { enterprises 5642 }
universityOfArizona               OBJECT IDENTIFIER ::= { enterprises 5643 }
passedge                          OBJECT IDENTIFIER ::= { enterprises 5644 }
bowstreetSoftware                 OBJECT IDENTIFIER ::= { enterprises 5645 }
onyxNetworks                      OBJECT IDENTIFIER ::= { enterprises 5646 }
emperative                        OBJECT IDENTIFIER ::= { enterprises 5647 }
iospanWireless                    OBJECT IDENTIFIER ::= { enterprises 5648 }
webswap                           OBJECT IDENTIFIER ::= { enterprises 5649 }
merckAndCo                        OBJECT IDENTIFIER ::= { enterprises 5650 }
maipuElectricIndustrialCo         OBJECT IDENTIFIER ::= { enterprises 5651 }
kraigSigman                       OBJECT IDENTIFIER ::= { enterprises 5652 }
csp                               OBJECT IDENTIFIER ::= { enterprises 5653 }
andoElectricCorporation           OBJECT IDENTIFIER ::= { enterprises 5654 }
pCube                             OBJECT IDENTIFIER ::= { enterprises 5655 }
monmouthUniversity                OBJECT IDENTIFIER ::= { enterprises 5656 }
universidadDeLaCoruna             OBJECT IDENTIFIER ::= { enterprises 5657 }
isl                               OBJECT IDENTIFIER ::= { enterprises 5658 }
coprosys                          OBJECT IDENTIFIER ::= { enterprises 5659 }
xi                                OBJECT IDENTIFIER ::= { enterprises 5660 }
one2one                           OBJECT IDENTIFIER ::= { enterprises 5661 }
nordicGlobal                      OBJECT IDENTIFIER ::= { enterprises 5662 }
tecnologicaInformatica            OBJECT IDENTIFIER ::= { enterprises 5663 }
monasteryOfTheGloriousAscension   OBJECT IDENTIFIER ::= { enterprises 5664 }
verticalOne                       OBJECT IDENTIFIER ::= { enterprises 5665 }
servevcast                        OBJECT IDENTIFIER ::= { enterprises 5666 }
teldataComputerIndustries         OBJECT IDENTIFIER ::= { enterprises 5667 }
mycroft                           OBJECT IDENTIFIER ::= { enterprises 5668 }
digitalIsland                     OBJECT IDENTIFIER ::= { enterprises 5669 }
redwoodTechnologies               OBJECT IDENTIFIER ::= { enterprises 5670 }
horusITGmbH                       OBJECT IDENTIFIER ::= { enterprises 5671 }
oniSystems                        OBJECT IDENTIFIER ::= { enterprises 5672 }
econvergent                       OBJECT IDENTIFIER ::= { enterprises 5673 }
texcelTechnologyPlc               OBJECT IDENTIFIER ::= { enterprises 5674 }
genosysTechnologyManagement       OBJECT IDENTIFIER ::= { enterprises 5675 }
dataflowAlaska                    OBJECT IDENTIFIER ::= { enterprises 5676 }
clunix                            OBJECT IDENTIFIER ::= { enterprises 5677 }
stalkerSoftware                   OBJECT IDENTIFIER ::= { enterprises 5678 }
eweAndEVE                         OBJECT IDENTIFIER ::= { enterprises 5679 }
windsorGroup                      OBJECT IDENTIFIER ::= { enterprises 5680 }
fruittm                           OBJECT IDENTIFIER ::= { enterprises 5681 }
synergon                          OBJECT IDENTIFIER ::= { enterprises 5682 }
metroOptix                        OBJECT IDENTIFIER ::= { enterprises 5684 }
davidCardimino                    OBJECT IDENTIFIER ::= { enterprises 5685 }
aHComputerCompany                 OBJECT IDENTIFIER ::= { enterprises 5686 }
iconLaboratories                  OBJECT IDENTIFIER ::= { enterprises 5687 }
stratasource                      OBJECT IDENTIFIER ::= { enterprises 5688 }
netAndSysCo                       OBJECT IDENTIFIER ::= { enterprises 5689 }
agriComHoldings                   OBJECT IDENTIFIER ::= { enterprises 5690 }
silverplatterInformation          OBJECT IDENTIFIER ::= { enterprises 5691 }
kilfoilInformationTechnologies    OBJECT IDENTIFIER ::= { enterprises 5692 }
accordionNetworks                 OBJECT IDENTIFIER ::= { enterprises 5693 }
integratedDigitalSolutionsLimited OBJECT IDENTIFIER ::= { enterprises 5694 }
bbqcom                            OBJECT IDENTIFIER ::= { enterprises 5695 }
walterGraphtekGmbH                OBJECT IDENTIFIER ::= { enterprises 5696 }
hansenet                          OBJECT IDENTIFIER ::= { enterprises 5697 }
digitrans                         OBJECT IDENTIFIER ::= { enterprises 5698 }
cornerstoneSolutionsCorporation   OBJECT IDENTIFIER ::= { enterprises 5699 }
universityOfTheWestIndies         OBJECT IDENTIFIER ::= { enterprises 5700 }
mapleNetworks                     OBJECT IDENTIFIER ::= { enterprises 5701 }
touchTechnologyInternational      OBJECT IDENTIFIER ::= { enterprises 5702 }
nvidiaCorporation                 OBJECT IDENTIFIER ::= { enterprises 5703 }
citgoPetroleumCorporation         OBJECT IDENTIFIER ::= { enterprises 5704 }
dta                               OBJECT IDENTIFIER ::= { enterprises 5705 }
lgsGroup                          OBJECT IDENTIFIER ::= { enterprises 5706 }
fiberspaceUnlimited               OBJECT IDENTIFIER ::= { enterprises 5707 }
ctsNetworkServices                OBJECT IDENTIFIER ::= { enterprises 5708 }
edsCFSM                           OBJECT IDENTIFIER ::= { enterprises 5709 }
wellknit                          OBJECT IDENTIFIER ::= { enterprises 5710 }
eccs                              OBJECT IDENTIFIER ::= { enterprises 5711 }
systemIntegrators                 OBJECT IDENTIFIER ::= { enterprises 5712 }
niksun                            OBJECT IDENTIFIER ::= { enterprises 5713 }
inshAllah                         OBJECT IDENTIFIER ::= { enterprises 5714 }
enigmaEnterprises                 OBJECT IDENTIFIER ::= { enterprises 5715 }
webspectrumSoftwarePvt            OBJECT IDENTIFIER ::= { enterprises 5716 }
uucom                             OBJECT IDENTIFIER ::= { enterprises 5717 }
cellit                            OBJECT IDENTIFIER ::= { enterprises 5718 }
pncFinancialServicesGroup         OBJECT IDENTIFIER ::= { enterprises 5719 }
imimicNetworking                  OBJECT IDENTIFIER ::= { enterprises 5720 }
intellops                         OBJECT IDENTIFIER ::= { enterprises 5721 }
altaworksCorporation              OBJECT IDENTIFIER ::= { enterprises 5722 }
samacSoftwareGmbH                 OBJECT IDENTIFIER ::= { enterprises 5723 }
ciceroCommunications              OBJECT IDENTIFIER ::= { enterprises 5724 }
xelCommunications                 OBJECT IDENTIFIER ::= { enterprises 5725 }
lyondellChemicalCompany           OBJECT IDENTIFIER ::= { enterprises 5726 }
smartCardApplicationsPtyLimited   OBJECT IDENTIFIER ::= { enterprises 5727 }
kRingTechnologies                 OBJECT IDENTIFIER ::= { enterprises 5728 }
sqli                              OBJECT IDENTIFIER ::= { enterprises 5729 }
simpsonProfessionalServices       OBJECT IDENTIFIER ::= { enterprises 5730 }
djmEnterprises                    OBJECT IDENTIFIER ::= { enterprises 5731 }
one                               OBJECT IDENTIFIER ::= { enterprises 5732 }
dept3                             OBJECT IDENTIFIER ::= { enterprises 5733 }
fabrica                           OBJECT IDENTIFIER ::= { enterprises 5734 }
ebsnet                            OBJECT IDENTIFIER ::= { enterprises 5735 }
powerConversionProducts           OBJECT IDENTIFIER ::= { enterprises 5736 }
eCommerceEnterprises              OBJECT IDENTIFIER ::= { enterprises 5737 }
vovidaNetworks                    OBJECT IDENTIFIER ::= { enterprises 5738 }
xpeed                             OBJECT IDENTIFIER ::= { enterprises 5739 }
birionicPvt                       OBJECT IDENTIFIER ::= { enterprises 5740 }
a2zcom                            OBJECT IDENTIFIER ::= { enterprises 5741 }
ssc                               OBJECT IDENTIFIER ::= { enterprises 5742 }
gtGroupTelecomServicesCorp        OBJECT IDENTIFIER ::= { enterprises 5743 }
tarsec                            OBJECT IDENTIFIER ::= { enterprises 5744 }
ericssonNikolaTeslaDd             OBJECT IDENTIFIER ::= { enterprises 5745 }
lanexSpZOo                        OBJECT IDENTIFIER ::= { enterprises 5746 }
bluetailAB                        OBJECT IDENTIFIER ::= { enterprises 5747 }
appliedExpertSystems              OBJECT IDENTIFIER ::= { enterprises 5748 }
tgsNOPECGeophysicalCompany        OBJECT IDENTIFIER ::= { enterprises 5749 }
generalMills                      OBJECT IDENTIFIER ::= { enterprises 5750 }
illuminationEnterprises           OBJECT IDENTIFIER ::= { enterprises 5751 }
hypersoft                         OBJECT IDENTIFIER ::= { enterprises 5752 }
universityOfMaribor               OBJECT IDENTIFIER ::= { enterprises 5753 }
clearstreamInternational          OBJECT IDENTIFIER ::= { enterprises 5754 }
its                               OBJECT IDENTIFIER ::= { enterprises 5755 }
supertel                          OBJECT IDENTIFIER ::= { enterprises 5756 }
trilithic                         OBJECT IDENTIFIER ::= { enterprises 5757 }
stinsComan                        OBJECT IDENTIFIER ::= { enterprises 5758 }
bridgescom                        OBJECT IDENTIFIER ::= { enterprises 5759 }
bellAtlanticMobile                OBJECT IDENTIFIER ::= { enterprises 5760 }
intercommunition                  OBJECT IDENTIFIER ::= { enterprises 5761 }
interland                         OBJECT IDENTIFIER ::= { enterprises 5762 }
dbPOWERELECTRONICS                OBJECT IDENTIFIER ::= { enterprises 5763 }
spinGmbH                          OBJECT IDENTIFIER ::= { enterprises 5764 }
gesellschaftFuerOptischeCommunicationsMbH OBJECT IDENTIFIER ::= { enterprises 5765 }
ibmGlobalServices                 OBJECT IDENTIFIER ::= { enterprises 5766 }
quark                             OBJECT IDENTIFIER ::= { enterprises 5767 }
polishJapaneseInstituteOfInformationTechnology OBJECT IDENTIFIER ::= { enterprises 5768 }
healthmagic                       OBJECT IDENTIFIER ::= { enterprises 5769 }
medepasscom                       OBJECT IDENTIFIER ::= { enterprises 5770 }
activeVoiceCorporation            OBJECT IDENTIFIER ::= { enterprises 5771 }
cIt                               OBJECT IDENTIFIER ::= { enterprises 5772 }
equiinet                          OBJECT IDENTIFIER ::= { enterprises 5773 }
beijingTelecableNetworkSystem     OBJECT IDENTIFIER ::= { enterprises 5774 }
advancedTechnologySolutionsInternational OBJECT IDENTIFIER ::= { enterprises 5775 }
expressScripts                    OBJECT IDENTIFIER ::= { enterprises 5776 }
universidadAutonomaDeMadrid       OBJECT IDENTIFIER ::= { enterprises 5778 }
dataGUYS                          OBJECT IDENTIFIER ::= { enterprises 5779 }
pdaVerticalsCorp                  OBJECT IDENTIFIER ::= { enterprises 5780 }
jordanNetworkEngineering          OBJECT IDENTIFIER ::= { enterprises 5781 }
universityOfWisconsinMadison      OBJECT IDENTIFIER ::= { enterprises 5782 }
broadpacCommunications            OBJECT IDENTIFIER ::= { enterprises 5783 }
cogita                            OBJECT IDENTIFIER ::= { enterprises 5784 }
intershopCommunications           OBJECT IDENTIFIER ::= { enterprises 5785 }
mcCoyMarineConsultants            OBJECT IDENTIFIER ::= { enterprises 5786 }
adventistHealth                   OBJECT IDENTIFIER ::= { enterprises 5787 }
softdevCorp                       OBJECT IDENTIFIER ::= { enterprises 5788 }
mobileqcom                        OBJECT IDENTIFIER ::= { enterprises 5789 }
shawnStarr                        OBJECT IDENTIFIER ::= { enterprises 5790 }
compuMentor                       OBJECT IDENTIFIER ::= { enterprises 5791 }
deanGakis                         OBJECT IDENTIFIER ::= { enterprises 5792 }
theEdgeConsultants                OBJECT IDENTIFIER ::= { enterprises 5793 }
obrCTM                            OBJECT IDENTIFIER ::= { enterprises 5794 }
bptTELBANKSA                      OBJECT IDENTIFIER ::= { enterprises 5795 }
stcInformatik                     OBJECT IDENTIFIER ::= { enterprises 5796 }
westernPowerDistribution          OBJECT IDENTIFIER ::= { enterprises 5797 }
viaccessSA                        OBJECT IDENTIFIER ::= { enterprises 5798 }
nyherji                           OBJECT IDENTIFIER ::= { enterprises 5799 }
cruiseControlsPvt                 OBJECT IDENTIFIER ::= { enterprises 5800 }
secondOpinionSoftware             OBJECT IDENTIFIER ::= { enterprises 5801 }
electrolineEquipment              OBJECT IDENTIFIER ::= { enterprises 5802 }
ab                                OBJECT IDENTIFIER ::= { enterprises 5803 }
lanternCommunications             OBJECT IDENTIFIER ::= { enterprises 5804 }
televideo                         OBJECT IDENTIFIER ::= { enterprises 5805 }
skTelecom                         OBJECT IDENTIFIER ::= { enterprises 5806 }
floraVanKesterenTuinadviezen      OBJECT IDENTIFIER ::= { enterprises 5807 }
inrangeTechnologiesCorporation    OBJECT IDENTIFIER ::= { enterprises 5808 }
niedenNsm                         OBJECT IDENTIFIER ::= { enterprises 5809 }
globalCrossing                    OBJECT IDENTIFIER ::= { enterprises 5810 }
theGoldParrotCorporation          OBJECT IDENTIFIER ::= { enterprises 5811 }
coriolisNetworks                  OBJECT IDENTIFIER ::= { enterprises 5812 }
opennms                           OBJECT IDENTIFIER ::= { enterprises 5813 }
generalCommunications             OBJECT IDENTIFIER ::= { enterprises 5814 }
optimaTelecom                     OBJECT IDENTIFIER ::= { enterprises 5815 }
lockstepSystems                   OBJECT IDENTIFIER ::= { enterprises 5816 }
highPrecisionRecordCompanyLimited OBJECT IDENTIFIER ::= { enterprises 5817 }
cherryCyberNet                    OBJECT IDENTIFIER ::= { enterprises 5818 }
xnet                              OBJECT IDENTIFIER ::= { enterprises 5819 }
flyforms                          OBJECT IDENTIFIER ::= { enterprises 5820 }
orangesoft                        OBJECT IDENTIFIER ::= { enterprises 5821 }
reynoldsAndReynoldsPty            OBJECT IDENTIFIER ::= { enterprises 5822 }
nrose                             OBJECT IDENTIFIER ::= { enterprises 5823 }
nikkaiElectronic                  OBJECT IDENTIFIER ::= { enterprises 5824 }
nativeNetworks                    OBJECT IDENTIFIER ::= { enterprises 5825 }
mindCTI                           OBJECT IDENTIFIER ::= { enterprises 5826 }
hermesSoftlab                     OBJECT IDENTIFIER ::= { enterprises 5827 }
spacenetCommunicationAB           OBJECT IDENTIFIER ::= { enterprises 5828 }
amccSwitchingCorp                 OBJECT IDENTIFIER ::= { enterprises 5829 }
xcellenet                         OBJECT IDENTIFIER ::= { enterprises 5830 }
siouxMediaServices                OBJECT IDENTIFIER ::= { enterprises 5831 }
horgannet                         OBJECT IDENTIFIER ::= { enterprises 5832 }
tailynCommunicationCompany        OBJECT IDENTIFIER ::= { enterprises 5833 }
identikey                         OBJECT IDENTIFIER ::= { enterprises 5834 }
newtecCy                          OBJECT IDENTIFIER ::= { enterprises 5835 }
toyoCOMMUNICATIONEQUIPMENTCO      OBJECT IDENTIFIER ::= { enterprises 5836 }
nedcorLimited                     OBJECT IDENTIFIER ::= { enterprises 5837 }
cabletime                         OBJECT IDENTIFIER ::= { enterprises 5838 }
bioplasmaAndaluzaSL               OBJECT IDENTIFIER ::= { enterprises 5839 }
aravoxTechnologies                OBJECT IDENTIFIER ::= { enterprises 5840 }
netfishTechnologies               OBJECT IDENTIFIER ::= { enterprises 5841 }
ciscoSystems                      OBJECT IDENTIFIER ::= { enterprises 5842 }
fiberlogicCommunications          OBJECT IDENTIFIER ::= { enterprises 5843 }
lgSpaceEngineeringCorp            OBJECT IDENTIFIER ::= { enterprises 5844 }
eisacom                           OBJECT IDENTIFIER ::= { enterprises 5845 }
netcentrex                        OBJECT IDENTIFIER ::= { enterprises 5846 }
knowledgeDesign                   OBJECT IDENTIFIER ::= { enterprises 5847 }
rissaSolutionsCorp                OBJECT IDENTIFIER ::= { enterprises 5848 }
signalCOM                         OBJECT IDENTIFIER ::= { enterprises 5849 }
hsLeaderSrl                       OBJECT IDENTIFIER ::= { enterprises 5850 }
ewindowshopcom                    OBJECT IDENTIFIER ::= { enterprises 5851 }
oscarJacobsson                    OBJECT IDENTIFIER ::= { enterprises 5852 }
bellTechnology                    OBJECT IDENTIFIER ::= { enterprises 5853 }
bellNetworkSolutions              OBJECT IDENTIFIER ::= { enterprises 5854 }
deereAndCompany                   OBJECT IDENTIFIER ::= { enterprises 5855 }
vianetTechnologies                OBJECT IDENTIFIER ::= { enterprises 5856 }
virtualworkout                    OBJECT IDENTIFIER ::= { enterprises 5857 }
cycloneCommerce                   OBJECT IDENTIFIER ::= { enterprises 5858 }
efaSoftwareServices               OBJECT IDENTIFIER ::= { enterprises 5859 }
telenet                           OBJECT IDENTIFIER ::= { enterprises 5860 }
mitsubishiHeavyIndustries         OBJECT IDENTIFIER ::= { enterprises 5861 }
ceycoInternetApplications         OBJECT IDENTIFIER ::= { enterprises 5862 }
d                                 OBJECT IDENTIFIER ::= { enterprises 5863 }
reitc                             OBJECT IDENTIFIER ::= { enterprises 5864 }
parallelNetworks                  OBJECT IDENTIFIER ::= { enterprises 5865 }
londonSchoolOfEconomicsComputerSecurityResearchCentre OBJECT IDENTIFIER ::= { enterprises 5866 }
sanJoaquinDeltaCommunityCollegeDistrict OBJECT IDENTIFIER ::= { enterprises 5867 }
cronosResearchCentreSdnBhd        OBJECT IDENTIFIER ::= { enterprises 5868 }
deutschePostEBusiness             OBJECT IDENTIFIER ::= { enterprises 5869 }
biofone                           OBJECT IDENTIFIER ::= { enterprises 5870 }
hyperxs                           OBJECT IDENTIFIER ::= { enterprises 5871 }
tdcSystems                        OBJECT IDENTIFIER ::= { enterprises 5872 }
softwareDynamics                  OBJECT IDENTIFIER ::= { enterprises 5873 }
ocularNetworks                    OBJECT IDENTIFIER ::= { enterprises 5874 }
chinaAdvancedInfoOpticalNetwork   OBJECT IDENTIFIER ::= { enterprises 5875 }
a2bSro                            OBJECT IDENTIFIER ::= { enterprises 5876 }
ruhrUniversitaetBochum            OBJECT IDENTIFIER ::= { enterprises 5877 }
niceGmbH                          OBJECT IDENTIFIER ::= { enterprises 5878 }
hudsonTechnology                  OBJECT IDENTIFIER ::= { enterprises 5879 }
opteway                           OBJECT IDENTIFIER ::= { enterprises 5880 }
arzAllgemeinessRechenzentrumGmbH  OBJECT IDENTIFIER ::= { enterprises 5881 }
inopoly                           OBJECT IDENTIFIER ::= { enterprises 5882 }
zaffire                           OBJECT IDENTIFIER ::= { enterprises 5883 }
universityOfUtah                  OBJECT IDENTIFIER ::= { enterprises 5884 }
microComputerDataSystems          OBJECT IDENTIFIER ::= { enterprises 5885 }
nuspeedInternetSystems            OBJECT IDENTIFIER ::= { enterprises 5886 }
falconnect                        OBJECT IDENTIFIER ::= { enterprises 5887 }
agiliti                           OBJECT IDENTIFIER ::= { enterprises 5888 }
universidadIberoamericanaGC       OBJECT IDENTIFIER ::= { enterprises 5889 }
lantopSystemsLTD                  OBJECT IDENTIFIER ::= { enterprises 5890 }
autototeSystems                   OBJECT IDENTIFIER ::= { enterprises 5891 }
legacyComputerServicesLimited     OBJECT IDENTIFIER ::= { enterprises 5892 }
pinpointCorporation               OBJECT IDENTIFIER ::= { enterprises 5893 }
dreamchal                         OBJECT IDENTIFIER ::= { enterprises 5894 }
atFutAS                           OBJECT IDENTIFIER ::= { enterprises 5895 }
csse                              OBJECT IDENTIFIER ::= { enterprises 5896 }
bpAmocoPLC                        OBJECT IDENTIFIER ::= { enterprises 5897 }
ritlabsSRL                        OBJECT IDENTIFIER ::= { enterprises 5898 }
micromElectronics                 OBJECT IDENTIFIER ::= { enterprises 5899 }
schraderBridgeportInternational   OBJECT IDENTIFIER ::= { enterprises 5900 }
nominuum                          OBJECT IDENTIFIER ::= { enterprises 5901 }
maharajahInfosys                  OBJECT IDENTIFIER ::= { enterprises 5902 }
paceMicroTechnologyPlc            OBJECT IDENTIFIER ::= { enterprises 5903 }
walgreens                         OBJECT IDENTIFIER ::= { enterprises 5904 }
storagenetworks                   OBJECT IDENTIFIER ::= { enterprises 5905 }
travsysBV                         OBJECT IDENTIFIER ::= { enterprises 5906 }
lokasoft                          OBJECT IDENTIFIER ::= { enterprises 5907 }
otelnet                           OBJECT IDENTIFIER ::= { enterprises 5908 }
skybitz                           OBJECT IDENTIFIER ::= { enterprises 5909 }
availant                          OBJECT IDENTIFIER ::= { enterprises 5910 }
cbrook                            OBJECT IDENTIFIER ::= { enterprises 5911 }
yuasaCorporation                  OBJECT IDENTIFIER ::= { enterprises 5912 }
oliverFehr                        OBJECT IDENTIFIER ::= { enterprises 5913 }
balsaSoftware                     OBJECT IDENTIFIER ::= { enterprises 5914 }
trilogicSystems                   OBJECT IDENTIFIER ::= { enterprises 5915 }
iNebulacom                        OBJECT IDENTIFIER ::= { enterprises 5916 }
gigalink                          OBJECT IDENTIFIER ::= { enterprises 5917 }
bbl                               OBJECT IDENTIFIER ::= { enterprises 5918 }
departamentoDeInformaticaDaFacCienciasDaUnivLisboa OBJECT IDENTIFIER ::= { enterprises 5919 }
zurichFinancialServicesGroup      OBJECT IDENTIFIER ::= { enterprises 5920 }
semaGroupAB                       OBJECT IDENTIFIER ::= { enterprises 5921 }
realTimeMonitors                  OBJECT IDENTIFIER ::= { enterprises 5922 }
internet2                         OBJECT IDENTIFIER ::= { enterprises 5923 }
xevoCorp                          OBJECT IDENTIFIER ::= { enterprises 5924 }
interactivePeopleUnpluggedAB      OBJECT IDENTIFIER ::= { enterprises 5925 }
interlink                         OBJECT IDENTIFIER ::= { enterprises 5926 }
nexcommSystems                    OBJECT IDENTIFIER ::= { enterprises 5927 }
zydacron                          OBJECT IDENTIFIER ::= { enterprises 5928 }
amercom                           OBJECT IDENTIFIER ::= { enterprises 5929 }
imagictv                          OBJECT IDENTIFIER ::= { enterprises 5930 }
presideo                          OBJECT IDENTIFIER ::= { enterprises 5931 }
opensystemscom                    OBJECT IDENTIFIER ::= { enterprises 5932 }
softwareServices                  OBJECT IDENTIFIER ::= { enterprises 5933 }
centerForTelecommunicationsStudies OBJECT IDENTIFIER ::= { enterprises 5934 }
academiaSinicaComputingCentre     OBJECT IDENTIFIER ::= { enterprises 5935 }
ahhaaaAB                          OBJECT IDENTIFIER ::= { enterprises 5936 }
hypovereinsbank                   OBJECT IDENTIFIER ::= { enterprises 5937 }
macfarlaneTeleSystems             OBJECT IDENTIFIER ::= { enterprises 5938 }
halcomInformatika                 OBJECT IDENTIFIER ::= { enterprises 5939 }
jbmElectronicsCo                  OBJECT IDENTIFIER ::= { enterprises 5940 }
cosmocom                          OBJECT IDENTIFIER ::= { enterprises 5941 }
thoughtshareCommunications        OBJECT IDENTIFIER ::= { enterprises 5942 }
matchcraft                        OBJECT IDENTIFIER ::= { enterprises 5943 }
nrose2                            OBJECT IDENTIFIER ::= { enterprises 5944 }
atbusinessCommunicationsOyj       OBJECT IDENTIFIER ::= { enterprises 5945 }
multitel                          OBJECT IDENTIFIER ::= { enterprises 5946 }
webforceLLC                       OBJECT IDENTIFIER ::= { enterprises 5947 }
threeNOSystems                    OBJECT IDENTIFIER ::= { enterprises 5948 }
ibm2                              OBJECT IDENTIFIER ::= { enterprises 5949 }
imagineering                      OBJECT IDENTIFIER ::= { enterprises 5950 }
netscaler                         OBJECT IDENTIFIER ::= { enterprises 5951 }
breakawaySolutions                OBJECT IDENTIFIER ::= { enterprises 5952 }
eletel                            OBJECT IDENTIFIER ::= { enterprises 5953 }
aaronTelecommunicationTechnology  OBJECT IDENTIFIER ::= { enterprises 5954 }
ascona                            OBJECT IDENTIFIER ::= { enterprises 5955 }
worldspan                         OBJECT IDENTIFIER ::= { enterprises 5956 }
essematicaSrl                     OBJECT IDENTIFIER ::= { enterprises 5957 }
kcell                             OBJECT IDENTIFIER ::= { enterprises 5958 }
easternCommunicationsCo           OBJECT IDENTIFIER ::= { enterprises 5959 }
cefriel                           OBJECT IDENTIFIER ::= { enterprises 5960 }
powecAS                           OBJECT IDENTIFIER ::= { enterprises 5961 }
davidClunie                       OBJECT IDENTIFIER ::= { enterprises 5962 }
radioscape                        OBJECT IDENTIFIER ::= { enterprises 5963 }
fenestraeBV                       OBJECT IDENTIFIER ::= { enterprises 5964 }
cenosis                           OBJECT IDENTIFIER ::= { enterprises 5965 }
hummingbird                       OBJECT IDENTIFIER ::= { enterprises 5966 }
janeEllenShatz                    OBJECT IDENTIFIER ::= { enterprises 5967 }
vams                              OBJECT IDENTIFIER ::= { enterprises 5968 }
lightspeedSystems                 OBJECT IDENTIFIER ::= { enterprises 5969 }
csiro                             OBJECT IDENTIFIER ::= { enterprises 5970 }
leadTechnologies                  OBJECT IDENTIFIER ::= { enterprises 5971 }
airnetCommunicationsCorporation   OBJECT IDENTIFIER ::= { enterprises 5972 }
rainbowTechnologies               OBJECT IDENTIFIER ::= { enterprises 5973 }
telecomTechnologies               OBJECT IDENTIFIER ::= { enterprises 5974 }
telchemy                          OBJECT IDENTIFIER ::= { enterprises 5975 }
redHillNetworks                   OBJECT IDENTIFIER ::= { enterprises 5976 }
universityOfTexasAtDallas         OBJECT IDENTIFIER ::= { enterprises 5977 }
californiaStateUniversityNorthridge OBJECT IDENTIFIER ::= { enterprises 5978 }
cscare                            OBJECT IDENTIFIER ::= { enterprises 5979 }
cssoftware                        OBJECT IDENTIFIER ::= { enterprises 5980 }
mediaTransferGmbH                 OBJECT IDENTIFIER ::= { enterprises 5981 }
walkerInteractiveSystems          OBJECT IDENTIFIER ::= { enterprises 5982 }
descartesSystemsGroup             OBJECT IDENTIFIER ::= { enterprises 5983 }
cedereCorporation                 OBJECT IDENTIFIER ::= { enterprises 5984 }
biocor                            OBJECT IDENTIFIER ::= { enterprises 5985 }
vpacketCommunications             OBJECT IDENTIFIER ::= { enterprises 5986 }
pacificBroadbandCommunications    OBJECT IDENTIFIER ::= { enterprises 5987 }
esutel                            OBJECT IDENTIFIER ::= { enterprises 5988 }
gocom                             OBJECT IDENTIFIER ::= { enterprises 5989 }
informzaschita                    OBJECT IDENTIFIER ::= { enterprises 5990 }
ntownCommunications               OBJECT IDENTIFIER ::= { enterprises 5991 }
epowerSolutions                   OBJECT IDENTIFIER ::= { enterprises 5992 }
terabeamNetworks                  OBJECT IDENTIFIER ::= { enterprises 5993 }
arcomControlSystems               OBJECT IDENTIFIER ::= { enterprises 5994 }
everypath                         OBJECT IDENTIFIER ::= { enterprises 5995 }
communicationWeaverCo             OBJECT IDENTIFIER ::= { enterprises 5996 }
teamtronicPscrl                   OBJECT IDENTIFIER ::= { enterprises 5997 }
citiDICITCO                       OBJECT IDENTIFIER ::= { enterprises 5998 }
scitelIndustrieberatungsGmbH      OBJECT IDENTIFIER ::= { enterprises 5999 }
cesComputerSolutions              OBJECT IDENTIFIER ::= { enterprises 6000 }
memorialSloanKetteringCancerCenter OBJECT IDENTIFIER ::= { enterprises 6001 }
impresseCorporation               OBJECT IDENTIFIER ::= { enterprises 6002 }
jasmineNetworks                   OBJECT IDENTIFIER ::= { enterprises 6003 }
sysmateCo                         OBJECT IDENTIFIER ::= { enterprises 6004 }
cityOfSydney                      OBJECT IDENTIFIER ::= { enterprises 6005 }
theSchleutkerSites                OBJECT IDENTIFIER ::= { enterprises 6006 }
reduxCommunications               OBJECT IDENTIFIER ::= { enterprises 6007 }
lynxus                            OBJECT IDENTIFIER ::= { enterprises 6008 }
gcsGlobalCommunicationAndServicesGmbH OBJECT IDENTIFIER ::= { enterprises 6009 }
serviceco                         OBJECT IDENTIFIER ::= { enterprises 6010 }
cintaCorporation                  OBJECT IDENTIFIER ::= { enterprises 6011 }
pingpongcom                       OBJECT IDENTIFIER ::= { enterprises 6012 }
tieturi                           OBJECT IDENTIFIER ::= { enterprises 6013 }
nationalLibraryOfMedicine         OBJECT IDENTIFIER ::= { enterprises 6014 }
chicagoBoardOptionsExchange       OBJECT IDENTIFIER ::= { enterprises 6015 }
technauts                         OBJECT IDENTIFIER ::= { enterprises 6016 }
g2xSoftware                       OBJECT IDENTIFIER ::= { enterprises 6017 }
excelMedicalElectronics           OBJECT IDENTIFIER ::= { enterprises 6018 }
simplifiedTelesys                 OBJECT IDENTIFIER ::= { enterprises 6019 }
lutrisTechnologies                OBJECT IDENTIFIER ::= { enterprises 6020 }
arcadianWireless                  OBJECT IDENTIFIER ::= { enterprises 6021 }
dfkiGmbH                          OBJECT IDENTIFIER ::= { enterprises 6022 }
steeleRaymondSolicitors           OBJECT IDENTIFIER ::= { enterprises 6023 }
scannexElectronics                OBJECT IDENTIFIER ::= { enterprises 6024 }
advancedNetworkSolutionsSpA       OBJECT IDENTIFIER ::= { enterprises 6025 }
usArmySTRICOM                     OBJECT IDENTIFIER ::= { enterprises 6026 }
force10Networks                   OBJECT IDENTIFIER ::= { enterprises 6027 }
odsiCoalition                     OBJECT IDENTIFIER ::= { enterprises 6028 }
exactiscom                        OBJECT IDENTIFIER ::= { enterprises 6029 }
flukeElectronics                  OBJECT IDENTIFIER ::= { enterprises 6030 }
computerProblemSolving            OBJECT IDENTIFIER ::= { enterprises 6031 }
stainlessSteelNetworks            OBJECT IDENTIFIER ::= { enterprises 6032 }
eTalkCorporation                  OBJECT IDENTIFIER ::= { enterprises 6033 }
broadjump                         OBJECT IDENTIFIER ::= { enterprises 6034 }
sensisCorporation                 OBJECT IDENTIFIER ::= { enterprises 6035 }
boseCorporation                   OBJECT IDENTIFIER ::= { enterprises 6036 }
edgeNetworksCorp                  OBJECT IDENTIFIER ::= { enterprises 6037 }
netwhistlecom                     OBJECT IDENTIFIER ::= { enterprises 6038 }
resscomComputersAndCommunications OBJECT IDENTIFIER ::= { enterprises 6039 }
universityOfKalmar                OBJECT IDENTIFIER ::= { enterprises 6040 }
kokuaCommunications               OBJECT IDENTIFIER ::= { enterprises 6041 }
southeasternAluminumProducts      OBJECT IDENTIFIER ::= { enterprises 6042 }
astroterraCorporation             OBJECT IDENTIFIER ::= { enterprises 6043 }
poyntz                            OBJECT IDENTIFIER ::= { enterprises 6044 }
synaptiqueInformationAndTechnologie OBJECT IDENTIFIER ::= { enterprises 6045 }
near2Communications               OBJECT IDENTIFIER ::= { enterprises 6046 }
floridaTeachingProfessionNEA      OBJECT IDENTIFIER ::= { enterprises 6047 }
exyst                             OBJECT IDENTIFIER ::= { enterprises 6048 }
hitachiInformationSystems         OBJECT IDENTIFIER ::= { enterprises 6049 }
gamatronicELECTRONICINDUSTRIESLTD OBJECT IDENTIFIER ::= { enterprises 6050 }
ameritrade                        OBJECT IDENTIFIER ::= { enterprises 6051 }
novasonics                        OBJECT IDENTIFIER ::= { enterprises 6052 }
eredyneCorporation                OBJECT IDENTIFIER ::= { enterprises 6053 }
access360                         OBJECT IDENTIFIER ::= { enterprises 6054 }
leesCommunication                 OBJECT IDENTIFIER ::= { enterprises 6055 }
rensselaerPolytechnicInstitute    OBJECT IDENTIFIER ::= { enterprises 6056 }
appnet                            OBJECT IDENTIFIER ::= { enterprises 6057 }
havasInteractive                  OBJECT IDENTIFIER ::= { enterprises 6058 }
adnovumInformatikAG               OBJECT IDENTIFIER ::= { enterprises 6059 }
ispSystemsPty                     OBJECT IDENTIFIER ::= { enterprises 6060 }
netuitive                         OBJECT IDENTIFIER ::= { enterprises 6061 }
tekelecTEMEX                      OBJECT IDENTIFIER ::= { enterprises 6062 }
axentTechnologies3                OBJECT IDENTIFIER ::= { enterprises 6063 }
jkMicrosystems                    OBJECT IDENTIFIER ::= { enterprises 6064 }
zuniversitycom                    OBJECT IDENTIFIER ::= { enterprises 6065 }
occamNetworks                     OBJECT IDENTIFIER ::= { enterprises 6066 }
adapcom                           OBJECT IDENTIFIER ::= { enterprises 6067 }
kcMarching                        OBJECT IDENTIFIER ::= { enterprises 6068 }
blocware                          OBJECT IDENTIFIER ::= { enterprises 6069 }
avivINFOCOMCO                     OBJECT IDENTIFIER ::= { enterprises 6070 }
sigmaInformatique                 OBJECT IDENTIFIER ::= { enterprises 6071 }
planSoftwareGmbH                  OBJECT IDENTIFIER ::= { enterprises 6072 }
businessGlobalSystems             OBJECT IDENTIFIER ::= { enterprises 6073 }
cenosis2                          OBJECT IDENTIFIER ::= { enterprises 6074 }
siemensAG                         OBJECT IDENTIFIER ::= { enterprises 6075 }
trellisoft                        OBJECT IDENTIFIER ::= { enterprises 6076 }
callNetTechnologyServices         OBJECT IDENTIFIER ::= { enterprises 6077 }
cyberintelligentTechnologies      OBJECT IDENTIFIER ::= { enterprises 6078 }
appoconnectcom                    OBJECT IDENTIFIER ::= { enterprises 6079 }
bridgewaveCommunications          OBJECT IDENTIFIER ::= { enterprises 6080 }
nexsi                             OBJECT IDENTIFIER ::= { enterprises 6081 }
ares                              OBJECT IDENTIFIER ::= { enterprises 6082 }
aatr                              OBJECT IDENTIFIER ::= { enterprises 6083 }
prismediaNetworks                 OBJECT IDENTIFIER ::= { enterprises 6084 }
hypergeneAB                       OBJECT IDENTIFIER ::= { enterprises 6085 }
newYorkLifeInsuranceCo            OBJECT IDENTIFIER ::= { enterprises 6086 }
mentat                            OBJECT IDENTIFIER ::= { enterprises 6087 }
opnix                             OBJECT IDENTIFIER ::= { enterprises 6088 }
lastmile                          OBJECT IDENTIFIER ::= { enterprises 6089 }
despatchbox                       OBJECT IDENTIFIER ::= { enterprises 6090 }
epki                              OBJECT IDENTIFIER ::= { enterprises 6091 }
agillionCorporation               OBJECT IDENTIFIER ::= { enterprises 6092 }
tessagAG                          OBJECT IDENTIFIER ::= { enterprises 6093 }
wapcom                            OBJECT IDENTIFIER ::= { enterprises 6094 }
khaledFAHMI                       OBJECT IDENTIFIER ::= { enterprises 6095 }
netsecureSoftware                 OBJECT IDENTIFIER ::= { enterprises 6096 }
stateOfMichigan                   OBJECT IDENTIFIER ::= { enterprises 6097 }
avantgo                           OBJECT IDENTIFIER ::= { enterprises 6098 }
continuumNetworks                 OBJECT IDENTIFIER ::= { enterprises 6099 }
covalentTechnologies              OBJECT IDENTIFIER ::= { enterprises 6100 }
trendMicro                        OBJECT IDENTIFIER ::= { enterprises 6101 }
integratedRESEARCHPTYLTD          OBJECT IDENTIFIER ::= { enterprises 6102 }
alRasheed                         OBJECT IDENTIFIER ::= { enterprises 6103 }
cosmobridgeCo                     OBJECT IDENTIFIER ::= { enterprises 6104 }
centerVladeZaInformatiko          OBJECT IDENTIFIER ::= { enterprises 6105 }
maharajaInfosysLimited            OBJECT IDENTIFIER ::= { enterprises 6106 }
idnTelecom                        OBJECT IDENTIFIER ::= { enterprises 6107 }
insuranceAutoAuctions             OBJECT IDENTIFIER ::= { enterprises 6108 }
adic                              OBJECT IDENTIFIER ::= { enterprises 6109 }
atrica                            OBJECT IDENTIFIER ::= { enterprises 6110 }
worldsportNetworks                OBJECT IDENTIFIER ::= { enterprises 6111 }
xinetronCO                        OBJECT IDENTIFIER ::= { enterprises 6112 }
datekTelecomSA                    OBJECT IDENTIFIER ::= { enterprises 6113 }
prosystSoftwareAG                 OBJECT IDENTIFIER ::= { enterprises 6114 }
openInteractiveLimited            OBJECT IDENTIFIER ::= { enterprises 6115 }
medtegrity                        OBJECT IDENTIFIER ::= { enterprises 6116 }
fiberNetworkEngineering           OBJECT IDENTIFIER ::= { enterprises 6117 }
quintiles                         OBJECT IDENTIFIER ::= { enterprises 6118 }
ipworks                           OBJECT IDENTIFIER ::= { enterprises 6119 }
nxtv                              OBJECT IDENTIFIER ::= { enterprises 6120 }
excite                            OBJECT IDENTIFIER ::= { enterprises 6121 }
moverSpA                          OBJECT IDENTIFIER ::= { enterprises 6122 }
nationalInstituteOfTelecommunications OBJECT IDENTIFIER ::= { enterprises 6123 }
saneSolutions                     OBJECT IDENTIFIER ::= { enterprises 6124 }
acerfiMICRONICS                   OBJECT IDENTIFIER ::= { enterprises 6125 }
epicrealm                         OBJECT IDENTIFIER ::= { enterprises 6126 }
laplinkcom                        OBJECT IDENTIFIER ::= { enterprises 6127 }
wirelessPlanet                    OBJECT IDENTIFIER ::= { enterprises 6128 }
bromaxCommunication               OBJECT IDENTIFIER ::= { enterprises 6129 }
cvi                               OBJECT IDENTIFIER ::= { enterprises 6130 }
starmediaMobile                   OBJECT IDENTIFIER ::= { enterprises 6131 }
lvl7Systems                       OBJECT IDENTIFIER ::= { enterprises 6132 }
deadFishTechnologies              OBJECT IDENTIFIER ::= { enterprises 6133 }
trioniq                           OBJECT IDENTIFIER ::= { enterprises 6134 }
chubuTelecommunicationsCo         OBJECT IDENTIFIER ::= { enterprises 6135 }
idealhostcom                      OBJECT IDENTIFIER ::= { enterprises 6136 }
universityOfCanterbury            OBJECT IDENTIFIER ::= { enterprises 6137 }
trasys                            OBJECT IDENTIFIER ::= { enterprises 6138 }
healthcareSpecialists             OBJECT IDENTIFIER ::= { enterprises 6139 }
enikia                            OBJECT IDENTIFIER ::= { enterprises 6140 }
worldWidePackets                  OBJECT IDENTIFIER ::= { enterprises 6141 }
tf1                               OBJECT IDENTIFIER ::= { enterprises 6142 }
eventlogic                        OBJECT IDENTIFIER ::= { enterprises 6143 }
suntechSpZoo                      OBJECT IDENTIFIER ::= { enterprises 6144 }
cendioSystemsAB                   OBJECT IDENTIFIER ::= { enterprises 6145 }
whirlpoolCorporation              OBJECT IDENTIFIER ::= { enterprises 6146 }
alliegianceTelecom                OBJECT IDENTIFIER ::= { enterprises 6147 }
cidera                            OBJECT IDENTIFIER ::= { enterprises 6148 }
londonSchoolOfEconomics           OBJECT IDENTIFIER ::= { enterprises 6149 }
openNetworksEngineering           OBJECT IDENTIFIER ::= { enterprises 6150 }
copyprintSL                       OBJECT IDENTIFIER ::= { enterprises 6151 }
sendmail                          OBJECT IDENTIFIER ::= { enterprises 6152 }
jolt                              OBJECT IDENTIFIER ::= { enterprises 6153 }
sonerisEngineering                OBJECT IDENTIFIER ::= { enterprises 6154 }
firebit                           OBJECT IDENTIFIER ::= { enterprises 6155 }
ttcTESLATELEKOMUNIKACE            OBJECT IDENTIFIER ::= { enterprises 6156 }
iccriBANCAFEDERALEEUROPEASPA      OBJECT IDENTIFIER ::= { enterprises 6157 }
nagus                             OBJECT IDENTIFIER ::= { enterprises 6158 }
universityOfIowa                  OBJECT IDENTIFIER ::= { enterprises 6159 }
affinityTechnologyGroup           OBJECT IDENTIFIER ::= { enterprises 6160 }
onfiberCommunications             OBJECT IDENTIFIER ::= { enterprises 6161 }
solidDataSystems                  OBJECT IDENTIFIER ::= { enterprises 6162 }
inaraNetworks                     OBJECT IDENTIFIER ::= { enterprises 6163 }
kinvaNetworkSystem                OBJECT IDENTIFIER ::= { enterprises 6164 }
portwell                          OBJECT IDENTIFIER ::= { enterprises 6165 }
interactiveEnterprise             OBJECT IDENTIFIER ::= { enterprises 6166 }
sphinx                            OBJECT IDENTIFIER ::= { enterprises 6167 }
bancoDoBrasilSA                   OBJECT IDENTIFIER ::= { enterprises 6168 }
paloAltoHighSchool                OBJECT IDENTIFIER ::= { enterprises 6169 }
partminer                         OBJECT IDENTIFIER ::= { enterprises 6170 }
kidataAG                          OBJECT IDENTIFIER ::= { enterprises 6171 }
worldwideEntrepreneuricEnterprises OBJECT IDENTIFIER ::= { enterprises 6172 }
fisherAndPaykelIndustriesLimited  OBJECT IDENTIFIER ::= { enterprises 6173 }
fusionx                           OBJECT IDENTIFIER ::= { enterprises 6174 }
pinesOfWoodedge                   OBJECT IDENTIFIER ::= { enterprises 6175 }
vipcom                            OBJECT IDENTIFIER ::= { enterprises 6176 }
blitzInformationTechnologiesBerhad OBJECT IDENTIFIER ::= { enterprises 6177 }
nttAdvancedTechnologyCorporation  OBJECT IDENTIFIER ::= { enterprises 6178 }
rmEDIZIONISRL                     OBJECT IDENTIFIER ::= { enterprises 6179 }
candocom                          OBJECT IDENTIFIER ::= { enterprises 6180 }
creativeLogicCorporation          OBJECT IDENTIFIER ::= { enterprises 6181 }
encoreElectronics                 OBJECT IDENTIFIER ::= { enterprises 6182 }
sharemedia                        OBJECT IDENTIFIER ::= { enterprises 6183 }
mitsuiAndCo                       OBJECT IDENTIFIER ::= { enterprises 6184 }
ghentUniversity                   OBJECT IDENTIFIER ::= { enterprises 6185 }
spaceCyberLink                    OBJECT IDENTIFIER ::= { enterprises 6186 }
dartmouthHitchcockMedicalCenter   OBJECT IDENTIFIER ::= { enterprises 6187 }
universityOfMassachusettsLowell   OBJECT IDENTIFIER ::= { enterprises 6188 }
competenceCenterInformatikGmbH    OBJECT IDENTIFIER ::= { enterprises 6189 }
network365                        OBJECT IDENTIFIER ::= { enterprises 6190 }
plasmon                           OBJECT IDENTIFIER ::= { enterprises 6191 }
environmentalMonitoringSolutions  OBJECT IDENTIFIER ::= { enterprises 6192 }
cplSystems                        OBJECT IDENTIFIER ::= { enterprises 6193 }
netcalibrate                      OBJECT IDENTIFIER ::= { enterprises 6194 }
advancedCommunicationResearch     OBJECT IDENTIFIER ::= { enterprises 6195 }
atlantecEnterpriseSolutionsGmbH   OBJECT IDENTIFIER ::= { enterprises 6196 }
arcordiaSolutions                 OBJECT IDENTIFIER ::= { enterprises 6197 }
easternNazareneCollege            OBJECT IDENTIFIER ::= { enterprises 6198 }
nyherjiHf                         OBJECT IDENTIFIER ::= { enterprises 6199 }
dnpg                              OBJECT IDENTIFIER ::= { enterprises 6200 }
asenti                            OBJECT IDENTIFIER ::= { enterprises 6201 }
nimble                            OBJECT IDENTIFIER ::= { enterprises 6202 }
topspinNetworks                   OBJECT IDENTIFIER ::= { enterprises 6203 }
sibsSociedadeInterbancariaDeServicos OBJECT IDENTIFIER ::= { enterprises 6204 }
lkcTechnology                     OBJECT IDENTIFIER ::= { enterprises 6205 }
ecritical                         OBJECT IDENTIFIER ::= { enterprises 6206 }
thePolishedGroupSA                OBJECT IDENTIFIER ::= { enterprises 6207 }
enterpriseInternetServicesLimited OBJECT IDENTIFIER ::= { enterprises 6208 }
theOpenUniversity                 OBJECT IDENTIFIER ::= { enterprises 6209 }
mayahCommunicationsGmbH           OBJECT IDENTIFIER ::= { enterprises 6210 }
murex                             OBJECT IDENTIFIER ::= { enterprises 6211 }
xmSatelliteRadio                  OBJECT IDENTIFIER ::= { enterprises 6212 }
redlineNetworks                   OBJECT IDENTIFIER ::= { enterprises 6213 }
surefireCommerce                  OBJECT IDENTIFIER ::= { enterprises 6214 }
streaming21                       OBJECT IDENTIFIER ::= { enterprises 6215 }
ciTechnologies                    OBJECT IDENTIFIER ::= { enterprises 6216 }
ngkindsoftltd                     OBJECT IDENTIFIER ::= { enterprises 6217 }
scanCOIN                          OBJECT IDENTIFIER ::= { enterprises 6218 }
iskraSYSENDd                      OBJECT IDENTIFIER ::= { enterprises 6219 }
cyberInternetServices             OBJECT IDENTIFIER ::= { enterprises 6220 }
baeSystems                        OBJECT IDENTIFIER ::= { enterprises 6221 }
stsn                              OBJECT IDENTIFIER ::= { enterprises 6222 }
cdsTechnologies                   OBJECT IDENTIFIER ::= { enterprises 6223 }
roxycom                           OBJECT IDENTIFIER ::= { enterprises 6224 }
broadcastTowers                   OBJECT IDENTIFIER ::= { enterprises 6225 }
barield                           OBJECT IDENTIFIER ::= { enterprises 6226 }
resolveEngineeringPty             OBJECT IDENTIFIER ::= { enterprises 6227 }
engineeringCenterForInformationSecurity OBJECT IDENTIFIER ::= { enterprises 6228 }
tango04ComputingGroup             OBJECT IDENTIFIER ::= { enterprises 6229 }
siteSkunkworks                    OBJECT IDENTIFIER ::= { enterprises 6230 }
fiduciaryAutomation               OBJECT IDENTIFIER ::= { enterprises 6231 }
corinexGlobalCorp                 OBJECT IDENTIFIER ::= { enterprises 6232 }
uunetEMEA                         OBJECT IDENTIFIER ::= { enterprises 6233 }
paulAbrahams                      OBJECT IDENTIFIER ::= { enterprises 6234 }
nawilsoncom                       OBJECT IDENTIFIER ::= { enterprises 6235 }
crayfishCo                        OBJECT IDENTIFIER ::= { enterprises 6236 }
netageSolutionsGmbHNetzwerklosungen OBJECT IDENTIFIER ::= { enterprises 6237 }
queenMaryAndWestfieldCollege      OBJECT IDENTIFIER ::= { enterprises 6238 }
technotrendAG                     OBJECT IDENTIFIER ::= { enterprises 6239 }
bryttan                           OBJECT IDENTIFIER ::= { enterprises 6240 }
calvinCollege                     OBJECT IDENTIFIER ::= { enterprises 6241 }
possmTechnologies                 OBJECT IDENTIFIER ::= { enterprises 6242 }
weberEnterprise                   OBJECT IDENTIFIER ::= { enterprises 6243 }
pdrSAGNPublishing                 OBJECT IDENTIFIER ::= { enterprises 6244 }
circlexLimited                    OBJECT IDENTIFIER ::= { enterprises 6245 }
mythologicalSolutions             OBJECT IDENTIFIER ::= { enterprises 6246 }
efDataCorporation                 OBJECT IDENTIFIER ::= { enterprises 6247 }
atecsDematic                      OBJECT IDENTIFIER ::= { enterprises 6248 }
hclTechnologies                   OBJECT IDENTIFIER ::= { enterprises 6249 }
pepsicoBusinessSolutionsGroup     OBJECT IDENTIFIER ::= { enterprises 6250 }
atogaSystems                      OBJECT IDENTIFIER ::= { enterprises 6251 }
srvlocorg                         OBJECT IDENTIFIER ::= { enterprises 6252 }
ipseal                            OBJECT IDENTIFIER ::= { enterprises 6253 }
timevision                        OBJECT IDENTIFIER ::= { enterprises 6254 }
commerceOnc                       OBJECT IDENTIFIER ::= { enterprises 6255 }
southwestCommunicationsInstitute  OBJECT IDENTIFIER ::= { enterprises 6256 }
disappearing                      OBJECT IDENTIFIER ::= { enterprises 6257 }
iwatsuElectricCo                  OBJECT IDENTIFIER ::= { enterprises 6258 }
sohonetLimited                    OBJECT IDENTIFIER ::= { enterprises 6259 }
makuInformationstechnikGmbH       OBJECT IDENTIFIER ::= { enterprises 6261 }
imcCommunications                 OBJECT IDENTIFIER ::= { enterprises 6262 }
avstarSystems                     OBJECT IDENTIFIER ::= { enterprises 6263 }
opennetworkTechnologies2          OBJECT IDENTIFIER ::= { enterprises 6264 }
gocekcom                          OBJECT IDENTIFIER ::= { enterprises 6265 }
everestECommerce2                 OBJECT IDENTIFIER ::= { enterprises 6266 }
mushtaqSONS                       OBJECT IDENTIFIER ::= { enterprises 6267 }
evistel                           OBJECT IDENTIFIER ::= { enterprises 6268 }
digimation                        OBJECT IDENTIFIER ::= { enterprises 6269 }
iasiaworks                        OBJECT IDENTIFIER ::= { enterprises 6270 }
nsc                               OBJECT IDENTIFIER ::= { enterprises 6271 }
kpnqwestFinland                   OBJECT IDENTIFIER ::= { enterprises 6272 }
weirConsulting                    OBJECT IDENTIFIER ::= { enterprises 6273 }
draelComputerCorporation          OBJECT IDENTIFIER ::= { enterprises 6274 }
hob                               OBJECT IDENTIFIER ::= { enterprises 6275 }
mahindraBritishTelecomLimited     OBJECT IDENTIFIER ::= { enterprises 6276 }
federaci                          OBJECT IDENTIFIER ::= { enterprises 6277 }
invisioncom                       OBJECT IDENTIFIER ::= { enterprises 6278 }
visibleMarkets                    OBJECT IDENTIFIER ::= { enterprises 6279 }
coreon                            OBJECT IDENTIFIER ::= { enterprises 6280 }
jingleCatsMusic                   OBJECT IDENTIFIER ::= { enterprises 6281 }
sdcCommunications                 OBJECT IDENTIFIER ::= { enterprises 6282 }
cityNetTechnology                 OBJECT IDENTIFIER ::= { enterprises 6283 }
wirelessNetworks                  OBJECT IDENTIFIER ::= { enterprises 6284 }
crossportSystems                  OBJECT IDENTIFIER ::= { enterprises 6285 }
oneTechTelecomCo                  OBJECT IDENTIFIER ::= { enterprises 6286 }
nextenso                          OBJECT IDENTIFIER ::= { enterprises 6287 }
euskaltelSA                       OBJECT IDENTIFIER ::= { enterprises 6288 }
adapcom2                          OBJECT IDENTIFIER ::= { enterprises 6289 }
lightsandCommunications           OBJECT IDENTIFIER ::= { enterprises 6290 }
batesCollege                      OBJECT IDENTIFIER ::= { enterprises 6291 }
leadershipTechnologies            OBJECT IDENTIFIER ::= { enterprises 6292 }
kasenna                           OBJECT IDENTIFIER ::= { enterprises 6293 }
activeTelco                       OBJECT IDENTIFIER ::= { enterprises 6294 }
wilhoytIndustries                 OBJECT IDENTIFIER ::= { enterprises 6295 }
dasanCo                           OBJECT IDENTIFIER ::= { enterprises 6296 }
enelit                            OBJECT IDENTIFIER ::= { enterprises 6297 }
mp3com                            OBJECT IDENTIFIER ::= { enterprises 6298 }
sunyCortland                      OBJECT IDENTIFIER ::= { enterprises 6299 }
karlMiller                        OBJECT IDENTIFIER ::= { enterprises 6300 }
packetDynamics                    OBJECT IDENTIFIER ::= { enterprises 6301 }
emersonEnergySystems              OBJECT IDENTIFIER ::= { enterprises 6302 }
cityspace                         OBJECT IDENTIFIER ::= { enterprises 6303 }
fogcity                           OBJECT IDENTIFIER ::= { enterprises 6304 }
flextronicsInternationalSwedenAB  OBJECT IDENTIFIER ::= { enterprises 6305 }
dartware                          OBJECT IDENTIFIER ::= { enterprises 6306 }
ipanemaTechnologies               OBJECT IDENTIFIER ::= { enterprises 6307 }
cholul                            OBJECT IDENTIFIER ::= { enterprises 6308 }
danNielsenConsulting              OBJECT IDENTIFIER ::= { enterprises 6309 }
kaanbaanTechnologies              OBJECT IDENTIFIER ::= { enterprises 6310 }
gomezAdvisors                     OBJECT IDENTIFIER ::= { enterprises 6311 }
pelicanSecurity                   OBJECT IDENTIFIER ::= { enterprises 6312 }
innovacom                         OBJECT IDENTIFIER ::= { enterprises 6313 }
villamontageSystems               OBJECT IDENTIFIER ::= { enterprises 6314 }
comiss                            OBJECT IDENTIFIER ::= { enterprises 6315 }
billFenner                        OBJECT IDENTIFIER ::= { enterprises 6316 }
netfox                            OBJECT IDENTIFIER ::= { enterprises 6317 }
lesswireAG                        OBJECT IDENTIFIER ::= { enterprises 6318 }
calderaSystems                    OBJECT IDENTIFIER ::= { enterprises 6319 }
simonstlcom                       OBJECT IDENTIFIER ::= { enterprises 6320 }
calixNetworks                     OBJECT IDENTIFIER ::= { enterprises 6321 }
entoneTechnologies                OBJECT IDENTIFIER ::= { enterprises 6322 }
edgenetCommunicationCorporation   OBJECT IDENTIFIER ::= { enterprises 6323 }
coolalerts                        OBJECT IDENTIFIER ::= { enterprises 6324 }
harmonixCorporation               OBJECT IDENTIFIER ::= { enterprises 6325 }
longboard                         OBJECT IDENTIFIER ::= { enterprises 6326 }
drewsTC                           OBJECT IDENTIFIER ::= { enterprises 6327 }
wizwiseTechnology                 OBJECT IDENTIFIER ::= { enterprises 6328 }
internetBusinessFactory           OBJECT IDENTIFIER ::= { enterprises 6329 }
microdotComputingServices         OBJECT IDENTIFIER ::= { enterprises 6330 }
optimationNewZealandLimited       OBJECT IDENTIFIER ::= { enterprises 6331 }
fourSeasonsProduce                OBJECT IDENTIFIER ::= { enterprises 6332 }
accordNetworks                    OBJECT IDENTIFIER ::= { enterprises 6333 }
betrusted                         OBJECT IDENTIFIER ::= { enterprises 6334 }
adroitControls                    OBJECT IDENTIFIER ::= { enterprises 6335 }
digitalFountain                   OBJECT IDENTIFIER ::= { enterprises 6336 }
crytaliz                          OBJECT IDENTIFIER ::= { enterprises 6337 }
sportshuddlecom                   OBJECT IDENTIFIER ::= { enterprises 6338 }
legendDigitalChina                OBJECT IDENTIFIER ::= { enterprises 6339 }
ottoKind                          OBJECT IDENTIFIER ::= { enterprises 6340 }
harvardUniversity                 OBJECT IDENTIFIER ::= { enterprises 6341 }
hyperchip                         OBJECT IDENTIFIER ::= { enterprises 6342 }
ymcaEngland                       OBJECT IDENTIFIER ::= { enterprises 6343 }
hunterTechnology                  OBJECT IDENTIFIER ::= { enterprises 6344 }
compuprintSPA                     OBJECT IDENTIFIER ::= { enterprises 6345 }
dimat                             OBJECT IDENTIFIER ::= { enterprises 6346 }
sierraMonitorCorporation          OBJECT IDENTIFIER ::= { enterprises 6347 }
liquidDigitalInformationSystems   OBJECT IDENTIFIER ::= { enterprises 6348 }
treeblossomTechnologies           OBJECT IDENTIFIER ::= { enterprises 6349 }
blueCrossBlueShieldOfMichigan     OBJECT IDENTIFIER ::= { enterprises 6350 }
shawnSystems                      OBJECT IDENTIFIER ::= { enterprises 6351 }
catenaNetworks                    OBJECT IDENTIFIER ::= { enterprises 6352 }
avistoSA                          OBJECT IDENTIFIER ::= { enterprises 6353 }
telwaysCommunicationCo            OBJECT IDENTIFIER ::= { enterprises 6354 }
sipherInternetTachnology          OBJECT IDENTIFIER ::= { enterprises 6355 }
innovativeSoftwareAG              OBJECT IDENTIFIER ::= { enterprises 6356 }
b2Systems                         OBJECT IDENTIFIER ::= { enterprises 6357 }
unimark                           OBJECT IDENTIFIER ::= { enterprises 6358 }
cyveillance                       OBJECT IDENTIFIER ::= { enterprises 6359 }
livevaultCorporation              OBJECT IDENTIFIER ::= { enterprises 6360 }
siemensBuildingTechnologies       OBJECT IDENTIFIER ::= { enterprises 6361 }
baumannTechnologie                OBJECT IDENTIFIER ::= { enterprises 6362 }
cybersolutionsGmbH                OBJECT IDENTIFIER ::= { enterprises 6363 }
andreaInformatique                OBJECT IDENTIFIER ::= { enterprises 6364 }
novamediaSistemasSL               OBJECT IDENTIFIER ::= { enterprises 6365 }
koreaLINK                         OBJECT IDENTIFIER ::= { enterprises 6366 }
linkabitATitanSystemsCompany      OBJECT IDENTIFIER ::= { enterprises 6367 }
schmidTelecomAG                   OBJECT IDENTIFIER ::= { enterprises 6368 }
lexiComp                          OBJECT IDENTIFIER ::= { enterprises 6369 }
firstUSABank                      OBJECT IDENTIFIER ::= { enterprises 6370 }
minervaNetworks                   OBJECT IDENTIFIER ::= { enterprises 6371 }
kresaRanch                        OBJECT IDENTIFIER ::= { enterprises 6372 }
dl                                OBJECT IDENTIFIER ::= { enterprises 6373 }
ceci                              OBJECT IDENTIFIER ::= { enterprises 6374 }
chinaENGINEERINGCONSULTANTS       OBJECT IDENTIFIER ::= { enterprises 6375 }
pdvsa                             OBJECT IDENTIFIER ::= { enterprises 6376 }
openpages                         OBJECT IDENTIFIER ::= { enterprises 6377 }
lanit                             OBJECT IDENTIFIER ::= { enterprises 6378 }
servgateTechnologiesCanada        OBJECT IDENTIFIER ::= { enterprises 6379 }
isdnet                            OBJECT IDENTIFIER ::= { enterprises 6380 }
burstcom                          OBJECT IDENTIFIER ::= { enterprises 6381 }
sagaSoftware                      OBJECT IDENTIFIER ::= { enterprises 6382 }
oc                                OBJECT IDENTIFIER ::= { enterprises 6383 }
vAndsMultimediaSA                 OBJECT IDENTIFIER ::= { enterprises 6384 }
pfizer                            OBJECT IDENTIFIER ::= { enterprises 6385 }
saturnTechnologies                OBJECT IDENTIFIER ::= { enterprises 6386 }
bigBandNetworks                   OBJECT IDENTIFIER ::= { enterprises 6387 }
telerelay                         OBJECT IDENTIFIER ::= { enterprises 6388 }
comDEVInternational               OBJECT IDENTIFIER ::= { enterprises 6389 }
dbcorpInformationSystems          OBJECT IDENTIFIER ::= { enterprises 6390 }
xtremesoft                        OBJECT IDENTIFIER ::= { enterprises 6391 }
chiaroNetworks                    OBJECT IDENTIFIER ::= { enterprises 6392 }
haliplexPty                       OBJECT IDENTIFIER ::= { enterprises 6393 }
skeltonConsultingGmbH             OBJECT IDENTIFIER ::= { enterprises 6394 }
prosaldoSoftwareBV                OBJECT IDENTIFIER ::= { enterprises 6395 }
absoluteWebsiteSolutions          OBJECT IDENTIFIER ::= { enterprises 6396 }
naynaNetworks                     OBJECT IDENTIFIER ::= { enterprises 6397 }
lindnerAndPelcConsultGmbH         OBJECT IDENTIFIER ::= { enterprises 6398 }
edrichIntegration                 OBJECT IDENTIFIER ::= { enterprises 6399 }
millenuxGmbH                      OBJECT IDENTIFIER ::= { enterprises 6400 }
jtiOFGEORGIA                      OBJECT IDENTIFIER ::= { enterprises 6401 }
optelGesFurLasertechnikUndElektronikMbH OBJECT IDENTIFIER ::= { enterprises 6402 }
universidadBlasPascal             OBJECT IDENTIFIER ::= { enterprises 6403 }
rftsSA                            OBJECT IDENTIFIER ::= { enterprises 6404 }
activAustralia                    OBJECT IDENTIFIER ::= { enterprises 6405 }
neomar                            OBJECT IDENTIFIER ::= { enterprises 6406 }
bitServicesGmbH                   OBJECT IDENTIFIER ::= { enterprises 6407 }
mikomGmbH                         OBJECT IDENTIFIER ::= { enterprises 6408 }
mondialAssistanceLimited          OBJECT IDENTIFIER ::= { enterprises 6409 }
zoneworx                          OBJECT IDENTIFIER ::= { enterprises 6410 }
quantumCorpSnapDivision           OBJECT IDENTIFIER ::= { enterprises 6411 }
hiddenmindTechnology              OBJECT IDENTIFIER ::= { enterprises 6412 }
isAssociates                      OBJECT IDENTIFIER ::= { enterprises 6413 }
embryRiddleUniversity             OBJECT IDENTIFIER ::= { enterprises 6414 }
caspianNetworks                   OBJECT IDENTIFIER ::= { enterprises 6415 }
solutionzPty                      OBJECT IDENTIFIER ::= { enterprises 6416 }
victorianAutomobileChamberOfCommerce OBJECT IDENTIFIER ::= { enterprises 6417 }
theTemplarCorporation             OBJECT IDENTIFIER ::= { enterprises 6418 }
chyronCorporation                 OBJECT IDENTIFIER ::= { enterprises 6419 }
inMX                              OBJECT IDENTIFIER ::= { enterprises 6420 }
hMCustomsAndExcise                OBJECT IDENTIFIER ::= { enterprises 6421 }
bt                                OBJECT IDENTIFIER ::= { enterprises 6422 }
objectspace                       OBJECT IDENTIFIER ::= { enterprises 6423 }
viawestInternetServices           OBJECT IDENTIFIER ::= { enterprises 6424 }
branchSystems                     OBJECT IDENTIFIER ::= { enterprises 6425 }
eApplianceCorporation             OBJECT IDENTIFIER ::= { enterprises 6426 }
locusDialogue                     OBJECT IDENTIFIER ::= { enterprises 6427 }
tOnlineInternationalAG            OBJECT IDENTIFIER ::= { enterprises 6428 }
alto                              OBJECT IDENTIFIER ::= { enterprises 6429 }
ericssonConsultingGmbH            OBJECT IDENTIFIER ::= { enterprises 6430 }
broadsoft                         OBJECT IDENTIFIER ::= { enterprises 6431 }
orblynx                           OBJECT IDENTIFIER ::= { enterprises 6432 }
excelnet                          OBJECT IDENTIFIER ::= { enterprises 6433 }
webmd                             OBJECT IDENTIFIER ::= { enterprises 6434 }
holistix                          OBJECT IDENTIFIER ::= { enterprises 6435 }
wapmeSystemsAG                    OBJECT IDENTIFIER ::= { enterprises 6436 }
kathreinWerkeKG                   OBJECT IDENTIFIER ::= { enterprises 6437 }
mknetADVIES                       OBJECT IDENTIFIER ::= { enterprises 6438 }
nextretSl                         OBJECT IDENTIFIER ::= { enterprises 6439 }
tradecast                         OBJECT IDENTIFIER ::= { enterprises 6440 }
i2Technologies                    OBJECT IDENTIFIER ::= { enterprises 6441 }
twctDbaDaughtersAndDad            OBJECT IDENTIFIER ::= { enterprises 6442 }
outOfOurMinds                     OBJECT IDENTIFIER ::= { enterprises 6443 }
gearheadGroup                     OBJECT IDENTIFIER ::= { enterprises 6444 }
sportsplanet2000                  OBJECT IDENTIFIER ::= { enterprises 6445 }
gatonTechnologiesLTD              OBJECT IDENTIFIER ::= { enterprises 6446 }
synaxiaNetworks                   OBJECT IDENTIFIER ::= { enterprises 6447 }
digivisionTech                    OBJECT IDENTIFIER ::= { enterprises 6448 }
comodoTechnologyDevelopment       OBJECT IDENTIFIER ::= { enterprises 6449 }
idsecLimited                      OBJECT IDENTIFIER ::= { enterprises 6450 }
mysticalCreations                 OBJECT IDENTIFIER ::= { enterprises 6451 }
advancedNetworkSolutions          OBJECT IDENTIFIER ::= { enterprises 6452 }
coreCOMMUNICATIONSCO              OBJECT IDENTIFIER ::= { enterprises 6453 }
postelServices                    OBJECT IDENTIFIER ::= { enterprises 6454 }
technologyThesaurusCorp           OBJECT IDENTIFIER ::= { enterprises 6455 }
netdefenceCoLimited               OBJECT IDENTIFIER ::= { enterprises 6456 }
eurekaSoft                        OBJECT IDENTIFIER ::= { enterprises 6457 }
gprSistemas                       OBJECT IDENTIFIER ::= { enterprises 6458 }
linfieldCollege                   OBJECT IDENTIFIER ::= { enterprises 6459 }
uclick                            OBJECT IDENTIFIER ::= { enterprises 6460 }
centerForInternetResearch         OBJECT IDENTIFIER ::= { enterprises 6461 }
freiheitcom                       OBJECT IDENTIFIER ::= { enterprises 6462 }
vocaldata                         OBJECT IDENTIFIER ::= { enterprises 6463 }
stevensInstituteOfTechnologyOIT   OBJECT IDENTIFIER ::= { enterprises 6464 }
cacheon                           OBJECT IDENTIFIER ::= { enterprises 6465 }
theDevilYouSay                    OBJECT IDENTIFIER ::= { enterprises 6466 }
landOfLinking                     OBJECT IDENTIFIER ::= { enterprises 6467 }
patentOff                         OBJECT IDENTIFIER ::= { enterprises 6468 }
karmaKahn                         OBJECT IDENTIFIER ::= { enterprises 6469 }
we                                OBJECT IDENTIFIER ::= { enterprises 6470 }
conTemporaries                    OBJECT IDENTIFIER ::= { enterprises 6471 }
antiballistic                     OBJECT IDENTIFIER ::= { enterprises 6472 }
hallsOfIvy                        OBJECT IDENTIFIER ::= { enterprises 6473 }
wiffenpoof                        OBJECT IDENTIFIER ::= { enterprises 6474 }
homeIsTheHunter                   OBJECT IDENTIFIER ::= { enterprises 6475 }
theCraftOfElves                   OBJECT IDENTIFIER ::= { enterprises 6476 }
iWasMisinformed                   OBJECT IDENTIFIER ::= { enterprises 6477 }
shotToShingles                    OBJECT IDENTIFIER ::= { enterprises 6478 }
rightHandTwist                    OBJECT IDENTIFIER ::= { enterprises 6479 }
solomonTechCorp                   OBJECT IDENTIFIER ::= { enterprises 6480 }
magistral                         OBJECT IDENTIFIER ::= { enterprises 6481 }
icsynergy                         OBJECT IDENTIFIER ::= { enterprises 6482 }
captusNetworks                    OBJECT IDENTIFIER ::= { enterprises 6483 }
campusCrusadeForChrist            OBJECT IDENTIFIER ::= { enterprises 6484 }
spatialTechnologies               OBJECT IDENTIFIER ::= { enterprises 6485 }
alcatel                           OBJECT IDENTIFIER ::= { enterprises 6486 }
yousync                           OBJECT IDENTIFIER ::= { enterprises 6487 }
talentstormEnterprises            OBJECT IDENTIFIER ::= { enterprises 6488 }
siemensCerberus                   OBJECT IDENTIFIER ::= { enterprises 6489 }
detemobilDeutscheTelekomMobilNetGmbH OBJECT IDENTIFIER ::= { enterprises 6490 }
cytekMediaSystems                 OBJECT IDENTIFIER ::= { enterprises 6491 }
phyve                             OBJECT IDENTIFIER ::= { enterprises 6492 }
comtrust                          OBJECT IDENTIFIER ::= { enterprises 6493 }
kraftUndPartnerGmbH               OBJECT IDENTIFIER ::= { enterprises 6494 }
seedragonSoftware                 OBJECT IDENTIFIER ::= { enterprises 6495 }
cottonsCarSuperstore              OBJECT IDENTIFIER ::= { enterprises 6496 }
neteyeSolutions                   OBJECT IDENTIFIER ::= { enterprises 6497 }
maintenanceOne                    OBJECT IDENTIFIER ::= { enterprises 6498 }
ekitcomPty                        OBJECT IDENTIFIER ::= { enterprises 6499 }
vaLinuxSystems                    OBJECT IDENTIFIER ::= { enterprises 6500 }
macro4                            OBJECT IDENTIFIER ::= { enterprises 6501 }
refat                             OBJECT IDENTIFIER ::= { enterprises 6502 }
netgem                            OBJECT IDENTIFIER ::= { enterprises 6503 }
naviniNetworks                    OBJECT IDENTIFIER ::= { enterprises 6504 }
targusinfo                        OBJECT IDENTIFIER ::= { enterprises 6505 }
livewireCommunications            OBJECT IDENTIFIER ::= { enterprises 6506 }
optimightCommunications           OBJECT IDENTIFIER ::= { enterprises 6507 }
shanghaiDigiVisionTechnologyCo    OBJECT IDENTIFIER ::= { enterprises 6508 }
antrimStudiosAndSoftwareCellar    OBJECT IDENTIFIER ::= { enterprises 6509 }
pioneerCorporation                OBJECT IDENTIFIER ::= { enterprises 6510 }
telcomTechnology                  OBJECT IDENTIFIER ::= { enterprises 6511 }
famtekProfessionalServices        OBJECT IDENTIFIER ::= { enterprises 6512 }
whaleCommunications               OBJECT IDENTIFIER ::= { enterprises 6513 }
innovativeSystems                 OBJECT IDENTIFIER ::= { enterprises 6514 }
zvolveSystems                     OBJECT IDENTIFIER ::= { enterprises 6515 }
comprehensiveTestBanTreatyOrganization OBJECT IDENTIFIER ::= { enterprises 6516 }
flowserver                        OBJECT IDENTIFIER ::= { enterprises 6517 }
systemsSolutionsOfTheSouthernTier OBJECT IDENTIFIER ::= { enterprises 6518 }
sabre                             OBJECT IDENTIFIER ::= { enterprises 6519 }
chaparralNetworkStorage           OBJECT IDENTIFIER ::= { enterprises 6520 }
chainlinkTechnologies             OBJECT IDENTIFIER ::= { enterprises 6521 }
cvCryptovisionGmbH                OBJECT IDENTIFIER ::= { enterprises 6522 }
bilbokoTrading                    OBJECT IDENTIFIER ::= { enterprises 6523 }
greenbytesGmbH                    OBJECT IDENTIFIER ::= { enterprises 6524 }
jasmineNetworks2                  OBJECT IDENTIFIER ::= { enterprises 6525 }
windwardConsultingGroup           OBJECT IDENTIFIER ::= { enterprises 6526 }
pantheraNetworks                  OBJECT IDENTIFIER ::= { enterprises 6527 }
sourceOne                         OBJECT IDENTIFIER ::= { enterprises 6528 }
bundesamtFurSicherheitInDerInformationstechnik OBJECT IDENTIFIER ::= { enterprises 6529 }
nSpolSRo                          OBJECT IDENTIFIER ::= { enterprises 6530 }
teamworkConsulting                OBJECT IDENTIFIER ::= { enterprises 6531 }
niobraraRAndDCorp                 OBJECT IDENTIFIER ::= { enterprises 6532 }
facetimeCommunications            OBJECT IDENTIFIER ::= { enterprises 6533 }
hp                                OBJECT IDENTIFIER ::= { enterprises 6534 }
tecore                            OBJECT IDENTIFIER ::= { enterprises 6535 }
netforensicscom                   OBJECT IDENTIFIER ::= { enterprises 6536 }
brownUniversity                   OBJECT IDENTIFIER ::= { enterprises 6537 }
winfordEngineering                OBJECT IDENTIFIER ::= { enterprises 6538 }
kenetec                           OBJECT IDENTIFIER ::= { enterprises 6539 }
alamoPersonalComputers            OBJECT IDENTIFIER ::= { enterprises 6540 }
transindigo                       OBJECT IDENTIFIER ::= { enterprises 6541 }
slamdunkNetworks                  OBJECT IDENTIFIER ::= { enterprises 6542 }
ambell                            OBJECT IDENTIFIER ::= { enterprises 6543 }
fivesightTechnologies             OBJECT IDENTIFIER ::= { enterprises 6544 }
thinkIT                           OBJECT IDENTIFIER ::= { enterprises 6545 }
itouchuTECHNOSCIENCECorporation   OBJECT IDENTIFIER ::= { enterprises 6546 }
networkManagementSolutions2       OBJECT IDENTIFIER ::= { enterprises 6547 }
wavelengthDigitalLimited          OBJECT IDENTIFIER ::= { enterprises 6548 }
adaptiveBroadbandCorporation      OBJECT IDENTIFIER ::= { enterprises 6549 }
webliconTechnologiesAG            OBJECT IDENTIFIER ::= { enterprises 6550 }
hotlineCommunications             OBJECT IDENTIFIER ::= { enterprises 6551 }
virbusAG                          OBJECT IDENTIFIER ::= { enterprises 6552 }
ghakoFISHERIESCOMPANYLIMITED      OBJECT IDENTIFIER ::= { enterprises 6553 }
optimaTechnologies                OBJECT IDENTIFIER ::= { enterprises 6554 }
datafoundrynet                    OBJECT IDENTIFIER ::= { enterprises 6555 }
sigmaNetworks                     OBJECT IDENTIFIER ::= { enterprises 6556 }
dotrocket                         OBJECT IDENTIFIER ::= { enterprises 6557 }
securityTechnologies              OBJECT IDENTIFIER ::= { enterprises 6558 }
ushaCommunicationsTechnology      OBJECT IDENTIFIER ::= { enterprises 6559 }
telenergyHGmbH                    OBJECT IDENTIFIER ::= { enterprises 6560 }
pskAG                             OBJECT IDENTIFIER ::= { enterprises 6561 }
nexland                           OBJECT IDENTIFIER ::= { enterprises 6562 }
timebridgeTechnologies            OBJECT IDENTIFIER ::= { enterprises 6563 }
gradientSolutions                 OBJECT IDENTIFIER ::= { enterprises 6564 }
johnsHopkinsInstitutions          OBJECT IDENTIFIER ::= { enterprises 6565 }
metropolitanLifeInsurance         OBJECT IDENTIFIER ::= { enterprises 6566 }
klimkeIndustryConsulting          OBJECT IDENTIFIER ::= { enterprises 6567 }
comtechEFDataCorp                 OBJECT IDENTIFIER ::= { enterprises 6568 }
inventecCORPORATION               OBJECT IDENTIFIER ::= { enterprises 6569 }
acomzNETWORKSCORP                 OBJECT IDENTIFIER ::= { enterprises 6570 }
fusionInTechCo                    OBJECT IDENTIFIER ::= { enterprises 6571 }
netlinksCO                        OBJECT IDENTIFIER ::= { enterprises 6572 }
pervigil                          OBJECT IDENTIFIER ::= { enterprises 6573 }
synology                          OBJECT IDENTIFIER ::= { enterprises 6574 }
marriottInternational             OBJECT IDENTIFIER ::= { enterprises 6575 }
privada                           OBJECT IDENTIFIER ::= { enterprises 6576 }
induraCorporation                 OBJECT IDENTIFIER ::= { enterprises 6577 }
redwaveNetworks                   OBJECT IDENTIFIER ::= { enterprises 6578 }
maruNetworks                      OBJECT IDENTIFIER ::= { enterprises 6579 }
ossSystems                        OBJECT IDENTIFIER ::= { enterprises 6580 }
exercitoBrasileiro                OBJECT IDENTIFIER ::= { enterprises 6581 }
sigmaServicesSenegal              OBJECT IDENTIFIER ::= { enterprises 6582 }
barone                            OBJECT IDENTIFIER ::= { enterprises 6583 }
bundesrechenzentrumGmbH           OBJECT IDENTIFIER ::= { enterprises 6584 }
wPhone                            OBJECT IDENTIFIER ::= { enterprises 6585 }
geoworks                          OBJECT IDENTIFIER ::= { enterprises 6586 }
airvana                           OBJECT IDENTIFIER ::= { enterprises 6587 }
tietoenator                       OBJECT IDENTIFIER ::= { enterprises 6588 }
--                                OBJECT IDENTIFIER ::= { enterprises 6589 }
keipherSolutions                  OBJECT IDENTIFIER ::= { enterprises 6590 }
haansoft                          OBJECT IDENTIFIER ::= { enterprises 6591 }
darinVisionCo                     OBJECT IDENTIFIER ::= { enterprises 6592 }
neoconsulting                     OBJECT IDENTIFIER ::= { enterprises 6593 }
shijinAndCo                       OBJECT IDENTIFIER ::= { enterprises 6594 }
saMartcom                         OBJECT IDENTIFIER ::= { enterprises 6595 }
julieJulie                        OBJECT IDENTIFIER ::= { enterprises 6596 }
messagehero                       OBJECT IDENTIFIER ::= { enterprises 6597 }
cybertronNetworkSolutions         OBJECT IDENTIFIER ::= { enterprises 6598 }
silverBowCo                       OBJECT IDENTIFIER ::= { enterprises 6599 }
internationalCharitiesDepOfTaiheTravelAgency OBJECT IDENTIFIER ::= { enterprises 6600 }
ipDynamics                        OBJECT IDENTIFIER ::= { enterprises 6601 }
sunriseTelecom                    OBJECT IDENTIFIER ::= { enterprises 6602 }
vitesseSemiconductors             OBJECT IDENTIFIER ::= { enterprises 6603 }
toskyManagementConsultingColtd    OBJECT IDENTIFIER ::= { enterprises 6604 }
euroclearOperationsCentre         OBJECT IDENTIFIER ::= { enterprises 6605 }
platypusTechnology                OBJECT IDENTIFIER ::= { enterprises 6606 }
radiantNetworksPlc                OBJECT IDENTIFIER ::= { enterprises 6607 }
circulab                          OBJECT IDENTIFIER ::= { enterprises 6608 }
westernNewEnglandCollege          OBJECT IDENTIFIER ::= { enterprises 6609 }
adityaSystems                     OBJECT IDENTIFIER ::= { enterprises 6610 }
sigmaSERVICESSENEGAL              OBJECT IDENTIFIER ::= { enterprises 6611 }
juniperFinancialCorp              OBJECT IDENTIFIER ::= { enterprises 6612 }
millimetrixBroadbandNetworks      OBJECT IDENTIFIER ::= { enterprises 6613 }
telecomTechnologies2              OBJECT IDENTIFIER ::= { enterprises 6614 }
clairvoyantSoftware               OBJECT IDENTIFIER ::= { enterprises 6615 }
lexica                            OBJECT IDENTIFIER ::= { enterprises 6616 }
microstrategy                     OBJECT IDENTIFIER ::= { enterprises 6617 }
quintumTechnologies               OBJECT IDENTIFIER ::= { enterprises 6618 }
droplet                           OBJECT IDENTIFIER ::= { enterprises 6619 }
globalTelemannSystem              OBJECT IDENTIFIER ::= { enterprises 6620 }
departmentOfForeignAffairsAndTrade OBJECT IDENTIFIER ::= { enterprises 6621 }
secondomillennio                  OBJECT IDENTIFIER ::= { enterprises 6622 }
servizi2000                       OBJECT IDENTIFIER ::= { enterprises 6623 }
sauroProsperi                     OBJECT IDENTIFIER ::= { enterprises 6624 }
pvt                               OBJECT IDENTIFIER ::= { enterprises 6625 }
tekotelecomSpA                    OBJECT IDENTIFIER ::= { enterprises 6626 }
telematicaInternationalBV         OBJECT IDENTIFIER ::= { enterprises 6627 }
juaben                            OBJECT IDENTIFIER ::= { enterprises 6628 }
ulticom                           OBJECT IDENTIFIER ::= { enterprises 6629 }
accuris                           OBJECT IDENTIFIER ::= { enterprises 6630 }
bowlingGreenStateUniversity       OBJECT IDENTIFIER ::= { enterprises 6631 }
dstControls                       OBJECT IDENTIFIER ::= { enterprises 6632 }
personalGenie                     OBJECT IDENTIFIER ::= { enterprises 6633 }
uunet                             OBJECT IDENTIFIER ::= { enterprises 6634 }
cenusTechnologies                 OBJECT IDENTIFIER ::= { enterprises 6635 }
indianaDistrictLCMS               OBJECT IDENTIFIER ::= { enterprises 6636 }
rainbowComputerWarehouse          OBJECT IDENTIFIER ::= { enterprises 6637 }
threeWare                         OBJECT IDENTIFIER ::= { enterprises 6638 }
hhl                               OBJECT IDENTIFIER ::= { enterprises 6639 }
gmvNetwork                        OBJECT IDENTIFIER ::= { enterprises 6640 }
netcoSystems                      OBJECT IDENTIFIER ::= { enterprises 6641 }
scommtech                         OBJECT IDENTIFIER ::= { enterprises 6642 }
iprSystemsPty                     OBJECT IDENTIFIER ::= { enterprises 6643 }
ozauthorsPty                      OBJECT IDENTIFIER ::= { enterprises 6644 }
gforceSystems                     OBJECT IDENTIFIER ::= { enterprises 6645 }
chevron                           OBJECT IDENTIFIER ::= { enterprises 6646 }
planet                            OBJECT IDENTIFIER ::= { enterprises 6647 }
intramon                          OBJECT IDENTIFIER ::= { enterprises 6648 }
newgridTechnology                 OBJECT IDENTIFIER ::= { enterprises 6649 }
theDistributionSystemsResearchInstitute OBJECT IDENTIFIER ::= { enterprises 6650 }
firebone                          OBJECT IDENTIFIER ::= { enterprises 6651 }
idKarta                           OBJECT IDENTIFIER ::= { enterprises 6652 }
tyanComputerCorporation           OBJECT IDENTIFIER ::= { enterprises 6653 }
chicTechnologyCorp                OBJECT IDENTIFIER ::= { enterprises 6654 }
agenetics                         OBJECT IDENTIFIER ::= { enterprises 6655 }
cauris                            OBJECT IDENTIFIER ::= { enterprises 6656 }
courionCorporation                OBJECT IDENTIFIER ::= { enterprises 6657 }
koshy                             OBJECT IDENTIFIER ::= { enterprises 6658 }
alisa                             OBJECT IDENTIFIER ::= { enterprises 6659 }
keraladotcom                      OBJECT IDENTIFIER ::= { enterprises 6660 }
spikeBroadbandSystems             OBJECT IDENTIFIER ::= { enterprises 6661 }
sesaAG                            OBJECT IDENTIFIER ::= { enterprises 6662 }
janevaInteractive                 OBJECT IDENTIFIER ::= { enterprises 6663 }
precidiaTechnologies              OBJECT IDENTIFIER ::= { enterprises 6664 }
atreusSystemsCorp                 OBJECT IDENTIFIER ::= { enterprises 6665 }
innovaphoneGmbH                   OBJECT IDENTIFIER ::= { enterprises 6666 }
mediumrare                        OBJECT IDENTIFIER ::= { enterprises 6667 }
toBeOrNot                         OBJECT IDENTIFIER ::= { enterprises 6668 }
videotronLtee                     OBJECT IDENTIFIER ::= { enterprises 6669 }
intelligentInstrumentation        OBJECT IDENTIFIER ::= { enterprises 6670 }
versonix                          OBJECT IDENTIFIER ::= { enterprises 6671 }
proscendCommunications            OBJECT IDENTIFIER ::= { enterprises 6672 }
alignSystemsPty                   OBJECT IDENTIFIER ::= { enterprises 6673 }
mercator                          OBJECT IDENTIFIER ::= { enterprises 6674 }
newsInteractive                   OBJECT IDENTIFIER ::= { enterprises 6675 }
scienceDynamicsCorporation        OBJECT IDENTIFIER ::= { enterprises 6676 }
onelineAG                         OBJECT IDENTIFIER ::= { enterprises 6677 }
hyperknowledge                    OBJECT IDENTIFIER ::= { enterprises 6678 }
surgientNetworks                  OBJECT IDENTIFIER ::= { enterprises 6679 }
southpaw                          OBJECT IDENTIFIER ::= { enterprises 6680 }
alteaCommunications               OBJECT IDENTIFIER ::= { enterprises 6681 }
commshouse                        OBJECT IDENTIFIER ::= { enterprises 6682 }
alphatrustCorporation             OBJECT IDENTIFIER ::= { enterprises 6683 }
eoriginal                         OBJECT IDENTIFIER ::= { enterprises 6684 }
inovaDiagnostics                  OBJECT IDENTIFIER ::= { enterprises 6685 }
vecommerce                        OBJECT IDENTIFIER ::= { enterprises 6686 }
pasia                             OBJECT IDENTIFIER ::= { enterprises 6687 }
nationalCenterForSoftwareTechnology OBJECT IDENTIFIER ::= { enterprises 6688 }
caveoSystems                      OBJECT IDENTIFIER ::= { enterprises 6689 }
omniclusterTechnologies           OBJECT IDENTIFIER ::= { enterprises 6690 }
utel                              OBJECT IDENTIFIER ::= { enterprises 6691 }
telenisusCorporation              OBJECT IDENTIFIER ::= { enterprises 6692 }
netcertainty                      OBJECT IDENTIFIER ::= { enterprises 6693 }
pgpSa                             OBJECT IDENTIFIER ::= { enterprises 6694 }
sams                              OBJECT IDENTIFIER ::= { enterprises 6695 }
niagaraMohawkPowerCorporation     OBJECT IDENTIFIER ::= { enterprises 6696 }
dotcom                            OBJECT IDENTIFIER ::= { enterprises 6697 }
micronetSrl                       OBJECT IDENTIFIER ::= { enterprises 6698 }
vulcanNetworks                    OBJECT IDENTIFIER ::= { enterprises 6699 }
fingo                             OBJECT IDENTIFIER ::= { enterprises 6700 }
creativNetworkTechnologies        OBJECT IDENTIFIER ::= { enterprises 6701 }
cygnacomSolutions                 OBJECT IDENTIFIER ::= { enterprises 6702 }
cognitronicsCorporation           OBJECT IDENTIFIER ::= { enterprises 6703 }
vancouverLanguageInstitute        OBJECT IDENTIFIER ::= { enterprises 6704 }
zygox                             OBJECT IDENTIFIER ::= { enterprises 6705 }
noaaPMELEPIC                      OBJECT IDENTIFIER ::= { enterprises 6706 }
rolfBuurke                        OBJECT IDENTIFIER ::= { enterprises 6707 }
handuruTelecom                    OBJECT IDENTIFIER ::= { enterprises 6708 }
scarletTelecomBV                  OBJECT IDENTIFIER ::= { enterprises 6709 }
southBirminghamCollege            OBJECT IDENTIFIER ::= { enterprises 6710 }
connectOne                        OBJECT IDENTIFIER ::= { enterprises 6711 }
voxtronicTechnology               OBJECT IDENTIFIER ::= { enterprises 6712 }
eizoNANAOCORPORATION              OBJECT IDENTIFIER ::= { enterprises 6713 }
bancoSantanderCentralHispano      OBJECT IDENTIFIER ::= { enterprises 6714 }
httConsulting                     OBJECT IDENTIFIER ::= { enterprises 6715 }
amsSystems                        OBJECT IDENTIFIER ::= { enterprises 6716 }
giantloopNetwork                  OBJECT IDENTIFIER ::= { enterprises 6717 }
exfoFiberOpticTestEquipment       OBJECT IDENTIFIER ::= { enterprises 6718 }
transcommTechnologySystem         OBJECT IDENTIFIER ::= { enterprises 6719 }
ptHariffDTE                       OBJECT IDENTIFIER ::= { enterprises 6720 }
lodbrokerPty                      OBJECT IDENTIFIER ::= { enterprises 6721 }
commatch                          OBJECT IDENTIFIER ::= { enterprises 6722 }
internetNamesUK                   OBJECT IDENTIFIER ::= { enterprises 6723 }
capGeminiTelecomFranceIPNS        OBJECT IDENTIFIER ::= { enterprises 6724 }
dataInterchangePlc                OBJECT IDENTIFIER ::= { enterprises 6725 }
cellpointSystems                  OBJECT IDENTIFIER ::= { enterprises 6726 }
winitSa                           OBJECT IDENTIFIER ::= { enterprises 6727 }
interlinkNetworks                 OBJECT IDENTIFIER ::= { enterprises 6728 }
dolbyLaboratories                 OBJECT IDENTIFIER ::= { enterprises 6729 }
nextelPartners                    OBJECT IDENTIFIER ::= { enterprises 6730 }
witSoundview                      OBJECT IDENTIFIER ::= { enterprises 6731 }
intercim                          OBJECT IDENTIFIER ::= { enterprises 6732 }
cmdTechnology                     OBJECT IDENTIFIER ::= { enterprises 6733 }
wego                              OBJECT IDENTIFIER ::= { enterprises 6734 }
tenebrous                         OBJECT IDENTIFIER ::= { enterprises 6735 }
jinnySoftware                     OBJECT IDENTIFIER ::= { enterprises 6736 }
newEraOfNetworks                  OBJECT IDENTIFIER ::= { enterprises 6737 }
threeBit                          OBJECT IDENTIFIER ::= { enterprises 6738 }
springYellow                      OBJECT IDENTIFIER ::= { enterprises 6739 }
calPolyStateUniversity            OBJECT IDENTIFIER ::= { enterprises 6740 }
nulliSecundus                     OBJECT IDENTIFIER ::= { enterprises 6741 }
pricelinecom                      OBJECT IDENTIFIER ::= { enterprises 6742 }
sophicomm                         OBJECT IDENTIFIER ::= { enterprises 6743 }
dantron                           OBJECT IDENTIFIER ::= { enterprises 6744 }
lasatNetworksAS                   OBJECT IDENTIFIER ::= { enterprises 6745 }
aftekInfosys                      OBJECT IDENTIFIER ::= { enterprises 6746 }
teraburstNetworks                 OBJECT IDENTIFIER ::= { enterprises 6747 }
up4grab                           OBJECT IDENTIFIER ::= { enterprises 6748 }
bosungHiNetCo                     OBJECT IDENTIFIER ::= { enterprises 6749 }
gascom                            OBJECT IDENTIFIER ::= { enterprises 6750 }
dolphinInterconnectSolutionsAS    OBJECT IDENTIFIER ::= { enterprises 6751 }
axtronics                         OBJECT IDENTIFIER ::= { enterprises 6752 }
syscontrolAG                      OBJECT IDENTIFIER ::= { enterprises 6753 }
ezgov                             OBJECT IDENTIFIER ::= { enterprises 6754 }
rushPresbyterianStLukesMedicalCenter OBJECT IDENTIFIER ::= { enterprises 6755 }
unixguyorg                        OBJECT IDENTIFIER ::= { enterprises 6756 }
grid                              OBJECT IDENTIFIER ::= { enterprises 6757 }
simplysay                         OBJECT IDENTIFIER ::= { enterprises 6758 }
allcharge                         OBJECT IDENTIFIER ::= { enterprises 6759 }
virginiaTech                      OBJECT IDENTIFIER ::= { enterprises 6760 }
axonnWirelessSolutions            OBJECT IDENTIFIER ::= { enterprises 6761 }
cambridgePositioningSystemsLimit  OBJECT IDENTIFIER ::= { enterprises 6762 }
metakernelNetworkLaboratories     OBJECT IDENTIFIER ::= { enterprises 6763 }
imagineSolutions                  OBJECT IDENTIFIER ::= { enterprises 6764 }
mlHightower                       OBJECT IDENTIFIER ::= { enterprises 6765 }
cpni                              OBJECT IDENTIFIER ::= { enterprises 6766 }
rocketlogix                       OBJECT IDENTIFIER ::= { enterprises 6767 }
pixelmetrixCorporationPte         OBJECT IDENTIFIER ::= { enterprises 6768 }
dynamicImagingCorporation         OBJECT IDENTIFIER ::= { enterprises 6769 }
openconCommunicationSystems       OBJECT IDENTIFIER ::= { enterprises 6770 }
cyberpath                         OBJECT IDENTIFIER ::= { enterprises 6771 }
ebsure                            OBJECT IDENTIFIER ::= { enterprises 6772 }
engineeringInternationalCorporation OBJECT IDENTIFIER ::= { enterprises 6773 }
universityOfVirginia              OBJECT IDENTIFIER ::= { enterprises 6774 }
cablevision                       OBJECT IDENTIFIER ::= { enterprises 6775 }
bmypc                             OBJECT IDENTIFIER ::= { enterprises 6776 }
trigemInfoComm                    OBJECT IDENTIFIER ::= { enterprises 6777 }
abocomSystems                     OBJECT IDENTIFIER ::= { enterprises 6778 }
chlNETHERLANDSBV                  OBJECT IDENTIFIER ::= { enterprises 6779 }
linuxCommunicationsAS             OBJECT IDENTIFIER ::= { enterprises 6780 }
vast                              OBJECT IDENTIFIER ::= { enterprises 6781 }
akara                             OBJECT IDENTIFIER ::= { enterprises 6782 }
tidepoint                         OBJECT IDENTIFIER ::= { enterprises 6783 }
jpSystems                         OBJECT IDENTIFIER ::= { enterprises 6784 }
deltaElectronicsINC               OBJECT IDENTIFIER ::= { enterprises 6785 }
dreamworksSKG                     OBJECT IDENTIFIER ::= { enterprises 6786 }
netconnect                        OBJECT IDENTIFIER ::= { enterprises 6787 }
whitebird                         OBJECT IDENTIFIER ::= { enterprises 6788 }
octogonSoftwareDevelopmentGmbH    OBJECT IDENTIFIER ::= { enterprises 6789 }
finjanSoftware                    OBJECT IDENTIFIER ::= { enterprises 6790 }
exeTechnologies                   OBJECT IDENTIFIER ::= { enterprises 6791 }
activeSoftware2                   OBJECT IDENTIFIER ::= { enterprises 6792 }
utiasi                            OBJECT IDENTIFIER ::= { enterprises 6793 }
adhesiveSoftware                  OBJECT IDENTIFIER ::= { enterprises 6794 }
poconoPetSitters                  OBJECT IDENTIFIER ::= { enterprises 6795 }
tekvisionCommunications           OBJECT IDENTIFIER ::= { enterprises 6796 }
fundamentalSoftware               OBJECT IDENTIFIER ::= { enterprises 6797 }
designOfSystemsOnSilicon          OBJECT IDENTIFIER ::= { enterprises 6798 }
gluecode                          OBJECT IDENTIFIER ::= { enterprises 6799 }
expressRailLinkSdnBhd             OBJECT IDENTIFIER ::= { enterprises 6800 }
gammaTechnologies                 OBJECT IDENTIFIER ::= { enterprises 6801 }
mDesignCommunications             OBJECT IDENTIFIER ::= { enterprises 6802 }
bci                               OBJECT IDENTIFIER ::= { enterprises 6803 }
weinschelCorp                     OBJECT IDENTIFIER ::= { enterprises 6804 }
psaWORLDNETINC                    OBJECT IDENTIFIER ::= { enterprises 6805 }
pennState                         OBJECT IDENTIFIER ::= { enterprises 6806 }
eotvosLorandUniversity            OBJECT IDENTIFIER ::= { enterprises 6807 }
buyersLaboratory                  OBJECT IDENTIFIER ::= { enterprises 6808 }
ontikaComputersystems             OBJECT IDENTIFIER ::= { enterprises 6809 }
muxcomINC                         OBJECT IDENTIFIER ::= { enterprises 6810 }
nameflow                          OBJECT IDENTIFIER ::= { enterprises 6811 }
yodaCommunications                OBJECT IDENTIFIER ::= { enterprises 6812 }
olympiaCollege                    OBJECT IDENTIFIER ::= { enterprises 6813 }
itchyfeetNetworks                 OBJECT IDENTIFIER ::= { enterprises 6814 }
cyberspaciaPty                    OBJECT IDENTIFIER ::= { enterprises 6815 }
b4                                OBJECT IDENTIFIER ::= { enterprises 6816 }
metanate                          OBJECT IDENTIFIER ::= { enterprises 6817 }
tripwire                          OBJECT IDENTIFIER ::= { enterprises 6818 }
musicfans                         OBJECT IDENTIFIER ::= { enterprises 6819 }
mentaSoftware                     OBJECT IDENTIFIER ::= { enterprises 6820 }
enic                              OBJECT IDENTIFIER ::= { enterprises 6821 }
universityOfCambridge             OBJECT IDENTIFIER ::= { enterprises 6822 }
distributedObjectTechnologies     OBJECT IDENTIFIER ::= { enterprises 6823 }
listAndNiemann                    OBJECT IDENTIFIER ::= { enterprises 6824 }
icueSystems                       OBJECT IDENTIFIER ::= { enterprises 6825 }
darkMatterNetworkTechnologies     OBJECT IDENTIFIER ::= { enterprises 6826 }
evertzMicrosystems                OBJECT IDENTIFIER ::= { enterprises 6827 }
cavinessSoftware                  OBJECT IDENTIFIER ::= { enterprises 6828 }
ramix                             OBJECT IDENTIFIER ::= { enterprises 6829 }
onehottmin                        OBJECT IDENTIFIER ::= { enterprises 6830 }
dssDigitalSecurityServiceGmbH     OBJECT IDENTIFIER ::= { enterprises 6831 }
vcheqcomPte                       OBJECT IDENTIFIER ::= { enterprises 6832 }
scarptorNetworkAB                 OBJECT IDENTIFIER ::= { enterprises 6833 }
sbuckNetworks                     OBJECT IDENTIFIER ::= { enterprises 6834 }
chelloBroadbandAustria            OBJECT IDENTIFIER ::= { enterprises 6835 }
felleskjopetTrondheim             OBJECT IDENTIFIER ::= { enterprises 6836 }
solcom                            OBJECT IDENTIFIER ::= { enterprises 6837 }
igc                               OBJECT IDENTIFIER ::= { enterprises 6838 }
accelightNetworks                 OBJECT IDENTIFIER ::= { enterprises 6839 }
deutschesElektronenSynchrotronDESY OBJECT IDENTIFIER ::= { enterprises 6840 }
vyx                               OBJECT IDENTIFIER ::= { enterprises 6841 }
telect                            OBJECT IDENTIFIER ::= { enterprises 6842 }
globalSolution                    OBJECT IDENTIFIER ::= { enterprises 6843 }
satConsultingApS                  OBJECT IDENTIFIER ::= { enterprises 6844 }
microEnergeticsCorp               OBJECT IDENTIFIER ::= { enterprises 6845 }
paulosoft                         OBJECT IDENTIFIER ::= { enterprises 6846 }
teleias                           OBJECT IDENTIFIER ::= { enterprises 6847 }
crossbeamSystems                  OBJECT IDENTIFIER ::= { enterprises 6848 }
reddoNetworksAB                   OBJECT IDENTIFIER ::= { enterprises 6849 }
mcct                              OBJECT IDENTIFIER ::= { enterprises 6850 }
xor                               OBJECT IDENTIFIER ::= { enterprises 6851 }
universityOfColoradoAtBoulder     OBJECT IDENTIFIER ::= { enterprises 6852 }
televisionSystems                 OBJECT IDENTIFIER ::= { enterprises 6853 }
regieDesTransportsDeMarseille     OBJECT IDENTIFIER ::= { enterprises 6854 }
wnfConsulting                     OBJECT IDENTIFIER ::= { enterprises 6855 }
liquidlight                       OBJECT IDENTIFIER ::= { enterprises 6856 }
digitalconvergence                OBJECT IDENTIFIER ::= { enterprises 6857 }
fantasmaNetworks                  OBJECT IDENTIFIER ::= { enterprises 6858 }
actzero                           OBJECT IDENTIFIER ::= { enterprises 6859 }
--                                OBJECT IDENTIFIER ::= { enterprises 6860 }
druma                             OBJECT IDENTIFIER ::= { enterprises 6861 }
wapinspaincom                     OBJECT IDENTIFIER ::= { enterprises 6862 }
zytraxCommunications              OBJECT IDENTIFIER ::= { enterprises 6863 }
harmaniaMultimedia                OBJECT IDENTIFIER ::= { enterprises 6864 }
elronTelesoft                     OBJECT IDENTIFIER ::= { enterprises 6865 }
lyonnaiseCommunication            OBJECT IDENTIFIER ::= { enterprises 6866 }
ipoptical                         OBJECT IDENTIFIER ::= { enterprises 6867 }
georgetownUniversity              OBJECT IDENTIFIER ::= { enterprises 6868 }
steveBurton                       OBJECT IDENTIFIER ::= { enterprises 6869 }
coreSoftwareTechnology            OBJECT IDENTIFIER ::= { enterprises 6870 }
certCoordinationCenter            OBJECT IDENTIFIER ::= { enterprises 6871 }
helpSystems                       OBJECT IDENTIFIER ::= { enterprises 6872 }
bholdCompany                      OBJECT IDENTIFIER ::= { enterprises 6873 }
woodwindCommunicationsSystems2    OBJECT IDENTIFIER ::= { enterprises 6874 }
newearthSwedenborgianBBS          OBJECT IDENTIFIER ::= { enterprises 6875 }
vmware                            OBJECT IDENTIFIER ::= { enterprises 6876 }
evergreenInternet                 OBJECT IDENTIFIER ::= { enterprises 6877 }
blackBoxCorp                      OBJECT IDENTIFIER ::= { enterprises 6878 }
digiminecom                       OBJECT IDENTIFIER ::= { enterprises 6879 }
--                                OBJECT IDENTIFIER ::= { enterprises 6880 }
kal                               OBJECT IDENTIFIER ::= { enterprises 6881 }
microElectronics                  OBJECT IDENTIFIER ::= { enterprises 6882 }
linuxNetworX                      OBJECT IDENTIFIER ::= { enterprises 6883 }
boco                              OBJECT IDENTIFIER ::= { enterprises 6884 }
intelligentTelecommunications     OBJECT IDENTIFIER ::= { enterprises 6885 }
kpn                               OBJECT IDENTIFIER ::= { enterprises 6886 }
itConference                      OBJECT IDENTIFIER ::= { enterprises 6887 }
milleniumInstaller                OBJECT IDENTIFIER ::= { enterprises 6888 }
avayaCommunication                OBJECT IDENTIFIER ::= { enterprises 6889 }
shellServicesInternational        OBJECT IDENTIFIER ::= { enterprises 6890 }
aceptacom                         OBJECT IDENTIFIER ::= { enterprises 6891 }
cnation                           OBJECT IDENTIFIER ::= { enterprises 6892 }
turbolinux                        OBJECT IDENTIFIER ::= { enterprises 6893 }
datadirectNetworks                OBJECT IDENTIFIER ::= { enterprises 6894 }
ereo                              OBJECT IDENTIFIER ::= { enterprises 6895 }
mahiNetworks                      OBJECT IDENTIFIER ::= { enterprises 6896 }
jdv                               OBJECT IDENTIFIER ::= { enterprises 6897 }
veranceCorporation                OBJECT IDENTIFIER ::= { enterprises 6898 }
nanyangTechnologicalUniversity    OBJECT IDENTIFIER ::= { enterprises 6899 }
balticInstituteOfEconomicsAndFinance OBJECT IDENTIFIER ::= { enterprises 6900 }
aetacom                           OBJECT IDENTIFIER ::= { enterprises 6901 }
plischGmbhAndCoKG                 OBJECT IDENTIFIER ::= { enterprises 6902 }
visoft                            OBJECT IDENTIFIER ::= { enterprises 6903 }
ibm3                              OBJECT IDENTIFIER ::= { enterprises 6904 }
rhapsodyNetworks                  OBJECT IDENTIFIER ::= { enterprises 6905 }
asianaCommunications              OBJECT IDENTIFIER ::= { enterprises 6906 }
broadTelecom                      OBJECT IDENTIFIER ::= { enterprises 6907 }
movazNetworks                     OBJECT IDENTIFIER ::= { enterprises 6908 }
networkSecurityTechnologies       OBJECT IDENTIFIER ::= { enterprises 6909 }
inquentTechnologies               OBJECT IDENTIFIER ::= { enterprises 6910 }
aucsCommunicationsServices        OBJECT IDENTIFIER ::= { enterprises 6911 }
morganStanleyDeanWitterOnline     OBJECT IDENTIFIER ::= { enterprises 6912 }
bonaTechnology                    OBJECT IDENTIFIER ::= { enterprises 6913 }
timingSolutionsCorporation        OBJECT IDENTIFIER ::= { enterprises 6914 }
computableFunctionsLimited        OBJECT IDENTIFIER ::= { enterprises 6915 }
norbertKlasen                     OBJECT IDENTIFIER ::= { enterprises 6916 }
alternativeAdvice                 OBJECT IDENTIFIER ::= { enterprises 6917 }
belleSystemsAS                    OBJECT IDENTIFIER ::= { enterprises 6918 }
cubenetSrl                        OBJECT IDENTIFIER ::= { enterprises 6919 }
thinkAndDoSoftware                OBJECT IDENTIFIER ::= { enterprises 6920 }
morrisonIndustries                OBJECT IDENTIFIER ::= { enterprises 6921 }
aminoCommunications               OBJECT IDENTIFIER ::= { enterprises 6922 }
shutterfly                        OBJECT IDENTIFIER ::= { enterprises 6923 }
capitalInternet                   OBJECT IDENTIFIER ::= { enterprises 6924 }
unitedSpaceAlliance               OBJECT IDENTIFIER ::= { enterprises 6925 }
opticalAccess                     OBJECT IDENTIFIER ::= { enterprises 6926 }
mailcom2                          OBJECT IDENTIFIER ::= { enterprises 6927 }
mobilityNextGeneration            OBJECT IDENTIFIER ::= { enterprises 6928 }
theRootGroup                      OBJECT IDENTIFIER ::= { enterprises 6929 }
lyceeLeonardDeVinci               OBJECT IDENTIFIER ::= { enterprises 6930 }
interessengemeinschaftSoftwareEngineering OBJECT IDENTIFIER ::= { enterprises 6931 }
internetContentRegister           OBJECT IDENTIFIER ::= { enterprises 6932 }
reputy                            OBJECT IDENTIFIER ::= { enterprises 6933 }
corporationOneOfAmerica           OBJECT IDENTIFIER ::= { enterprises 6934 }
arachne                           OBJECT IDENTIFIER ::= { enterprises 6935 }
vicorsoftCORPORATION              OBJECT IDENTIFIER ::= { enterprises 6936 }
netreliance                       OBJECT IDENTIFIER ::= { enterprises 6937 }
enigma                            OBJECT IDENTIFIER ::= { enterprises 6938 }
hemporg                           OBJECT IDENTIFIER ::= { enterprises 6939 }
tuftsUniversity                   OBJECT IDENTIFIER ::= { enterprises 6940 }
proflashCrossMediaAG              OBJECT IDENTIFIER ::= { enterprises 6941 }
jamesCookUniversity               OBJECT IDENTIFIER ::= { enterprises 6942 }
rAlpha                            OBJECT IDENTIFIER ::= { enterprises 6943 }
sermepa                           OBJECT IDENTIFIER ::= { enterprises 6944 }
lakeCommunications                OBJECT IDENTIFIER ::= { enterprises 6945 }
foucheConsultingServices          OBJECT IDENTIFIER ::= { enterprises 6946 }
centralBankOfRussia               OBJECT IDENTIFIER ::= { enterprises 6947 }
tumsanOy                          OBJECT IDENTIFIER ::= { enterprises 6948 }
nextraBWCSPGmbH                   OBJECT IDENTIFIER ::= { enterprises 6949 }
aztec                             OBJECT IDENTIFIER ::= { enterprises 6950 }
freelerBV                         OBJECT IDENTIFIER ::= { enterprises 6951 }
ibiomaticsLLC                     OBJECT IDENTIFIER ::= { enterprises 6952 }
air2netAB                         OBJECT IDENTIFIER ::= { enterprises 6953 }
semaGroup                         OBJECT IDENTIFIER ::= { enterprises 6954 }
comsolKommunikationssystemeGmbH   OBJECT IDENTIFIER ::= { enterprises 6955 }
etopwareLabs                      OBJECT IDENTIFIER ::= { enterprises 6956 }
rapi10net                         OBJECT IDENTIFIER ::= { enterprises 6957 }
kentStateUniversity               OBJECT IDENTIFIER ::= { enterprises 6958 }
bluestreak                        OBJECT IDENTIFIER ::= { enterprises 6959 }
felixDANZIGERINTERNATIONALKUNSTHANDEL OBJECT IDENTIFIER ::= { enterprises 6960 }
teleringTelekomServiceGmbh        OBJECT IDENTIFIER ::= { enterprises 6961 }
theUniversityOfSydney             OBJECT IDENTIFIER ::= { enterprises 6962 }
andrewsITEngineering              OBJECT IDENTIFIER ::= { enterprises 6963 }
softTeleware                      OBJECT IDENTIFIER ::= { enterprises 6964 }
rsbx                              OBJECT IDENTIFIER ::= { enterprises 6965 }
theBrightOceansCorporation        OBJECT IDENTIFIER ::= { enterprises 6966 }
digismart                         OBJECT IDENTIFIER ::= { enterprises 6967 }
systekAS                          OBJECT IDENTIFIER ::= { enterprises 6968 }
copernicusGlobalBillingServices   OBJECT IDENTIFIER ::= { enterprises 6969 }
vcon                              OBJECT IDENTIFIER ::= { enterprises 6970 }
ferimexITSpolSRo                  OBJECT IDENTIFIER ::= { enterprises 6971 }
canbox                            OBJECT IDENTIFIER ::= { enterprises 6972 }
savatech                          OBJECT IDENTIFIER ::= { enterprises 6973 }
earthlink                         OBJECT IDENTIFIER ::= { enterprises 6974 }
watercoveNetworks                 OBJECT IDENTIFIER ::= { enterprises 6975 }
howstuffworkscom                  OBJECT IDENTIFIER ::= { enterprises 6976 }
resilienceCorporation             OBJECT IDENTIFIER ::= { enterprises 6977 }
jbrucenet                         OBJECT IDENTIFIER ::= { enterprises 6978 }
kerenix                           OBJECT IDENTIFIER ::= { enterprises 6979 }
mrcProject                        OBJECT IDENTIFIER ::= { enterprises 6980 }
interq                            OBJECT IDENTIFIER ::= { enterprises 6981 }
erbaHolding                       OBJECT IDENTIFIER ::= { enterprises 6982 }
sofawareTechnologies              OBJECT IDENTIFIER ::= { enterprises 6983 }
fovea                             OBJECT IDENTIFIER ::= { enterprises 6984 }
prismSoftware                     OBJECT IDENTIFIER ::= { enterprises 6985 }
kiodex                            OBJECT IDENTIFIER ::= { enterprises 6986 }
wronlineGbR                       OBJECT IDENTIFIER ::= { enterprises 6987 }
universityOfNorthernBritishColumbia OBJECT IDENTIFIER ::= { enterprises 6988 }
extelCommunicationsPty            OBJECT IDENTIFIER ::= { enterprises 6989 }
redfernBroadbandNetworks          OBJECT IDENTIFIER ::= { enterprises 6990 }
nSpacePty                         OBJECT IDENTIFIER ::= { enterprises 6991 }
knownow                           OBJECT IDENTIFIER ::= { enterprises 6992 }
virtualnet                        OBJECT IDENTIFIER ::= { enterprises 6993 }
theMidgardProject                 OBJECT IDENTIFIER ::= { enterprises 6994 }
cBaseEV                           OBJECT IDENTIFIER ::= { enterprises 6995 }
whatevernetComputing              OBJECT IDENTIFIER ::= { enterprises 6996 }
yaleUniversity                    OBJECT IDENTIFIER ::= { enterprises 6997 }
channelogics                      OBJECT IDENTIFIER ::= { enterprises 6998 }
universityOfIndianapolis          OBJECT IDENTIFIER ::= { enterprises 6999 }
netVolutionSrl                    OBJECT IDENTIFIER ::= { enterprises 7000 }
bigNet                            OBJECT IDENTIFIER ::= { enterprises 7001 }
sebastianCrespo                   OBJECT IDENTIFIER ::= { enterprises 7002 }
ciscoMASBU                        OBJECT IDENTIFIER ::= { enterprises 7003 }
metodoSrl                         OBJECT IDENTIFIER ::= { enterprises 7004 }
kagoorNetworks                    OBJECT IDENTIFIER ::= { enterprises 7005 }
eyeocom                           OBJECT IDENTIFIER ::= { enterprises 7006 }
guangzhouThinkerCommunicationsTechnologyCo OBJECT IDENTIFIER ::= { enterprises 7007 }
discordianAllianceForTeaching     OBJECT IDENTIFIER ::= { enterprises 7008 }
chemtexEngineeringOfIndia         OBJECT IDENTIFIER ::= { enterprises 7009 }
oranjeConsulting                  OBJECT IDENTIFIER ::= { enterprises 7010 }
prismMicrosystems                 OBJECT IDENTIFIER ::= { enterprises 7011 }
edisontelSpA                      OBJECT IDENTIFIER ::= { enterprises 7012 }
bytesphereTechnologies            OBJECT IDENTIFIER ::= { enterprises 7013 }
adexa                             OBJECT IDENTIFIER ::= { enterprises 7014 }
vignetteCorporation               OBJECT IDENTIFIER ::= { enterprises 7015 }
senecaNetworks                    OBJECT IDENTIFIER ::= { enterprises 7016 }
adariTeleComp                     OBJECT IDENTIFIER ::= { enterprises 7017 }
ptMultimedia                      OBJECT IDENTIFIER ::= { enterprises 7018 }
polarisNetworks                   OBJECT IDENTIFIER ::= { enterprises 7019 }
saecosCorporation                 OBJECT IDENTIFIER ::= { enterprises 7020 }
sysnetSnc                         OBJECT IDENTIFIER ::= { enterprises 7021 }
mrzAG                             OBJECT IDENTIFIER ::= { enterprises 7022 }
theDirectConnection               OBJECT IDENTIFIER ::= { enterprises 7023 }
vhbTechnologies                   OBJECT IDENTIFIER ::= { enterprises 7024 }
doubleDInvestments                OBJECT IDENTIFIER ::= { enterprises 7025 }
soneraSmartTrust                  OBJECT IDENTIFIER ::= { enterprises 7026 }
onixMicrosystems                  OBJECT IDENTIFIER ::= { enterprises 7027 }
alloptic                          OBJECT IDENTIFIER ::= { enterprises 7028 }
cubiweb                           OBJECT IDENTIFIER ::= { enterprises 7029 }
ethernet                          OBJECT IDENTIFIER ::= { enterprises 7030 }
securify                          OBJECT IDENTIFIER ::= { enterprises 7031 }
charteredSemiconductorManufacturing OBJECT IDENTIFIER ::= { enterprises 7032 }
matiasSoftwareGroup               OBJECT IDENTIFIER ::= { enterprises 7033 }
inyourwake                        OBJECT IDENTIFIER ::= { enterprises 7034 }
vttElectronics                    OBJECT IDENTIFIER ::= { enterprises 7035 }
mbdyn                             OBJECT IDENTIFIER ::= { enterprises 7036 }
ubris                             OBJECT IDENTIFIER ::= { enterprises 7037 }
tronNetworkSolutions              OBJECT IDENTIFIER ::= { enterprises 7038 }
bisonGmbH                         OBJECT IDENTIFIER ::= { enterprises 7039 }
datalinx                          OBJECT IDENTIFIER ::= { enterprises 7040 }
integra                           OBJECT IDENTIFIER ::= { enterprises 7041 }
permanentVacations                OBJECT IDENTIFIER ::= { enterprises 7042 }
aptComputerSystemsLimited         OBJECT IDENTIFIER ::= { enterprises 7043 }
primal                            OBJECT IDENTIFIER ::= { enterprises 7044 }
tbaCommunications                 OBJECT IDENTIFIER ::= { enterprises 7045 }
tom                               OBJECT IDENTIFIER ::= { enterprises 7046 }
fluxProductions                   OBJECT IDENTIFIER ::= { enterprises 7047 }
picoCommunications                OBJECT IDENTIFIER ::= { enterprises 7048 }
datanetDevelopmentGroup           OBJECT IDENTIFIER ::= { enterprises 7049 }
kazanStateUniversity              OBJECT IDENTIFIER ::= { enterprises 7050 }
epicomSA                          OBJECT IDENTIFIER ::= { enterprises 7051 }
ikomIngenieurburo                 OBJECT IDENTIFIER ::= { enterprises 7052 }
videonCableSystemsAlberta         OBJECT IDENTIFIER ::= { enterprises 7053 }
mazuNetworks                      OBJECT IDENTIFIER ::= { enterprises 7054 }
coxInternetServices               OBJECT IDENTIFIER ::= { enterprises 7055 }
senterprise                       OBJECT IDENTIFIER ::= { enterprises 7056 }
suseLinuxAG                       OBJECT IDENTIFIER ::= { enterprises 7057 }
bb4Technologies                   OBJECT IDENTIFIER ::= { enterprises 7058 }
completeBusinessSolutionsGlobalHealth OBJECT IDENTIFIER ::= { enterprises 7059 }
naikelSoftware                    OBJECT IDENTIFIER ::= { enterprises 7060 }
automatedLogicCorporation         OBJECT IDENTIFIER ::= { enterprises 7061 }
oasisTelecommunications           OBJECT IDENTIFIER ::= { enterprises 7062 }
australianDefenceForceAcademy     OBJECT IDENTIFIER ::= { enterprises 7063 }
utstarcom2                        OBJECT IDENTIFIER ::= { enterprises 7064 }
shiminDenshiJouhouMou             OBJECT IDENTIFIER ::= { enterprises 7065 }
drSrinivas                        OBJECT IDENTIFIER ::= { enterprises 7066 }
telcoTECHGmbH                     OBJECT IDENTIFIER ::= { enterprises 7067 }
cryptopro                         OBJECT IDENTIFIER ::= { enterprises 7068 }
sfiOpenSourceServices             OBJECT IDENTIFIER ::= { enterprises 7069 }
naradNetworks                     OBJECT IDENTIFIER ::= { enterprises 7070 }
teleInfoSystem                    OBJECT IDENTIFIER ::= { enterprises 7071 }
ehrhartJewelers                   OBJECT IDENTIFIER ::= { enterprises 7072 }
r00tkitcom                        OBJECT IDENTIFIER ::= { enterprises 7073 }
themagicprogrammer                OBJECT IDENTIFIER ::= { enterprises 7074 }
lotharMaronn                      OBJECT IDENTIFIER ::= { enterprises 7075 }
farEdgeTechnology                 OBJECT IDENTIFIER ::= { enterprises 7076 }
desarrollosDigitales              OBJECT IDENTIFIER ::= { enterprises 7077 }
trueNorthCommunications           OBJECT IDENTIFIER ::= { enterprises 7078 }
megistoSystems                    OBJECT IDENTIFIER ::= { enterprises 7079 }
xelinet                           OBJECT IDENTIFIER ::= { enterprises 7080 }
maaslandseUnixAndLinuxLaboratorium OBJECT IDENTIFIER ::= { enterprises 7081 }
daidenCO                          OBJECT IDENTIFIER ::= { enterprises 7082 }
appliedGenerics                   OBJECT IDENTIFIER ::= { enterprises 7083 }
friendsProvident                  OBJECT IDENTIFIER ::= { enterprises 7084 }
cybercommBV                       OBJECT IDENTIFIER ::= { enterprises 7085 }
gtongShenzhen                     OBJECT IDENTIFIER ::= { enterprises 7086 }
selisNetworks                     OBJECT IDENTIFIER ::= { enterprises 7087 }
networkSystems                    OBJECT IDENTIFIER ::= { enterprises 7088 }
centrumArbeidsverhoudingen        OBJECT IDENTIFIER ::= { enterprises 7089 }
elBitSalvaje                      OBJECT IDENTIFIER ::= { enterprises 7090 }
cren                              OBJECT IDENTIFIER ::= { enterprises 7091 }
sciencexchange                    OBJECT IDENTIFIER ::= { enterprises 7092 }
ericssonGeobility                 OBJECT IDENTIFIER ::= { enterprises 7093 }
wachoviaTrust                     OBJECT IDENTIFIER ::= { enterprises 7094 }
pert                              OBJECT IDENTIFIER ::= { enterprises 7095 }
jseic                             OBJECT IDENTIFIER ::= { enterprises 7096 }
leatherxchange                    OBJECT IDENTIFIER ::= { enterprises 7097 }
edisonMissionEnergy               OBJECT IDENTIFIER ::= { enterprises 7098 }
ripeco                            OBJECT IDENTIFIER ::= { enterprises 7099 }
killikAndCo                       OBJECT IDENTIFIER ::= { enterprises 7100 }
co3i                              OBJECT IDENTIFIER ::= { enterprises 7101 }
idealx                            OBJECT IDENTIFIER ::= { enterprises 7102 }
saltfire                          OBJECT IDENTIFIER ::= { enterprises 7103 }
superverticalSistemas             OBJECT IDENTIFIER ::= { enterprises 7104 }
cantv                             OBJECT IDENTIFIER ::= { enterprises 7105 }
teleportCorp                      OBJECT IDENTIFIER ::= { enterprises 7106 }
geocastNetworkSystems             OBJECT IDENTIFIER ::= { enterprises 7107 }
urschelerSoftware                 OBJECT IDENTIFIER ::= { enterprises 7108 }
cityUniversityOfHongkong          OBJECT IDENTIFIER ::= { enterprises 7109 }
kaashyapRadiantSystem             OBJECT IDENTIFIER ::= { enterprises 7110 }
sunamericanCommunicationTechnology OBJECT IDENTIFIER ::= { enterprises 7111 }
usDepartmentOfCommerce            OBJECT IDENTIFIER ::= { enterprises 7112 }
yottayotta                        OBJECT IDENTIFIER ::= { enterprises 7113 }
universidadDeNavarra              OBJECT IDENTIFIER ::= { enterprises 7114 }
book2eatcomLimited                OBJECT IDENTIFIER ::= { enterprises 7115 }
techtradeInternationalManagementAB OBJECT IDENTIFIER ::= { enterprises 7116 }
invertix                          OBJECT IDENTIFIER ::= { enterprises 7117 }
netcontinuum                      OBJECT IDENTIFIER ::= { enterprises 7118 }
networkPhysics                    OBJECT IDENTIFIER ::= { enterprises 7119 }
sentryTelecomSystems              OBJECT IDENTIFIER ::= { enterprises 7120 }
psinetChileSA                     OBJECT IDENTIFIER ::= { enterprises 7121 }
lusarsnet                         OBJECT IDENTIFIER ::= { enterprises 7122 }
nsofParallelSoftware              OBJECT IDENTIFIER ::= { enterprises 7123 }
standBy                           OBJECT IDENTIFIER ::= { enterprises 7124 }
digitalCreations                  OBJECT IDENTIFIER ::= { enterprises 7125 }
positronPublicSafetySystems       OBJECT IDENTIFIER ::= { enterprises 7126 }
nadeemHasan                       OBJECT IDENTIFIER ::= { enterprises 7127 }
worcesterPolytechnicInstitute     OBJECT IDENTIFIER ::= { enterprises 7128 }
lancasterUniversity               OBJECT IDENTIFIER ::= { enterprises 7129 }
kiddiepotcom                      OBJECT IDENTIFIER ::= { enterprises 7130 }
orientTelecom                     OBJECT IDENTIFIER ::= { enterprises 7131 }
elansatTECHNOLOGIESINC            OBJECT IDENTIFIER ::= { enterprises 7132 }
corenixSystem                     OBJECT IDENTIFIER ::= { enterprises 7133 }
prosolve                          OBJECT IDENTIFIER ::= { enterprises 7134 }
--                                OBJECT IDENTIFIER ::= { enterprises 7135 }
sysnet                            OBJECT IDENTIFIER ::= { enterprises 7136 }
tunisieTelecom                    OBJECT IDENTIFIER ::= { enterprises 7137 }
allaireCorporation                OBJECT IDENTIFIER ::= { enterprises 7138 }
echostarDataNetworks              OBJECT IDENTIFIER ::= { enterprises 7139 }
inpg                              OBJECT IDENTIFIER ::= { enterprises 7140 }
freesoft                          OBJECT IDENTIFIER ::= { enterprises 7141 }
pingtelCorp                       OBJECT IDENTIFIER ::= { enterprises 7142 }
entrustTechnologies               OBJECT IDENTIFIER ::= { enterprises 7143 }
facetimeCommunications2           OBJECT IDENTIFIER ::= { enterprises 7144 }
evecom                            OBJECT IDENTIFIER ::= { enterprises 7145 }
zeusTechnology                    OBJECT IDENTIFIER ::= { enterprises 7146 }
imperialTechnology                OBJECT IDENTIFIER ::= { enterprises 7147 }
unitreeSoftware                   OBJECT IDENTIFIER ::= { enterprises 7148 }
arcotSystems                      OBJECT IDENTIFIER ::= { enterprises 7149 }
initech                           OBJECT IDENTIFIER ::= { enterprises 7150 }
rPdeshpande                       OBJECT IDENTIFIER ::= { enterprises 7151 }
capeTechnologies                  OBJECT IDENTIFIER ::= { enterprises 7152 }
foertschEDVBeratung               OBJECT IDENTIFIER ::= { enterprises 7153 }
intelligentPlatformManagementInterfaceForum OBJECT IDENTIFIER ::= { enterprises 7154 }
neohavennet                       OBJECT IDENTIFIER ::= { enterprises 7155 }
princetonNetworks                 OBJECT IDENTIFIER ::= { enterprises 7156 }
scDartIMPEXSRL                    OBJECT IDENTIFIER ::= { enterprises 7157 }
globalCitycom                     OBJECT IDENTIFIER ::= { enterprises 7158 }
allianzAG                         OBJECT IDENTIFIER ::= { enterprises 7159 }
granadaLearning                   OBJECT IDENTIFIER ::= { enterprises 7160 }
networkSolutions2                 OBJECT IDENTIFIER ::= { enterprises 7161 }
delanceyManagementAndConsulting   OBJECT IDENTIFIER ::= { enterprises 7162 }
fioranoSoftware                   OBJECT IDENTIFIER ::= { enterprises 7163 }
schizoInformationNetwork          OBJECT IDENTIFIER ::= { enterprises 7164 }
sambaTeam                         OBJECT IDENTIFIER ::= { enterprises 7165 }
petersSecuritiesCo                OBJECT IDENTIFIER ::= { enterprises 7166 }
wintertek                         OBJECT IDENTIFIER ::= { enterprises 7167 }
eurosoftSas                       OBJECT IDENTIFIER ::= { enterprises 7168 }
engage                            OBJECT IDENTIFIER ::= { enterprises 7169 }
centellTelecommunicationCompany   OBJECT IDENTIFIER ::= { enterprises 7170 }
europesaveSA                      OBJECT IDENTIFIER ::= { enterprises 7171 }
sparknetSA                        OBJECT IDENTIFIER ::= { enterprises 7172 }
jiangsuUniversityOfScienceAndTechnology OBJECT IDENTIFIER ::= { enterprises 7173 }
tonicSoftware                     OBJECT IDENTIFIER ::= { enterprises 7174 }
tspLab                            OBJECT IDENTIFIER ::= { enterprises 7175 }
orangefoodcom                     OBJECT IDENTIFIER ::= { enterprises 7176 }
ipitek                            OBJECT IDENTIFIER ::= { enterprises 7177 }
sanjosedeocoacomdo                OBJECT IDENTIFIER ::= { enterprises 7178 }
arioDataNetworks                  OBJECT IDENTIFIER ::= { enterprises 7179 }
talarianCorporation               OBJECT IDENTIFIER ::= { enterprises 7180 }
trendium                          OBJECT IDENTIFIER ::= { enterprises 7181 }
ypassnet                          OBJECT IDENTIFIER ::= { enterprises 7182 }
springfieldPublicSchools          OBJECT IDENTIFIER ::= { enterprises 7183 }
--                                OBJECT IDENTIFIER ::= { enterprises 7184 }
latitudeCommunications            OBJECT IDENTIFIER ::= { enterprises 7185 }
baypackets                        OBJECT IDENTIFIER ::= { enterprises 7186 }
netsystems                        OBJECT IDENTIFIER ::= { enterprises 7187 }
curtinUniversityOfTechnology      OBJECT IDENTIFIER ::= { enterprises 7188 }
emsGlobal                         OBJECT IDENTIFIER ::= { enterprises 7189 }
legatoSystemsIndia                OBJECT IDENTIFIER ::= { enterprises 7190 }
gebruederWeissGmbH                OBJECT IDENTIFIER ::= { enterprises 7191 }
idPROAktiengesellschaft           OBJECT IDENTIFIER ::= { enterprises 7192 }
bourseConnect                     OBJECT IDENTIFIER ::= { enterprises 7193 }
stevensGagnonServicesInfoTechniques OBJECT IDENTIFIER ::= { enterprises 7194 }
iquilibrium                       OBJECT IDENTIFIER ::= { enterprises 7195 }
imagineSoftware                   OBJECT IDENTIFIER ::= { enterprises 7196 }
intertech                         OBJECT IDENTIFIER ::= { enterprises 7197 }
celight                           OBJECT IDENTIFIER ::= { enterprises 7198 }
bridgeSoftware                    OBJECT IDENTIFIER ::= { enterprises 7199 }
forebrickInternational            OBJECT IDENTIFIER ::= { enterprises 7200 }
drukerConsulting                  OBJECT IDENTIFIER ::= { enterprises 7201 }
seastem                           OBJECT IDENTIFIER ::= { enterprises 7202 }
technologyBuilders                OBJECT IDENTIFIER ::= { enterprises 7203 }
performanceitcom                  OBJECT IDENTIFIER ::= { enterprises 7204 }
coretechConsultingGroup           OBJECT IDENTIFIER ::= { enterprises 7205 }
realMedia                         OBJECT IDENTIFIER ::= { enterprises 7206 }
denonDENTAL                       OBJECT IDENTIFIER ::= { enterprises 7207 }
afconSoftwareAndElectronics       OBJECT IDENTIFIER ::= { enterprises 7208 }
societeBryardeDeTravauxPublics    OBJECT IDENTIFIER ::= { enterprises 7209 }
workspot                          OBJECT IDENTIFIER ::= { enterprises 7210 }
raiffeisen                        OBJECT IDENTIFIER ::= { enterprises 7211 }
basoft                            OBJECT IDENTIFIER ::= { enterprises 7212 }
datriaSystems                     OBJECT IDENTIFIER ::= { enterprises 7213 }
virginiaMerylandRegionalCollegeOfVeterinaryMedicine OBJECT IDENTIFIER ::= { enterprises 7214 }
abnAMRO                           OBJECT IDENTIFIER ::= { enterprises 7215 }
institutNationalDeLaRechercheAgronomique OBJECT IDENTIFIER ::= { enterprises 7216 }
theUniversityOfMemphis            OBJECT IDENTIFIER ::= { enterprises 7217 }
hbesoftware                       OBJECT IDENTIFIER ::= { enterprises 7218 }
firedrop                          OBJECT IDENTIFIER ::= { enterprises 7219 }
shanghaiOpticalNetworkingTechnologyCo OBJECT IDENTIFIER ::= { enterprises 7220 }
handlinkTechnologies              OBJECT IDENTIFIER ::= { enterprises 7221 }
tiscover                          OBJECT IDENTIFIER ::= { enterprises 7222 }
ofehrnet                          OBJECT IDENTIFIER ::= { enterprises 7223 }
netarchitectsSA                   OBJECT IDENTIFIER ::= { enterprises 7224 }
spacecheckerNv                    OBJECT IDENTIFIER ::= { enterprises 7225 }
microFX                           OBJECT IDENTIFIER ::= { enterprises 7226 }
centreInformatiqueNationalDeL     OBJECT IDENTIFIER ::= { enterprises 7227 }
theWebFoundryLimited              OBJECT IDENTIFIER ::= { enterprises 7228 }
vogelerEnterpriseArchitectures    OBJECT IDENTIFIER ::= { enterprises 7229 }
easternMichiganUniversity         OBJECT IDENTIFIER ::= { enterprises 7230 }
midstreamTechnologies             OBJECT IDENTIFIER ::= { enterprises 7231 }
vr1Entertainment                  OBJECT IDENTIFIER ::= { enterprises 7232 }
sierracitiescom                   OBJECT IDENTIFIER ::= { enterprises 7233 }
kore                              OBJECT IDENTIFIER ::= { enterprises 7234 }
eradlink                          OBJECT IDENTIFIER ::= { enterprises 7235 }
simmComm                          OBJECT IDENTIFIER ::= { enterprises 7236 }
aaronsenGroup                     OBJECT IDENTIFIER ::= { enterprises 7237 }
omTechnology                      OBJECT IDENTIFIER ::= { enterprises 7238 }
legrand                           OBJECT IDENTIFIER ::= { enterprises 7239 }
princetonNetworks2                OBJECT IDENTIFIER ::= { enterprises 7240 }
internet                          OBJECT IDENTIFIER ::= { enterprises 7241 }
qwicnet                           OBJECT IDENTIFIER ::= { enterprises 7242 }
zivoWellington                    OBJECT IDENTIFIER ::= { enterprises 7243 }
quantaComputer                    OBJECT IDENTIFIER ::= { enterprises 7244 }
northernDistrictsInLineHockeyClub OBJECT IDENTIFIER ::= { enterprises 7245 }
projectXConsulting                OBJECT IDENTIFIER ::= { enterprises 7246 }
nexsanTechnologies                OBJECT IDENTIFIER ::= { enterprises 7247 }
hypertrust                        OBJECT IDENTIFIER ::= { enterprises 7248 }
manageIT                          OBJECT IDENTIFIER ::= { enterprises 7249 }
viewgraphics                      OBJECT IDENTIFIER ::= { enterprises 7250 }
spcSolutionsSro                   OBJECT IDENTIFIER ::= { enterprises 7251 }
institutMondorDeMedecineMoleculaire OBJECT IDENTIFIER ::= { enterprises 7252 }
streamcache                       OBJECT IDENTIFIER ::= { enterprises 7253 }
intronixCorporation               OBJECT IDENTIFIER ::= { enterprises 7254 }
pointoneTelecommunications        OBJECT IDENTIFIER ::= { enterprises 7255 }
geyserNetworks                    OBJECT IDENTIFIER ::= { enterprises 7256 }
marNet                            OBJECT IDENTIFIER ::= { enterprises 7257 }
centreNationalDeDocumentationPedagogique OBJECT IDENTIFIER ::= { enterprises 7258 }
oullimInformationTechnology       OBJECT IDENTIFIER ::= { enterprises 7259 }
opthos                            OBJECT IDENTIFIER ::= { enterprises 7260 }
infospace                         OBJECT IDENTIFIER ::= { enterprises 7261 }
dragonwave                        OBJECT IDENTIFIER ::= { enterprises 7262 }
littProductions                   OBJECT IDENTIFIER ::= { enterprises 7263 }
--                                OBJECT IDENTIFIER ::= { enterprises 7264 }
interactivePortal                 OBJECT IDENTIFIER ::= { enterprises 7265 }
softfront                         OBJECT IDENTIFIER ::= { enterprises 7266 }
broadlinkTechnologies             OBJECT IDENTIFIER ::= { enterprises 7267 }
axiavoiceSoftware                 OBJECT IDENTIFIER ::= { enterprises 7268 }
universityOfKlagenfurt            OBJECT IDENTIFIER ::= { enterprises 7269 }
supanetLimited                    OBJECT IDENTIFIER ::= { enterprises 7270 }
tuxwarp                           OBJECT IDENTIFIER ::= { enterprises 7271 }
redsirenTechnologies              OBJECT IDENTIFIER ::= { enterprises 7272 }
whenPigsFlyClub                   OBJECT IDENTIFIER ::= { enterprises 7273 }
cityOFWILLCOX                     OBJECT IDENTIFIER ::= { enterprises 7274 }
amsterdamseHogeschoolVoorDeKunsten OBJECT IDENTIFIER ::= { enterprises 7275 }
parabonComputation                OBJECT IDENTIFIER ::= { enterprises 7276 }
polyserve                         OBJECT IDENTIFIER ::= { enterprises 7277 }
digitalArchway                    OBJECT IDENTIFIER ::= { enterprises 7278 }
zembuLabs                         OBJECT IDENTIFIER ::= { enterprises 7279 }
vodafoneNetworkPty                OBJECT IDENTIFIER ::= { enterprises 7280 }
socixBusinessInternetSoftwareCo   OBJECT IDENTIFIER ::= { enterprises 7281 }
superchannelApS                   OBJECT IDENTIFIER ::= { enterprises 7282 }
defenceScienceAndTechnologyAgency OBJECT IDENTIFIER ::= { enterprises 7283 }
asitaTechnologies                 OBJECT IDENTIFIER ::= { enterprises 7284 }
hutchisonPortsUKLimited           OBJECT IDENTIFIER ::= { enterprises 7285 }
betanet                           OBJECT IDENTIFIER ::= { enterprises 7286 }
premierProgramming                OBJECT IDENTIFIER ::= { enterprises 7287 }
activesky                         OBJECT IDENTIFIER ::= { enterprises 7288 }
visualAnalysisAG                  OBJECT IDENTIFIER ::= { enterprises 7289 }
samjungDataServiceLTD             OBJECT IDENTIFIER ::= { enterprises 7290 }
lecointeLudovic                   OBJECT IDENTIFIER ::= { enterprises 7291 }
kroneMultimediaGesmbHCoKG         OBJECT IDENTIFIER ::= { enterprises 7292 }
powercomCO                        OBJECT IDENTIFIER ::= { enterprises 7293 }
--                                OBJECT IDENTIFIER ::= { enterprises 7294 }
planBGmbH                         OBJECT IDENTIFIER ::= { enterprises 7295 }
eforce                            OBJECT IDENTIFIER ::= { enterprises 7296 }
adventistCareCenters              OBJECT IDENTIFIER ::= { enterprises 7297 }
yumaEducationalConsortium         OBJECT IDENTIFIER ::= { enterprises 7298 }
valenceSemiconductor              OBJECT IDENTIFIER ::= { enterprises 7299 }
bangladeshConsultants             OBJECT IDENTIFIER ::= { enterprises 7300 }
kinzebach                         OBJECT IDENTIFIER ::= { enterprises 7301 }
medsys                            OBJECT IDENTIFIER ::= { enterprises 7302 }
bygInformatique                   OBJECT IDENTIFIER ::= { enterprises 7303 }
wwwDEPARTMENT                     OBJECT IDENTIFIER ::= { enterprises 7304 }
esurvey                           OBJECT IDENTIFIER ::= { enterprises 7305 }
boku                              OBJECT IDENTIFIER ::= { enterprises 7306 }
ponyexpressnet                    OBJECT IDENTIFIER ::= { enterprises 7307 }
zaantek                           OBJECT IDENTIFIER ::= { enterprises 7308 }
argusTechnologies                 OBJECT IDENTIFIER ::= { enterprises 7309 }
enstor                            OBJECT IDENTIFIER ::= { enterprises 7310 }
tNova                             OBJECT IDENTIFIER ::= { enterprises 7311 }
barco                             OBJECT IDENTIFIER ::= { enterprises 7312 }
stwave                            OBJECT IDENTIFIER ::= { enterprises 7313 }
codeweavers                       OBJECT IDENTIFIER ::= { enterprises 7314 }
cabSoftware                       OBJECT IDENTIFIER ::= { enterprises 7315 }
bridgeSolutionsAG                 OBJECT IDENTIFIER ::= { enterprises 7316 }
mobileReachTechnologies           OBJECT IDENTIFIER ::= { enterprises 7317 }
siniaCorporation                  OBJECT IDENTIFIER ::= { enterprises 7318 }
universiteDeToulonEtDuVar         OBJECT IDENTIFIER ::= { enterprises 7319 }
ivronSystems                      OBJECT IDENTIFIER ::= { enterprises 7320 }
connext                           OBJECT IDENTIFIER ::= { enterprises 7321 }
tiburonNetworks                   OBJECT IDENTIFIER ::= { enterprises 7322 }
voicecom                          OBJECT IDENTIFIER ::= { enterprises 7323 }
chambreSyndicaleDesBanquesPopulaires OBJECT IDENTIFIER ::= { enterprises 7324 }
redeyeTelecommunications          OBJECT IDENTIFIER ::= { enterprises 7325 }
mciworldcomAccessServerProject    OBJECT IDENTIFIER ::= { enterprises 7326 }
wavesmithNetworks                 OBJECT IDENTIFIER ::= { enterprises 7327 }
matrixone                         OBJECT IDENTIFIER ::= { enterprises 7328 }
virtualLearn                      OBJECT IDENTIFIER ::= { enterprises 7329 }
bundesanstaltFuerWasserbau        OBJECT IDENTIFIER ::= { enterprises 7330 }
ddsProjectsBV                     OBJECT IDENTIFIER ::= { enterprises 7331 }
divitechAS                        OBJECT IDENTIFIER ::= { enterprises 7332 }
eCottageIndustries                OBJECT IDENTIFIER ::= { enterprises 7333 }
theSanJoaquinValleyScienceCollective OBJECT IDENTIFIER ::= { enterprises 7334 }
expertsMD                         OBJECT IDENTIFIER ::= { enterprises 7335 }
wind                              OBJECT IDENTIFIER ::= { enterprises 7336 }
liproAG                           OBJECT IDENTIFIER ::= { enterprises 7337 }
paramhamsaTech                    OBJECT IDENTIFIER ::= { enterprises 7338 }
generalsearchcom                  OBJECT IDENTIFIER ::= { enterprises 7339 }
northwesternUniversity            OBJECT IDENTIFIER ::= { enterprises 7340 }
universityOfAlabamaAtBirmingham   OBJECT IDENTIFIER ::= { enterprises 7341 }
omnitronSystemsTechnology         OBJECT IDENTIFIER ::= { enterprises 7342 }
broadconnexNetworks               OBJECT IDENTIFIER ::= { enterprises 7343 }
jedaiBroadbandNetworks            OBJECT IDENTIFIER ::= { enterprises 7344 }
learnsoftCorporation              OBJECT IDENTIFIER ::= { enterprises 7345 }
uniC                              OBJECT IDENTIFIER ::= { enterprises 7346 }
pointReyesNetworks                OBJECT IDENTIFIER ::= { enterprises 7347 }
torrenSoftwareCompany             OBJECT IDENTIFIER ::= { enterprises 7348 }
hangzhouTorrenSoftwareCompany     OBJECT IDENTIFIER ::= { enterprises 7349 }
belkamneft                        OBJECT IDENTIFIER ::= { enterprises 7350 }
teledanmarkDevelopment            OBJECT IDENTIFIER ::= { enterprises 7351 }
gilatSatelliteNetworks            OBJECT IDENTIFIER ::= { enterprises 7352 }
datelDefenceLimited               OBJECT IDENTIFIER ::= { enterprises 7353 }
vesperSA                          OBJECT IDENTIFIER ::= { enterprises 7354 }
hassAsscoiates                    OBJECT IDENTIFIER ::= { enterprises 7355 }
gatewayToTheWeb                   OBJECT IDENTIFIER ::= { enterprises 7356 }
scronercom                        OBJECT IDENTIFIER ::= { enterprises 7357 }
povCorp                           OBJECT IDENTIFIER ::= { enterprises 7358 }
steeleyeTechnology                OBJECT IDENTIFIER ::= { enterprises 7359 }
telecomPersonal                   OBJECT IDENTIFIER ::= { enterprises 7360 }
certificadoDigitalSA              OBJECT IDENTIFIER ::= { enterprises 7361 }
departmentLand                    OBJECT IDENTIFIER ::= { enterprises 7362 }
prominenceNetworks                OBJECT IDENTIFIER ::= { enterprises 7363 }
imsHealth                         OBJECT IDENTIFIER ::= { enterprises 7364 }
easily                            OBJECT IDENTIFIER ::= { enterprises 7365 }
markettouch                       OBJECT IDENTIFIER ::= { enterprises 7366 }
draytekCorporation                OBJECT IDENTIFIER ::= { enterprises 7367 }
falconstor                        OBJECT IDENTIFIER ::= { enterprises 7368 }
suncomCommunications              OBJECT IDENTIFIER ::= { enterprises 7369 }
cbeyondCommunications             OBJECT IDENTIFIER ::= { enterprises 7370 }
inserm                            OBJECT IDENTIFIER ::= { enterprises 7371 }
cratosNetworks                    OBJECT IDENTIFIER ::= { enterprises 7372 }
naradNetworks2                    OBJECT IDENTIFIER ::= { enterprises 7373 }
cAnddMicroSolutions               OBJECT IDENTIFIER ::= { enterprises 7374 }
isoftPlc                          OBJECT IDENTIFIER ::= { enterprises 7375 }
magentaSites                      OBJECT IDENTIFIER ::= { enterprises 7376 }
ubiquitySoftwareCorporation       OBJECT IDENTIFIER ::= { enterprises 7377 }
firesummit                        OBJECT IDENTIFIER ::= { enterprises 7378 }
solitonTechnologiesCO             OBJECT IDENTIFIER ::= { enterprises 7379 }
shoreCorporation                  OBJECT IDENTIFIER ::= { enterprises 7380 }
owlOnlineGmbHAndCoKG              OBJECT IDENTIFIER ::= { enterprises 7381 }
justitSdnBhd                      OBJECT IDENTIFIER ::= { enterprises 7382 }
libertech                         OBJECT IDENTIFIER ::= { enterprises 7383 }
cryptotech                        OBJECT IDENTIFIER ::= { enterprises 7384 }
celoxNetworks                     OBJECT IDENTIFIER ::= { enterprises 7385 }
cakeFarm                          OBJECT IDENTIFIER ::= { enterprises 7386 }
canonInformationSystemsResearchAustralia OBJECT IDENTIFIER ::= { enterprises 7387 }
luneNetworks                      OBJECT IDENTIFIER ::= { enterprises 7388 }
vdslSystemsOy                     OBJECT IDENTIFIER ::= { enterprises 7389 }
grisoft                           OBJECT IDENTIFIER ::= { enterprises 7390 }
institutNationalDesTelecommunications OBJECT IDENTIFIER ::= { enterprises 7391 }
telispark                         OBJECT IDENTIFIER ::= { enterprises 7392 }
oasysTelecom                      OBJECT IDENTIFIER ::= { enterprises 7393 }
cosmocom2                         OBJECT IDENTIFIER ::= { enterprises 7394 }
beelineNetworks                   OBJECT IDENTIFIER ::= { enterprises 7395 }
olympoControls                    OBJECT IDENTIFIER ::= { enterprises 7396 }
onepage                           OBJECT IDENTIFIER ::= { enterprises 7397 }
corporation124                    OBJECT IDENTIFIER ::= { enterprises 7398 }
dataSystemsWest                   OBJECT IDENTIFIER ::= { enterprises 7399 }
ehiINSM                           OBJECT IDENTIFIER ::= { enterprises 7400 }
ekotacentral                      OBJECT IDENTIFIER ::= { enterprises 7401 }
vigorSoftPrivateLimited           OBJECT IDENTIFIER ::= { enterprises 7402 }
biomedTranslations                OBJECT IDENTIFIER ::= { enterprises 7403 }
djWilliamsEditorial               OBJECT IDENTIFIER ::= { enterprises 7404 }
ipsDoo                            OBJECT IDENTIFIER ::= { enterprises 7405 }
efsEtablisssement                 OBJECT IDENTIFIER ::= { enterprises 7406 }
observatoireDeBesancon            OBJECT IDENTIFIER ::= { enterprises 7407 }
kunskapstvISverigeAB              OBJECT IDENTIFIER ::= { enterprises 7408 }
janNiehusmann                     OBJECT IDENTIFIER ::= { enterprises 7409 }
telekursFinancial                 OBJECT IDENTIFIER ::= { enterprises 7410 }
finix                             OBJECT IDENTIFIER ::= { enterprises 7411 }
angstromMicrosystems              OBJECT IDENTIFIER ::= { enterprises 7412 }
computerServiceDepot              OBJECT IDENTIFIER ::= { enterprises 7413 }
muffettAndCo                      OBJECT IDENTIFIER ::= { enterprises 7414 }
berlinBrandenburgische            OBJECT IDENTIFIER ::= { enterprises 7415 }
softwareAdvancedTechnologyLab     OBJECT IDENTIFIER ::= { enterprises 7416 }
cornellUniversity                 OBJECT IDENTIFIER ::= { enterprises 7417 }
procketNetworks                   OBJECT IDENTIFIER ::= { enterprises 7418 }
daiHocSuPhamKyThuat               OBJECT IDENTIFIER ::= { enterprises 7419 }
taylorCompany                     OBJECT IDENTIFIER ::= { enterprises 7420 }
milcomSystemsCorporation          OBJECT IDENTIFIER ::= { enterprises 7421 }
currenex                          OBJECT IDENTIFIER ::= { enterprises 7422 }
medplus                           OBJECT IDENTIFIER ::= { enterprises 7423 }
infosecTechnologiesCo             OBJECT IDENTIFIER ::= { enterprises 7424 }
companyOfTheFarCountries          OBJECT IDENTIFIER ::= { enterprises 7425 }
nestInformationTechnologies       OBJECT IDENTIFIER ::= { enterprises 7426 }
yokogawaElectricCorporation       OBJECT IDENTIFIER ::= { enterprises 7427 }
powerdsine                        OBJECT IDENTIFIER ::= { enterprises 7428 }
broadwebCorporation               OBJECT IDENTIFIER ::= { enterprises 7429 }
mediascapeCommunicationsAG        OBJECT IDENTIFIER ::= { enterprises 7430 }
altivaSolutions                   OBJECT IDENTIFIER ::= { enterprises 7431 }
tcomlabsNV                        OBJECT IDENTIFIER ::= { enterprises 7432 }
sittiSpa                          OBJECT IDENTIFIER ::= { enterprises 7433 }
planetasia                        OBJECT IDENTIFIER ::= { enterprises 7434 }
tkCOMPANY                         OBJECT IDENTIFIER ::= { enterprises 7435 }
oxirInternetSolutions             OBJECT IDENTIFIER ::= { enterprises 7436 }
siemensICNItaly                   OBJECT IDENTIFIER ::= { enterprises 7437 }
safe                              OBJECT IDENTIFIER ::= { enterprises 7438 }
appstream                         OBJECT IDENTIFIER ::= { enterprises 7439 }
omnitechComputerCorp              OBJECT IDENTIFIER ::= { enterprises 7440 }
ciphertrust                       OBJECT IDENTIFIER ::= { enterprises 7441 }
idahoNationalEngineeringAndEnvironmentalLaboratory OBJECT IDENTIFIER ::= { enterprises 7442 }
everexCOMMUNICATION               OBJECT IDENTIFIER ::= { enterprises 7443 }
imagineNetworks                   OBJECT IDENTIFIER ::= { enterprises 7444 }
javelinaSoftware                  OBJECT IDENTIFIER ::= { enterprises 7445 }
instituteOfLeadershipAndManagement OBJECT IDENTIFIER ::= { enterprises 7446 }
signalTechnologyINC               OBJECT IDENTIFIER ::= { enterprises 7447 }
advancedTrainingAndConsultingServices OBJECT IDENTIFIER ::= { enterprises 7448 }
whamCOMPUTER                      OBJECT IDENTIFIER ::= { enterprises 7449 }
framfab                           OBJECT IDENTIFIER ::= { enterprises 7450 }
nsysTechnologiesCo                OBJECT IDENTIFIER ::= { enterprises 7451 }
guangzhouGaokeCommunicationEquipmentCo OBJECT IDENTIFIER ::= { enterprises 7452 }
turtlefootInternational           OBJECT IDENTIFIER ::= { enterprises 7453 }
oksystem                          OBJECT IDENTIFIER ::= { enterprises 7454 }
devConsultingGmbH                 OBJECT IDENTIFIER ::= { enterprises 7455 }
virtualNet                        OBJECT IDENTIFIER ::= { enterprises 7456 }
zaoEMAX                           OBJECT IDENTIFIER ::= { enterprises 7457 }
clemensBenden                     OBJECT IDENTIFIER ::= { enterprises 7458 }
memiq                             OBJECT IDENTIFIER ::= { enterprises 7459 }
xs4allInternetBV                  OBJECT IDENTIFIER ::= { enterprises 7460 }
pageOneAG                         OBJECT IDENTIFIER ::= { enterprises 7461 }
nordnorskHelsenett                OBJECT IDENTIFIER ::= { enterprises 7462 }
whitecell                         OBJECT IDENTIFIER ::= { enterprises 7463 }
ecmwf                             OBJECT IDENTIFIER ::= { enterprises 7464 }
wisi                              OBJECT IDENTIFIER ::= { enterprises 7465 }
cliGmbH                           OBJECT IDENTIFIER ::= { enterprises 7466 }
ttiSystems                        OBJECT IDENTIFIER ::= { enterprises 7467 }
mixbaal                           OBJECT IDENTIFIER ::= { enterprises 7468 }
voicegenieTechnologies            OBJECT IDENTIFIER ::= { enterprises 7469 }
princetonFinancialSystems         OBJECT IDENTIFIER ::= { enterprises 7470 }
discreetCommunicationsGroup       OBJECT IDENTIFIER ::= { enterprises 7471 }
mshowcom                          OBJECT IDENTIFIER ::= { enterprises 7472 }
easyplanetCorp                    OBJECT IDENTIFIER ::= { enterprises 7473 }
inabledOnline                     OBJECT IDENTIFIER ::= { enterprises 7474 }
shanghaiBellCompany               OBJECT IDENTIFIER ::= { enterprises 7475 }
departamentoGeneralDeIrrigacion   OBJECT IDENTIFIER ::= { enterprises 7476 }
unkSAArgentina                    OBJECT IDENTIFIER ::= { enterprises 7477 }
netcraftSdnBhd                    OBJECT IDENTIFIER ::= { enterprises 7478 }
triadDevelopmentGroupNA           OBJECT IDENTIFIER ::= { enterprises 7479 }
newNetworking                     OBJECT IDENTIFIER ::= { enterprises 7481 }
widaxCorporation                  OBJECT IDENTIFIER ::= { enterprises 7482 }
tropicNetworks                    OBJECT IDENTIFIER ::= { enterprises 7483 }
teleias2                          OBJECT IDENTIFIER ::= { enterprises 7484 }
sps                               OBJECT IDENTIFIER ::= { enterprises 7485 }
embassySystems                    OBJECT IDENTIFIER ::= { enterprises 7486 }
meisolutionscom                   OBJECT IDENTIFIER ::= { enterprises 7487 }
infinitecNetworks                 OBJECT IDENTIFIER ::= { enterprises 7488 }
eHealthSign                       OBJECT IDENTIFIER ::= { enterprises 7489 }
totalwisdom                       OBJECT IDENTIFIER ::= { enterprises 7490 }
gnumonksorg                       OBJECT IDENTIFIER ::= { enterprises 7491 }
kommunikationsnetzFrankenEV       OBJECT IDENTIFIER ::= { enterprises 7492 }
ldapAbook                         OBJECT IDENTIFIER ::= { enterprises 7493 }
rovorTechnologies                 OBJECT IDENTIFIER ::= { enterprises 7494 }
advancedWebSolutions              OBJECT IDENTIFIER ::= { enterprises 7495 }
jbHoldingBv                       OBJECT IDENTIFIER ::= { enterprises 7496 }
magnoliaBroadband                 OBJECT IDENTIFIER ::= { enterprises 7497 }
gorskinet                         OBJECT IDENTIFIER ::= { enterprises 7498 }
pacificCenturyCyberWorksHongkongTelecom OBJECT IDENTIFIER ::= { enterprises 7499 }
iics                              OBJECT IDENTIFIER ::= { enterprises 7500 }
nextream                          OBJECT IDENTIFIER ::= { enterprises 7501 }
africanMedicalImaging             OBJECT IDENTIFIER ::= { enterprises 7502 }
henkelsAndMcCoy                   OBJECT IDENTIFIER ::= { enterprises 7503 }
aersoft                           OBJECT IDENTIFIER ::= { enterprises 7504 }
calista                           OBJECT IDENTIFIER ::= { enterprises 7505 }
scorelineTechnologies             OBJECT IDENTIFIER ::= { enterprises 7506 }
wayneware                         OBJECT IDENTIFIER ::= { enterprises 7507 }
fujiElectricCo                    OBJECT IDENTIFIER ::= { enterprises 7508 }
storability                       OBJECT IDENTIFIER ::= { enterprises 7509 }
luxxonCorporation                 OBJECT IDENTIFIER ::= { enterprises 7510 }
wdt                               OBJECT IDENTIFIER ::= { enterprises 7511 }
netensCorporation                 OBJECT IDENTIFIER ::= { enterprises 7512 }
elimpexMedizintechnikGesmbH       OBJECT IDENTIFIER ::= { enterprises 7513 }
stHelensAndKnowsleyHospitalsNHSTrust OBJECT IDENTIFIER ::= { enterprises 7514 }
pLancier                          OBJECT IDENTIFIER ::= { enterprises 7515 }
andyStubbs                        OBJECT IDENTIFIER ::= { enterprises 7516 }
acxsysCorporation                 OBJECT IDENTIFIER ::= { enterprises 7517 }
chicagoMercantileExchange         OBJECT IDENTIFIER ::= { enterprises 7518 }
rateintegration                   OBJECT IDENTIFIER ::= { enterprises 7519 }
comNetEricsson                    OBJECT IDENTIFIER ::= { enterprises 7520 }
netstarNetworks                   OBJECT IDENTIFIER ::= { enterprises 7521 }
brainsCorp                        OBJECT IDENTIFIER ::= { enterprises 7522 }
accessnet                         OBJECT IDENTIFIER ::= { enterprises 7523 }
rapidsolutionSoftwareGmbH         OBJECT IDENTIFIER ::= { enterprises 7524 }
ecalCorporation                   OBJECT IDENTIFIER ::= { enterprises 7525 }
snomTechnologyAG                  OBJECT IDENTIFIER ::= { enterprises 7526 }
acropole                          OBJECT IDENTIFIER ::= { enterprises 7527 }
metabox                           OBJECT IDENTIFIER ::= { enterprises 7528 }
netarx                            OBJECT IDENTIFIER ::= { enterprises 7529 }
optxcon                           OBJECT IDENTIFIER ::= { enterprises 7530 }
rapidwan                          OBJECT IDENTIFIER ::= { enterprises 7531 }
munat                             OBJECT IDENTIFIER ::= { enterprises 7532 }
hondaELECTRONCO                   OBJECT IDENTIFIER ::= { enterprises 7533 }
universita                        OBJECT IDENTIFIER ::= { enterprises 7534 }
capclearLimited                   OBJECT IDENTIFIER ::= { enterprises 7535 }
hHZentrumFRechnerkommunikationGmbH OBJECT IDENTIFIER ::= { enterprises 7536 }
e2Communications                  OBJECT IDENTIFIER ::= { enterprises 7537 }
veripriseWirelessCompany          OBJECT IDENTIFIER ::= { enterprises 7538 }
quackcom                          OBJECT IDENTIFIER ::= { enterprises 7539 }
ispsoft                           OBJECT IDENTIFIER ::= { enterprises 7540 }
ibuildingcom                      OBJECT IDENTIFIER ::= { enterprises 7541 }
mountAllisonUniversity            OBJECT IDENTIFIER ::= { enterprises 7542 }
visionshop                        OBJECT IDENTIFIER ::= { enterprises 7543 }
wirelinkCo                        OBJECT IDENTIFIER ::= { enterprises 7544 }
qosbaSystemsCo                    OBJECT IDENTIFIER ::= { enterprises 7545 }
axxessitASA                       OBJECT IDENTIFIER ::= { enterprises 7546 }
csicRedIRIS                       OBJECT IDENTIFIER ::= { enterprises 7547 }
netcentricSystems                 OBJECT IDENTIFIER ::= { enterprises 7548 }
datacenterdirectcom               OBJECT IDENTIFIER ::= { enterprises 7549 }
deltaDataSoftware                 OBJECT IDENTIFIER ::= { enterprises 7550 }
enatel                            OBJECT IDENTIFIER ::= { enterprises 7551 }
infraValley                       OBJECT IDENTIFIER ::= { enterprises 7552 }
tampereUniversityOfTechnology     OBJECT IDENTIFIER ::= { enterprises 7553 }
zlooperMediaPerkasa               OBJECT IDENTIFIER ::= { enterprises 7554 }
institutionSaintJoseph            OBJECT IDENTIFIER ::= { enterprises 7555 }
movilogicSA                       OBJECT IDENTIFIER ::= { enterprises 7556 }
echomine                          OBJECT IDENTIFIER ::= { enterprises 7557 }
nationalAirTrafficServices        OBJECT IDENTIFIER ::= { enterprises 7558 }
egenera                           OBJECT IDENTIFIER ::= { enterprises 7559 }
trendCommunications               OBJECT IDENTIFIER ::= { enterprises 7560 }
askooSA                           OBJECT IDENTIFIER ::= { enterprises 7561 }
icpsr                             OBJECT IDENTIFIER ::= { enterprises 7562 }
onespot                           OBJECT IDENTIFIER ::= { enterprises 7563 }
clickarrrayNetworks               OBJECT IDENTIFIER ::= { enterprises 7564 }
usgsSouthFloridaInformationAccessProject OBJECT IDENTIFIER ::= { enterprises 7565 }
codestreamTechnologiesCorporation OBJECT IDENTIFIER ::= { enterprises 7566 }
porteraSystems                    OBJECT IDENTIFIER ::= { enterprises 7567 }
ircam                             OBJECT IDENTIFIER ::= { enterprises 7568 }
convediaCorporation               OBJECT IDENTIFIER ::= { enterprises 7569 }
brience                           OBJECT IDENTIFIER ::= { enterprises 7570 }
safTehnika                        OBJECT IDENTIFIER ::= { enterprises 7571 }
questSoftware                     OBJECT IDENTIFIER ::= { enterprises 7572 }
nbcInternet                       OBJECT IDENTIFIER ::= { enterprises 7573 }
torqueSystems                     OBJECT IDENTIFIER ::= { enterprises 7574 }
maharashtraInstituteOfTechnology  OBJECT IDENTIFIER ::= { enterprises 7575 }
geaITServicesGmbH                 OBJECT IDENTIFIER ::= { enterprises 7576 }
universityOfStrathclyde           OBJECT IDENTIFIER ::= { enterprises 7577 }
energisDeutschland                OBJECT IDENTIFIER ::= { enterprises 7578 }
universityOfFreiburg              OBJECT IDENTIFIER ::= { enterprises 7579 }
anixGroupLimited                  OBJECT IDENTIFIER ::= { enterprises 7580 }
adventNetworks                    OBJECT IDENTIFIER ::= { enterprises 7581 }
eZData                            OBJECT IDENTIFIER ::= { enterprises 7582 }
theEleven                         OBJECT IDENTIFIER ::= { enterprises 7583 }
intertrustTechnologiesCorporation OBJECT IDENTIFIER ::= { enterprises 7584 }
geniusSoftware                    OBJECT IDENTIFIER ::= { enterprises 7585 }
parametricTechnologyCorporation   OBJECT IDENTIFIER ::= { enterprises 7586 }
worldDigitelCorporation           OBJECT IDENTIFIER ::= { enterprises 7587 }
wisCOMMUNICATIONCOLTD             OBJECT IDENTIFIER ::= { enterprises 7588 }
memlink                           OBJECT IDENTIFIER ::= { enterprises 7589 }
bodachina                         OBJECT IDENTIFIER ::= { enterprises 7590 }
divisaInformaticaYTelecomunicacionesSA OBJECT IDENTIFIER ::= { enterprises 7591 }
swedishInstituteOfSpacePhysics    OBJECT IDENTIFIER ::= { enterprises 7592 }
universityOfCambridge2            OBJECT IDENTIFIER ::= { enterprises 7593 }
citadelInvestmentGroup            OBJECT IDENTIFIER ::= { enterprises 7594 }
ratioEntwicklungenGmbH            OBJECT IDENTIFIER ::= { enterprises 7595 }
trellisPhotonics                  OBJECT IDENTIFIER ::= { enterprises 7596 }
novaLJUBLJANSKABANKA              OBJECT IDENTIFIER ::= { enterprises 7597 }
ktsi                              OBJECT IDENTIFIER ::= { enterprises 7598 }
rebelcom                          OBJECT IDENTIFIER ::= { enterprises 7599 }
eazel                             OBJECT IDENTIFIER ::= { enterprises 7600 }
trinityCollege                    OBJECT IDENTIFIER ::= { enterprises 7601 }
coversde                          OBJECT IDENTIFIER ::= { enterprises 7602 }
kingfisherICTServices             OBJECT IDENTIFIER ::= { enterprises 7603 }
mseIT                             OBJECT IDENTIFIER ::= { enterprises 7604 }
ePointSA                          OBJECT IDENTIFIER ::= { enterprises 7605 }
theUniversityOfAlabamaInHuntsville OBJECT IDENTIFIER ::= { enterprises 7606 }
appgate                           OBJECT IDENTIFIER ::= { enterprises 7607 }
celionNetworks                    OBJECT IDENTIFIER ::= { enterprises 7608 }
spinstate                         OBJECT IDENTIFIER ::= { enterprises 7609 }
something4                        OBJECT IDENTIFIER ::= { enterprises 7610 }
federalReserveSystem              OBJECT IDENTIFIER ::= { enterprises 7611 }
digiDataCorp                      OBJECT IDENTIFIER ::= { enterprises 7612 }
pantherSoftware                   OBJECT IDENTIFIER ::= { enterprises 7613 }
isovia                            OBJECT IDENTIFIER ::= { enterprises 7614 }
universitatDeGirona               OBJECT IDENTIFIER ::= { enterprises 7615 }
stmicroelectronics                OBJECT IDENTIFIER ::= { enterprises 7616 }
stendahlsnetAB                    OBJECT IDENTIFIER ::= { enterprises 7617 }
adomo                             OBJECT IDENTIFIER ::= { enterprises 7618 }
amonTechnologies                  OBJECT IDENTIFIER ::= { enterprises 7619 }
franceTeaser                      OBJECT IDENTIFIER ::= { enterprises 7620 }
echostarCorporation               OBJECT IDENTIFIER ::= { enterprises 7621 }
mesaSystemsInternational          OBJECT IDENTIFIER ::= { enterprises 7622 }
dxoTelecomCo                      OBJECT IDENTIFIER ::= { enterprises 7623 }
akalSystems                       OBJECT IDENTIFIER ::= { enterprises 7624 }
comconGmbH                        OBJECT IDENTIFIER ::= { enterprises 7625 }
universityOfOsnabrueck            OBJECT IDENTIFIER ::= { enterprises 7626 }
telebroadNetworks                 OBJECT IDENTIFIER ::= { enterprises 7627 }
reedMatthews                      OBJECT IDENTIFIER ::= { enterprises 7628 }
unet                              OBJECT IDENTIFIER ::= { enterprises 7629 }
tiogaTechnologies                 OBJECT IDENTIFIER ::= { enterprises 7630 }
interfaceCONCEPT                  OBJECT IDENTIFIER ::= { enterprises 7631 }
gns                               OBJECT IDENTIFIER ::= { enterprises 7632 }
cityUniversity                    OBJECT IDENTIFIER ::= { enterprises 7633 }
bungeeCommunications              OBJECT IDENTIFIER ::= { enterprises 7634 }
thomsonMultimediaRAndDFrance      OBJECT IDENTIFIER ::= { enterprises 7635 }
laponiaVeiculos                   OBJECT IDENTIFIER ::= { enterprises 7636 }
jpmConsulting                     OBJECT IDENTIFIER ::= { enterprises 7637 }
carrier1                          OBJECT IDENTIFIER ::= { enterprises 7638 }
netverkSA                         OBJECT IDENTIFIER ::= { enterprises 7639 }
quantumCorp                       OBJECT IDENTIFIER ::= { enterprises 7640 }
astronomicalSocietyOfEdinburgh    OBJECT IDENTIFIER ::= { enterprises 7641 }
spidertechSoftwarePvt             OBJECT IDENTIFIER ::= { enterprises 7642 }
nationalChungChengUniversity      OBJECT IDENTIFIER ::= { enterprises 7643 }
ekGroeinkaufEG                    OBJECT IDENTIFIER ::= { enterprises 7644 }
netxl                             OBJECT IDENTIFIER ::= { enterprises 7645 }
exemus                            OBJECT IDENTIFIER ::= { enterprises 7646 }
oreganNetworks                    OBJECT IDENTIFIER ::= { enterprises 7647 }
nationwideMutualInsuranceCompany  OBJECT IDENTIFIER ::= { enterprises 7648 }
everfile                          OBJECT IDENTIFIER ::= { enterprises 7649 }
leibnizRechenzentrum              OBJECT IDENTIFIER ::= { enterprises 7650 }
unisecurity                       OBJECT IDENTIFIER ::= { enterprises 7651 }
datacoreSoftwareCorporation       OBJECT IDENTIFIER ::= { enterprises 7652 }
dashbit                           OBJECT IDENTIFIER ::= { enterprises 7653 }
snonet                            OBJECT IDENTIFIER ::= { enterprises 7654 }
seanKelly                         OBJECT IDENTIFIER ::= { enterprises 7655 }
bertrandtAG                       OBJECT IDENTIFIER ::= { enterprises 7656 }
disatSISTEMASTELECOMUNICACIoN     OBJECT IDENTIFIER ::= { enterprises 7657 }
webonomicsGmbH                    OBJECT IDENTIFIER ::= { enterprises 7658 }
uestc                             OBJECT IDENTIFIER ::= { enterprises 7659 }
okiokData                         OBJECT IDENTIFIER ::= { enterprises 7660 }
dcsAG                             OBJECT IDENTIFIER ::= { enterprises 7661 }
sogetek                           OBJECT IDENTIFIER ::= { enterprises 7662 }
taralNetworks                     OBJECT IDENTIFIER ::= { enterprises 7663 }
mezzonetEasyTechnologieSL         OBJECT IDENTIFIER ::= { enterprises 7664 }
intriaHPCorp                      OBJECT IDENTIFIER ::= { enterprises 7665 }
advECommerce                      OBJECT IDENTIFIER ::= { enterprises 7666 }
banqueNationaleDuCanada           OBJECT IDENTIFIER ::= { enterprises 7667 }
praeterTechnologies               OBJECT IDENTIFIER ::= { enterprises 7668 }
networkPhotonics                  OBJECT IDENTIFIER ::= { enterprises 7669 }
viator                            OBJECT IDENTIFIER ::= { enterprises 7670 }
invertixCorporation               OBJECT IDENTIFIER ::= { enterprises 7671 }
fujitsuNNC                        OBJECT IDENTIFIER ::= { enterprises 7672 }
fusionCommunicationsCorp          OBJECT IDENTIFIER ::= { enterprises 7673 }
northernPrincipleLimited          OBJECT IDENTIFIER ::= { enterprises 7674 }
sparHandelsAG                     OBJECT IDENTIFIER ::= { enterprises 7675 }
strawberrySoftwareLimited         OBJECT IDENTIFIER ::= { enterprises 7676 }
lynxPhotonicNetworks              OBJECT IDENTIFIER ::= { enterprises 7677 }
xyrius                            OBJECT IDENTIFIER ::= { enterprises 7678 }
winagcom                          OBJECT IDENTIFIER ::= { enterprises 7679 }
corrigentSystems                  OBJECT IDENTIFIER ::= { enterprises 7680 }
trakonic                          OBJECT IDENTIFIER ::= { enterprises 7681 }
ncipherPLC                        OBJECT IDENTIFIER ::= { enterprises 7682 }
airLiquideElectronics             OBJECT IDENTIFIER ::= { enterprises 7683 }
nextoneCommunications             OBJECT IDENTIFIER ::= { enterprises 7684 }
kpmgConsulting                    OBJECT IDENTIFIER ::= { enterprises 7685 }
pechesEtOceansCanadaGardeCotiere  OBJECT IDENTIFIER ::= { enterprises 7686 }
ufscLabSEC                        OBJECT IDENTIFIER ::= { enterprises 7687 }
socialChangeOnline                OBJECT IDENTIFIER ::= { enterprises 7688 }
rasimusi                          OBJECT IDENTIFIER ::= { enterprises 7689 }
thrupoint                         OBJECT IDENTIFIER ::= { enterprises 7690 }
warpSolutions                     OBJECT IDENTIFIER ::= { enterprises 7691 }
theStoddardGroup                  OBJECT IDENTIFIER ::= { enterprises 7692 }
internationalLifeSciencesInstitute OBJECT IDENTIFIER ::= { enterprises 7693 }
summitTechnologies                OBJECT IDENTIFIER ::= { enterprises 7694 }
mediaCloud                        OBJECT IDENTIFIER ::= { enterprises 7695 }
bachSystems                       OBJECT IDENTIFIER ::= { enterprises 7696 }
athabascaUniversity               OBJECT IDENTIFIER ::= { enterprises 7697 }
contextMedia                      OBJECT IDENTIFIER ::= { enterprises 7698 }
syncwaveNetworks                  OBJECT IDENTIFIER ::= { enterprises 7699 }
endeavorsTechnology               OBJECT IDENTIFIER ::= { enterprises 7700 }
gemstoneSystems                   OBJECT IDENTIFIER ::= { enterprises 7701 }
keicho                            OBJECT IDENTIFIER ::= { enterprises 7702 }
ecrio                             OBJECT IDENTIFIER ::= { enterprises 7703 }
derPolizeipraesidentInBerlin      OBJECT IDENTIFIER ::= { enterprises 7704 }
centreForWirelessCommunications   OBJECT IDENTIFIER ::= { enterprises 7705 }
joncolcom                         OBJECT IDENTIFIER ::= { enterprises 7706 }
proactiveTechnologyLimited        OBJECT IDENTIFIER ::= { enterprises 7707 }
wydeband                          OBJECT IDENTIFIER ::= { enterprises 7708 }
aristotleUniversityOfThessaloniki OBJECT IDENTIFIER ::= { enterprises 7709 }
agrilis                           OBJECT IDENTIFIER ::= { enterprises 7710 }
gnkc                              OBJECT IDENTIFIER ::= { enterprises 7711 }
secartisAG                        OBJECT IDENTIFIER ::= { enterprises 7712 }
tomorrowTechnologiesMarcusRating  OBJECT IDENTIFIER ::= { enterprises 7713 }
evidian                           OBJECT IDENTIFIER ::= { enterprises 7714 }
eyeCommunicationsAG               OBJECT IDENTIFIER ::= { enterprises 7715 }
artSpA                            OBJECT IDENTIFIER ::= { enterprises 7716 }
flyingJ                           OBJECT IDENTIFIER ::= { enterprises 7717 }
ina                               OBJECT IDENTIFIER ::= { enterprises 7718 }
avilinks                          OBJECT IDENTIFIER ::= { enterprises 7719 }
wiSimonson                        OBJECT IDENTIFIER ::= { enterprises 7720 }
dmsDigitaleMedienSystemeAG        OBJECT IDENTIFIER ::= { enterprises 7721 }
netLinxPsSii                      OBJECT IDENTIFIER ::= { enterprises 7722 }
benhamnet                         OBJECT IDENTIFIER ::= { enterprises 7723 }
trailbreakercom                   OBJECT IDENTIFIER ::= { enterprises 7724 }
harkTowerSystems                  OBJECT IDENTIFIER ::= { enterprises 7725 }
pointgainCorporation              OBJECT IDENTIFIER ::= { enterprises 7726 }
cinNIC                            OBJECT IDENTIFIER ::= { enterprises 7727 }
threeR                            OBJECT IDENTIFIER ::= { enterprises 7728 }
telson                            OBJECT IDENTIFIER ::= { enterprises 7729 }
voxpathNetworks                   OBJECT IDENTIFIER ::= { enterprises 7730 }
homestorecom                      OBJECT IDENTIFIER ::= { enterprises 7731 }
philiplo                          OBJECT IDENTIFIER ::= { enterprises 7732 }
pulsarTechnologies                OBJECT IDENTIFIER ::= { enterprises 7733 }
avianCommunications               OBJECT IDENTIFIER ::= { enterprises 7734 }
airbiquity                        OBJECT IDENTIFIER ::= { enterprises 7735 }
jarna                             OBJECT IDENTIFIER ::= { enterprises 7736 }
internetPhotonics                 OBJECT IDENTIFIER ::= { enterprises 7737 }
encendraCommunications            OBJECT IDENTIFIER ::= { enterprises 7738 }
digencp                           OBJECT IDENTIFIER ::= { enterprises 7739 }
netmongerCommunicationsChristopherMasto OBJECT IDENTIFIER ::= { enterprises 7740 }
snmpTechnologies                  OBJECT IDENTIFIER ::= { enterprises 7741 }
antithesysPty                     OBJECT IDENTIFIER ::= { enterprises 7742 }
salomonSmithBarney                OBJECT IDENTIFIER ::= { enterprises 7743 }
speSystemhausGmbH                 OBJECT IDENTIFIER ::= { enterprises 7744 }
aethra                            OBJECT IDENTIFIER ::= { enterprises 7745 }
watershedConsultants              OBJECT IDENTIFIER ::= { enterprises 7746 }
federation                        OBJECT IDENTIFIER ::= { enterprises 7747 }
globecomInteractive               OBJECT IDENTIFIER ::= { enterprises 7748 }
hicom                             OBJECT IDENTIFIER ::= { enterprises 7749 }
heliconNetworks                   OBJECT IDENTIFIER ::= { enterprises 7750 }
mdiversity                        OBJECT IDENTIFIER ::= { enterprises 7751 }
bravidaCorporation                OBJECT IDENTIFIER ::= { enterprises 7752 }
zelpos                            OBJECT IDENTIFIER ::= { enterprises 7753 }
infosquareCorp                    OBJECT IDENTIFIER ::= { enterprises 7754 }
waltDisneyInternetGroup           OBJECT IDENTIFIER ::= { enterprises 7755 }
netarenaCommunications            OBJECT IDENTIFIER ::= { enterprises 7756 }
tonbu                             OBJECT IDENTIFIER ::= { enterprises 7757 }
eBUSINESSNETWORKCOM               OBJECT IDENTIFIER ::= { enterprises 7758 }
eenaducom                         OBJECT IDENTIFIER ::= { enterprises 7759 }
anyscapecom                       OBJECT IDENTIFIER ::= { enterprises 7760 }
pointgocom                        OBJECT IDENTIFIER ::= { enterprises 7761 }
ebizxmlcom                        OBJECT IDENTIFIER ::= { enterprises 7762 }
pointgainnet                      OBJECT IDENTIFIER ::= { enterprises 7763 }
ebusinessxchangecom               OBJECT IDENTIFIER ::= { enterprises 7764 }
sysdynamicscom                    OBJECT IDENTIFIER ::= { enterprises 7765 }
businessacrosscom                 OBJECT IDENTIFIER ::= { enterprises 7766 }
ebusinessopenworldcom             OBJECT IDENTIFIER ::= { enterprises 7767 }
eBUSINESSOPENWORLDCOM             OBJECT IDENTIFIER ::= { enterprises 7768 }
eBUSINESSOPENWORLDNET             OBJECT IDENTIFIER ::= { enterprises 7769 }
ebusinessopenworldnet             OBJECT IDENTIFIER ::= { enterprises 7770 }
ebusinessacrosscom                OBJECT IDENTIFIER ::= { enterprises 7771 }
ebizdynamicscom                   OBJECT IDENTIFIER ::= { enterprises 7772 }
eBUSINESSDYNAMICSCOM              OBJECT IDENTIFIER ::= { enterprises 7773 }
ebusinessxcom                     OBJECT IDENTIFIER ::= { enterprises 7774 }
eDYNAMICSCOM                      OBJECT IDENTIFIER ::= { enterprises 7775 }
eDYNAMICSNET                      OBJECT IDENTIFIER ::= { enterprises 7776 }
eDYNAMICSORG                      OBJECT IDENTIFIER ::= { enterprises 7777 }
excessTradeZone                   OBJECT IDENTIFIER ::= { enterprises 7778 }
infoblox                          OBJECT IDENTIFIER ::= { enterprises 7779 }
mirametric                        OBJECT IDENTIFIER ::= { enterprises 7780 }
conservatoireNationalDesArtsEtMetiers OBJECT IDENTIFIER ::= { enterprises 7781 }
greekSchoolNetwork                OBJECT IDENTIFIER ::= { enterprises 7782 }
rielloSpA                         OBJECT IDENTIFIER ::= { enterprises 7783 }
lattisEnterpriseManagement        OBJECT IDENTIFIER ::= { enterprises 7784 }
rivneCommunicationTechnologies    OBJECT IDENTIFIER ::= { enterprises 7785 }
ibcnet                            OBJECT IDENTIFIER ::= { enterprises 7786 }
frontsiteAG                       OBJECT IDENTIFIER ::= { enterprises 7787 }
liebregts                         OBJECT IDENTIFIER ::= { enterprises 7788 }
lpmOnline                         OBJECT IDENTIFIER ::= { enterprises 7789 }
lisitLombardiaIntegrataServiziInfotelematiciPerIl OBJECT IDENTIFIER ::= { enterprises 7790 }
conseilGeneralDeLaLoire           OBJECT IDENTIFIER ::= { enterprises 7791 }
incshopkorea                      OBJECT IDENTIFIER ::= { enterprises 7792 }
hms                               OBJECT IDENTIFIER ::= { enterprises 7793 }
infinityTelData                   OBJECT IDENTIFIER ::= { enterprises 7794 }
customSoftwareSolutions           OBJECT IDENTIFIER ::= { enterprises 7795 }
bowdengsTechnoloiges              OBJECT IDENTIFIER ::= { enterprises 7796 }
aculeus                           OBJECT IDENTIFIER ::= { enterprises 7797 }
tokoElectricCo                    OBJECT IDENTIFIER ::= { enterprises 7798 }
thePacificRoot                    OBJECT IDENTIFIER ::= { enterprises 7799 }
premierNetworkCo                  OBJECT IDENTIFIER ::= { enterprises 7800 }
radionetOy                        OBJECT IDENTIFIER ::= { enterprises 7801 }
limited                           OBJECT IDENTIFIER ::= { enterprises 7802 }
terraNetworksBrasilSA             OBJECT IDENTIFIER ::= { enterprises 7803 }
elcanCorp                         OBJECT IDENTIFIER ::= { enterprises 7804 }
netnationCommunications           OBJECT IDENTIFIER ::= { enterprises 7805 }
techsar                           OBJECT IDENTIFIER ::= { enterprises 7806 }
stoneware                         OBJECT IDENTIFIER ::= { enterprises 7807 }
reardenSteelTechnologies          OBJECT IDENTIFIER ::= { enterprises 7808 }
finchComputerServices             OBJECT IDENTIFIER ::= { enterprises 7809 }
seekSystems                       OBJECT IDENTIFIER ::= { enterprises 7810 }
streetRecords                     OBJECT IDENTIFIER ::= { enterprises 7811 }
pfadiLimmattal                    OBJECT IDENTIFIER ::= { enterprises 7812 }
cogetecHSI                        OBJECT IDENTIFIER ::= { enterprises 7813 }
infinityTelData2                  OBJECT IDENTIFIER ::= { enterprises 7814 }
gilmoreHouseAssociates            OBJECT IDENTIFIER ::= { enterprises 7815 }
wissenschaftladenDortmundEV       OBJECT IDENTIFIER ::= { enterprises 7816 }
chipheadConsulting                OBJECT IDENTIFIER ::= { enterprises 7817 }
rohitCommunicationsPte            OBJECT IDENTIFIER ::= { enterprises 7818 }
opensourceConsult                 OBJECT IDENTIFIER ::= { enterprises 7819 }
configate                         OBJECT IDENTIFIER ::= { enterprises 7820 }
universityOfSilesia               OBJECT IDENTIFIER ::= { enterprises 7821 }
athenaSecurity                    OBJECT IDENTIFIER ::= { enterprises 7822 }
clickaction                       OBJECT IDENTIFIER ::= { enterprises 7823 }
lgElectronics                     OBJECT IDENTIFIER ::= { enterprises 7824 }
cognizantTechnologySolutions      OBJECT IDENTIFIER ::= { enterprises 7825 }
kpnqwestAustriaGmbH               OBJECT IDENTIFIER ::= { enterprises 7826 }
sofadexPuratos                    OBJECT IDENTIFIER ::= { enterprises 7827 }
commsblokecom                     OBJECT IDENTIFIER ::= { enterprises 7828 }
axonDigitalDesignBV               OBJECT IDENTIFIER ::= { enterprises 7829 }
serviceInfoTechno                 OBJECT IDENTIFIER ::= { enterprises 7830 }
dataflexDesignCommunicationsLimited OBJECT IDENTIFIER ::= { enterprises 7831 }
icsaLabs                          OBJECT IDENTIFIER ::= { enterprises 7832 }
davebnet                          OBJECT IDENTIFIER ::= { enterprises 7833 }
wissenschaftsladenDortmundEV      OBJECT IDENTIFIER ::= { enterprises 7834 }
hopeTranportation                 OBJECT IDENTIFIER ::= { enterprises 7835 }
nuarkCo                           OBJECT IDENTIFIER ::= { enterprises 7836 }
sumtelCommunications              OBJECT IDENTIFIER ::= { enterprises 7837 }
utomiAG                           OBJECT IDENTIFIER ::= { enterprises 7838 }
teliaUKLimited                    OBJECT IDENTIFIER ::= { enterprises 7839 }
zelax                             OBJECT IDENTIFIER ::= { enterprises 7840 }
skynet                            OBJECT IDENTIFIER ::= { enterprises 7841 }
universiteParis12ValDeMarne       OBJECT IDENTIFIER ::= { enterprises 7842 }
callera                           OBJECT IDENTIFIER ::= { enterprises 7843 }
kgbEntertainment                  OBJECT IDENTIFIER ::= { enterprises 7844 }
cipher                            OBJECT IDENTIFIER ::= { enterprises 7845 }
etrali                            OBJECT IDENTIFIER ::= { enterprises 7846 }
theEvangelicalLutheranGoodSamaritanSociety OBJECT IDENTIFIER ::= { enterprises 7847 }
sachsischeStaatskanzlei           OBJECT IDENTIFIER ::= { enterprises 7848 }
commeceoneAuctionServices         OBJECT IDENTIFIER ::= { enterprises 7849 }
penfordCorporation                OBJECT IDENTIFIER ::= { enterprises 7850 }
softwareMunitions                 OBJECT IDENTIFIER ::= { enterprises 7851 }
cyberelves                        OBJECT IDENTIFIER ::= { enterprises 7852 }
teknoids                          OBJECT IDENTIFIER ::= { enterprises 7853 }
nazit                             OBJECT IDENTIFIER ::= { enterprises 7854 }
isiCNR                            OBJECT IDENTIFIER ::= { enterprises 7855 }
realtronic                        OBJECT IDENTIFIER ::= { enterprises 7856 }
xenosite                          OBJECT IDENTIFIER ::= { enterprises 7857 }
outcomeTechnologyAssociates       OBJECT IDENTIFIER ::= { enterprises 7858 }
netmount                          OBJECT IDENTIFIER ::= { enterprises 7859 }
datatone                          OBJECT IDENTIFIER ::= { enterprises 7860 }
degree2Innovations                OBJECT IDENTIFIER ::= { enterprises 7861 }
herrnsPC                          OBJECT IDENTIFIER ::= { enterprises 7862 }
freew3                            OBJECT IDENTIFIER ::= { enterprises 7863 }
megadotPty                        OBJECT IDENTIFIER ::= { enterprises 7864 }
litnetNOC                         OBJECT IDENTIFIER ::= { enterprises 7865 }
corinthianEngineeringPty          OBJECT IDENTIFIER ::= { enterprises 7866 }
mailvision2                       OBJECT IDENTIFIER ::= { enterprises 7867 }
universiteDeSherbrooke            OBJECT IDENTIFIER ::= { enterprises 7868 }
byzantiumSolutions                OBJECT IDENTIFIER ::= { enterprises 7869 }
polskaPlatformaInternetowa        OBJECT IDENTIFIER ::= { enterprises 7870 }
nicsysGbR                         OBJECT IDENTIFIER ::= { enterprises 7871 }
arristaTechnologies               OBJECT IDENTIFIER ::= { enterprises 7872 }
infoOnscreenSoftwareSystemsPty    OBJECT IDENTIFIER ::= { enterprises 7873 }
highlandInjectionMolding          OBJECT IDENTIFIER ::= { enterprises 7874 }
shibauraInstituteOfTechnology     OBJECT IDENTIFIER ::= { enterprises 7875 }
statensVegvesen                   OBJECT IDENTIFIER ::= { enterprises 7876 }
basefarmAS                        OBJECT IDENTIFIER ::= { enterprises 7877 }
theUniversityOfTheSouthPacific    OBJECT IDENTIFIER ::= { enterprises 7878 }
tTeleSec                          OBJECT IDENTIFIER ::= { enterprises 7879 }
pecoII2                           OBJECT IDENTIFIER ::= { enterprises 7880 }
cognitasTechnologies              OBJECT IDENTIFIER ::= { enterprises 7881 }
cityOfPrescottITDepartment        OBJECT IDENTIFIER ::= { enterprises 7882 }
amirkcom                          OBJECT IDENTIFIER ::= { enterprises 7883 }
francisWParkerSchool              OBJECT IDENTIFIER ::= { enterprises 7884 }
arekDreyer                        OBJECT IDENTIFIER ::= { enterprises 7885 }
kApplication                      OBJECT IDENTIFIER ::= { enterprises 7886 }
ncube                             OBJECT IDENTIFIER ::= { enterprises 7887 }
iambaTechnologiesLTD              OBJECT IDENTIFIER ::= { enterprises 7888 }
lingnanUniversity                 OBJECT IDENTIFIER ::= { enterprises 7889 }
arrowElectronics                  OBJECT IDENTIFIER ::= { enterprises 7890 }
confederationOfNorwegianBusinessAndIndustry OBJECT IDENTIFIER ::= { enterprises 7891 }
lannertde                         OBJECT IDENTIFIER ::= { enterprises 7892 }
yacomInternetFactorySA            OBJECT IDENTIFIER ::= { enterprises 7893 }
vanconetSro                       OBJECT IDENTIFIER ::= { enterprises 7894 }
amethonSolutions                  OBJECT IDENTIFIER ::= { enterprises 7895 }
rietumuBanka                      OBJECT IDENTIFIER ::= { enterprises 7896 }
knowledgeBaseBV                   OBJECT IDENTIFIER ::= { enterprises 7897 }
openetTelecom                     OBJECT IDENTIFIER ::= { enterprises 7898 }
capGemini                         OBJECT IDENTIFIER ::= { enterprises 7899 }
neubergerAndHughesGmbH            OBJECT IDENTIFIER ::= { enterprises 7900 }
capiro                            OBJECT IDENTIFIER ::= { enterprises 7901 }
albertaWellnet                    OBJECT IDENTIFIER ::= { enterprises 7902 }
ecoprog                           OBJECT IDENTIFIER ::= { enterprises 7903 }
greenwichCapitalMarkets           OBJECT IDENTIFIER ::= { enterprises 7904 }
nationalTrainingInstitute         OBJECT IDENTIFIER ::= { enterprises 7905 }
brainworkersSrl                   OBJECT IDENTIFIER ::= { enterprises 7906 }
allianceRaceCarBuilders           OBJECT IDENTIFIER ::= { enterprises 7907 }
telsoftSolutions                  OBJECT IDENTIFIER ::= { enterprises 7908 }
americanCommunicationTechnologiesInternational OBJECT IDENTIFIER ::= { enterprises 7909 }
csts                              OBJECT IDENTIFIER ::= { enterprises 7910 }
dreamintekCo                      OBJECT IDENTIFIER ::= { enterprises 7911 }
staffwarePLC                      OBJECT IDENTIFIER ::= { enterprises 7912 }
spaceHellasSA                     OBJECT IDENTIFIER ::= { enterprises 7913 }
qmailLdapProject                  OBJECT IDENTIFIER ::= { enterprises 7914 }
cetevoAB                          OBJECT IDENTIFIER ::= { enterprises 7915 }
page                              OBJECT IDENTIFIER ::= { enterprises 7916 }
areaDeCienciasDeLaComputacionEInteligenciaArtificial OBJECT IDENTIFIER ::= { enterprises 7917 }
electrosonic                      OBJECT IDENTIFIER ::= { enterprises 7918 }
spyn                              OBJECT IDENTIFIER ::= { enterprises 7919 }
nationalEducationAssociationOfTheUnitedStates OBJECT IDENTIFIER ::= { enterprises 7920 }
aethyrnetSoluitions               OBJECT IDENTIFIER ::= { enterprises 7921 }
spiroKommunikation                OBJECT IDENTIFIER ::= { enterprises 7922 }
organetGmbH                       OBJECT IDENTIFIER ::= { enterprises 7923 }
bundesamtFuerSicherheitInDerInformationstechnik OBJECT IDENTIFIER ::= { enterprises 7924 }
specsGmbHSurfaceAnalysisAndComputerTechnology OBJECT IDENTIFIER ::= { enterprises 7925 }
universitaireInstellingAntwerpen  OBJECT IDENTIFIER ::= { enterprises 7926 }
splendidInternetGmbH              OBJECT IDENTIFIER ::= { enterprises 7927 }
wysdom                            OBJECT IDENTIFIER ::= { enterprises 7928 }
halifaxPLC                        OBJECT IDENTIFIER ::= { enterprises 7929 }
telecomArgentina                  OBJECT IDENTIFIER ::= { enterprises 7930 }
smcc                              OBJECT IDENTIFIER ::= { enterprises 7931 }
amerinet                          OBJECT IDENTIFIER ::= { enterprises 7932 }
promiseTechnology                 OBJECT IDENTIFIER ::= { enterprises 7933 }
shanghaiJiaoTongUniversity        OBJECT IDENTIFIER ::= { enterprises 7934 }
ivt                               OBJECT IDENTIFIER ::= { enterprises 7935 }
yangjaeMICRO                      OBJECT IDENTIFIER ::= { enterprises 7936 }
inpactTechnologies                OBJECT IDENTIFIER ::= { enterprises 7937 }
iee                               OBJECT IDENTIFIER ::= { enterprises 7938 }
lisconGmbH                        OBJECT IDENTIFIER ::= { enterprises 7939 }
celeritas                         OBJECT IDENTIFIER ::= { enterprises 7940 }
tecnica6000SL                     OBJECT IDENTIFIER ::= { enterprises 7941 }
xtempus                           OBJECT IDENTIFIER ::= { enterprises 7942 }
homeWirelessNetworks              OBJECT IDENTIFIER ::= { enterprises 7943 }
pennylan                          OBJECT IDENTIFIER ::= { enterprises 7944 }
umbBank                           OBJECT IDENTIFIER ::= { enterprises 7945 }
flashpointTechnology              OBJECT IDENTIFIER ::= { enterprises 7946 }
mspTechnolgies                    OBJECT IDENTIFIER ::= { enterprises 7947 }
dasirENTERPRISES                  OBJECT IDENTIFIER ::= { enterprises 7948 }
broadcloudCommunications          OBJECT IDENTIFIER ::= { enterprises 7949 }
overtureNetworks                  OBJECT IDENTIFIER ::= { enterprises 7950 }
cnctc                             OBJECT IDENTIFIER ::= { enterprises 7951 }
tooCorporation                    OBJECT IDENTIFIER ::= { enterprises 7952 }
chaosLabs                         OBJECT IDENTIFIER ::= { enterprises 7953 }
siemensBusinessServicesAS         OBJECT IDENTIFIER ::= { enterprises 7954 }
alfaskopAB                        OBJECT IDENTIFIER ::= { enterprises 7955 }
initioITLosningerAS               OBJECT IDENTIFIER ::= { enterprises 7956 }
laresTechnology                   OBJECT IDENTIFIER ::= { enterprises 7957 }
efficientChannelCoding            OBJECT IDENTIFIER ::= { enterprises 7958 }
gabrielRoman                      OBJECT IDENTIFIER ::= { enterprises 7959 }
freerein                          OBJECT IDENTIFIER ::= { enterprises 7960 }
harryLStyron                      OBJECT IDENTIFIER ::= { enterprises 7961 }
notAnotherCorporation             OBJECT IDENTIFIER ::= { enterprises 7962 }
tebie                             OBJECT IDENTIFIER ::= { enterprises 7963 }
masterComunicacaoEMarketing       OBJECT IDENTIFIER ::= { enterprises 7964 }
ingenieurbueroTartsch             OBJECT IDENTIFIER ::= { enterprises 7965 }
spyInternetworking                OBJECT IDENTIFIER ::= { enterprises 7966 }
tekbabble                         OBJECT IDENTIFIER ::= { enterprises 7967 }
spearheadTechnologies             OBJECT IDENTIFIER ::= { enterprises 7968 }
becomm                            OBJECT IDENTIFIER ::= { enterprises 7969 }
athelonCorporation                OBJECT IDENTIFIER ::= { enterprises 7970 }
networkDigitaleAS                 OBJECT IDENTIFIER ::= { enterprises 7971 }
xingtangCommunicationTechnologyCo OBJECT IDENTIFIER ::= { enterprises 7972 }
telefonicaDEESPAnA                OBJECT IDENTIFIER ::= { enterprises 7973 }
turbomeca                         OBJECT IDENTIFIER ::= { enterprises 7974 }
arkEManagement                    OBJECT IDENTIFIER ::= { enterprises 7975 }
brotsmanAndDreger                 OBJECT IDENTIFIER ::= { enterprises 7976 }
vidsoftGmbH                       OBJECT IDENTIFIER ::= { enterprises 7977 }
franceTelecomHosting              OBJECT IDENTIFIER ::= { enterprises 7978 }
storigenSystems                   OBJECT IDENTIFIER ::= { enterprises 7979 }
sistemasYAplicacionesDeTelecomunicacionesSA OBJECT IDENTIFIER ::= { enterprises 7980 }
interbind                         OBJECT IDENTIFIER ::= { enterprises 7981 }
theSimonShapiroFoundation         OBJECT IDENTIFIER ::= { enterprises 7982 }
hpeb                              OBJECT IDENTIFIER ::= { enterprises 7983 }
ticketMasterCitySearchCorp        OBJECT IDENTIFIER ::= { enterprises 7984 }
universityOfCatania               OBJECT IDENTIFIER ::= { enterprises 7985 }
ipaccess                          OBJECT IDENTIFIER ::= { enterprises 7986 }
universiteDePauEtDesPaysDeL       OBJECT IDENTIFIER ::= { enterprises 7987 }
universiteNancy2                  OBJECT IDENTIFIER ::= { enterprises 7988 }
imag                              OBJECT IDENTIFIER ::= { enterprises 7989 }
eoiTechnologies                   OBJECT IDENTIFIER ::= { enterprises 7990 }
elawcom                           OBJECT IDENTIFIER ::= { enterprises 7991 }
prfd                              OBJECT IDENTIFIER ::= { enterprises 7992 }
factoritSpA                       OBJECT IDENTIFIER ::= { enterprises 7993 }
continuousComputingCorp           OBJECT IDENTIFIER ::= { enterprises 7994 }
snellAndWilcox                    OBJECT IDENTIFIER ::= { enterprises 7995 }
electricPowerResearchInstitute    OBJECT IDENTIFIER ::= { enterprises 7996 }
ballCorporation                   OBJECT IDENTIFIER ::= { enterprises 7997 }
mailfriday                        OBJECT IDENTIFIER ::= { enterprises 7998 }
tpInternet                        OBJECT IDENTIFIER ::= { enterprises 7999 }
ipace                             OBJECT IDENTIFIER ::= { enterprises 8000 }
keytrendTechnologyLimited         OBJECT IDENTIFIER ::= { enterprises 8001 }
architechAS                       OBJECT IDENTIFIER ::= { enterprises 8002 }
swisscomIPPlus                    OBJECT IDENTIFIER ::= { enterprises 8003 }
midGmbH                           OBJECT IDENTIFIER ::= { enterprises 8004 }
physicsDepartment                 OBJECT IDENTIFIER ::= { enterprises 8005 }
einsteinetGmbH                    OBJECT IDENTIFIER ::= { enterprises 8006 }
hbsSolutions                      OBJECT IDENTIFIER ::= { enterprises 8007 }
pactolusCommunicationSoftware     OBJECT IDENTIFIER ::= { enterprises 8008 }
isecuritas                        OBJECT IDENTIFIER ::= { enterprises 8009 }
exanet                            OBJECT IDENTIFIER ::= { enterprises 8010 }
mckeeFoodsCorporation             OBJECT IDENTIFIER ::= { enterprises 8011 }
hyperdriveSistemas                OBJECT IDENTIFIER ::= { enterprises 8012 }
nextlevelcomInternetProductions   OBJECT IDENTIFIER ::= { enterprises 8013 }
stoneflyNetworks                  OBJECT IDENTIFIER ::= { enterprises 8014 }
airocon                           OBJECT IDENTIFIER ::= { enterprises 8015 }
ravensbourneCollegeOfDesignAndCom OBJECT IDENTIFIER ::= { enterprises 8016 }
primusCanada                      OBJECT IDENTIFIER ::= { enterprises 8017 }
hogeschoolVanArnhemEnNijmegen     OBJECT IDENTIFIER ::= { enterprises 8018 }
theStellarIceCompany              OBJECT IDENTIFIER ::= { enterprises 8019 }
ecoleNormaleSuperieureDeLyon      OBJECT IDENTIFIER ::= { enterprises 8020 }
gAEnterprises                     OBJECT IDENTIFIER ::= { enterprises 8021 }
senetsBroadband                   OBJECT IDENTIFIER ::= { enterprises 8022 }
infocruiser                       OBJECT IDENTIFIER ::= { enterprises 8023 }
quovadisLimited                   OBJECT IDENTIFIER ::= { enterprises 8024 }
friendlyworks                     OBJECT IDENTIFIER ::= { enterprises 8025 }
rockbrookSystemsGroup             OBJECT IDENTIFIER ::= { enterprises 8026 }
binhostcom                        OBJECT IDENTIFIER ::= { enterprises 8027 }
cast                              OBJECT IDENTIFIER ::= { enterprises 8028 }
dctc                              OBJECT IDENTIFIER ::= { enterprises 8029 }
prakashCottonMills                OBJECT IDENTIFIER ::= { enterprises 8030 }
universityLibraryOfKassel         OBJECT IDENTIFIER ::= { enterprises 8031 }
agendaDoo                         OBJECT IDENTIFIER ::= { enterprises 8032 }
almende                           OBJECT IDENTIFIER ::= { enterprises 8033 }
rohillTechnologiesBV              OBJECT IDENTIFIER ::= { enterprises 8034 }
ryEnterprises                     OBJECT IDENTIFIER ::= { enterprises 8035 }
usanet                            OBJECT IDENTIFIER ::= { enterprises 8036 }
colomarGroup                      OBJECT IDENTIFIER ::= { enterprises 8037 }
homebaseWorkSolutions             OBJECT IDENTIFIER ::= { enterprises 8038 }
sillyAnts                         OBJECT IDENTIFIER ::= { enterprises 8039 }
thunderSystems                    OBJECT IDENTIFIER ::= { enterprises 8040 }
hostwayCorporation                OBJECT IDENTIFIER ::= { enterprises 8041 }
ecellTechnologies                 OBJECT IDENTIFIER ::= { enterprises 8042 }
proactivemonitoring               OBJECT IDENTIFIER ::= { enterprises 8043 }
mjDuCheneAndAssociates            OBJECT IDENTIFIER ::= { enterprises 8044 }
glenLewis                         OBJECT IDENTIFIER ::= { enterprises 8045 }
utahJavaUserGroup                 OBJECT IDENTIFIER ::= { enterprises 8046 }
osedu                             OBJECT IDENTIFIER ::= { enterprises 8047 }
avatarInternetServices            OBJECT IDENTIFIER ::= { enterprises 8048 }
netaccess                         OBJECT IDENTIFIER ::= { enterprises 8049 }
rissTelecom                       OBJECT IDENTIFIER ::= { enterprises 8050 }
michaelMcCafferty                 OBJECT IDENTIFIER ::= { enterprises 8051 }
tessernetSystems                  OBJECT IDENTIFIER ::= { enterprises 8052 }
islingtonAve                      OBJECT IDENTIFIER ::= { enterprises 8053 }
theScanShopPty                    OBJECT IDENTIFIER ::= { enterprises 8054 }
optilinkTechnologiesCompanyLimited OBJECT IDENTIFIER ::= { enterprises 8055 }
shenyangNEUALPINESOFTWARECO       OBJECT IDENTIFIER ::= { enterprises 8056 }
cesnet                            OBJECT IDENTIFIER ::= { enterprises 8057 }
messagevine                       OBJECT IDENTIFIER ::= { enterprises 8058 }
netToNetTechnologies              OBJECT IDENTIFIER ::= { enterprises 8059 }
armstrongAtlanticStateUniversity  OBJECT IDENTIFIER ::= { enterprises 8060 }
multipointCommunications          OBJECT IDENTIFIER ::= { enterprises 8061 }
colormaxInteractive               OBJECT IDENTIFIER ::= { enterprises 8062 }
m                                 OBJECT IDENTIFIER ::= { enterprises 8063 }
globalTechnologySolutions         OBJECT IDENTIFIER ::= { enterprises 8064 }
uniTerUnderwritingManagementCorporation OBJECT IDENTIFIER ::= { enterprises 8065 }
watchmarkCorporation              OBJECT IDENTIFIER ::= { enterprises 8066 }
worldcomGenDXPM                   OBJECT IDENTIFIER ::= { enterprises 8067 }
buffaloRockCompany                OBJECT IDENTIFIER ::= { enterprises 8068 }
rozzEnterprises                   OBJECT IDENTIFIER ::= { enterprises 8069 }
zerohypeTechnologies              OBJECT IDENTIFIER ::= { enterprises 8070 }
sandstormEnterprises              OBJECT IDENTIFIER ::= { enterprises 8071 }
netSnmp                           OBJECT IDENTIFIER ::= { enterprises 8072 }
lumosTechnologies                 OBJECT IDENTIFIER ::= { enterprises 8073 }
boxSolutionsCorporation           OBJECT IDENTIFIER ::= { enterprises 8074 }
lateralConceptsAndDesigns         OBJECT IDENTIFIER ::= { enterprises 8075 }
siemensPSEAustria                 OBJECT IDENTIFIER ::= { enterprises 8076 }
chambersignFrance                 OBJECT IDENTIFIER ::= { enterprises 8077 }
inuConsultancy                    OBJECT IDENTIFIER ::= { enterprises 8078 }
ensoportcom                       OBJECT IDENTIFIER ::= { enterprises 8079 }
fastwebSpA                        OBJECT IDENTIFIER ::= { enterprises 8080 }
magnumSolutions                   OBJECT IDENTIFIER ::= { enterprises 8081 }
sangateSystems                    OBJECT IDENTIFIER ::= { enterprises 8082 }
packetDesign                      OBJECT IDENTIFIER ::= { enterprises 8083 }
tangalieuorg                      OBJECT IDENTIFIER ::= { enterprises 8084 }
ironstream                        OBJECT IDENTIFIER ::= { enterprises 8085 }
nuasisCorporation                 OBJECT IDENTIFIER ::= { enterprises 8086 }
tiernext                          OBJECT IDENTIFIER ::= { enterprises 8087 }
dcsi                              OBJECT IDENTIFIER ::= { enterprises 8088 }
covadCommunications               OBJECT IDENTIFIER ::= { enterprises 8089 }
enterpriseComputingServices       OBJECT IDENTIFIER ::= { enterprises 8090 }
ipSoft                            OBJECT IDENTIFIER ::= { enterprises 8091 }
elgoMariborDoo                    OBJECT IDENTIFIER ::= { enterprises 8092 }
aliroo                            OBJECT IDENTIFIER ::= { enterprises 8093 }
dreamartsCorp                     OBJECT IDENTIFIER ::= { enterprises 8094 }
--                                OBJECT IDENTIFIER ::= { enterprises 8095 }
theVoiceTechnologyForum           OBJECT IDENTIFIER ::= { enterprises 8096 }
servicom2000                      OBJECT IDENTIFIER ::= { enterprises 8097 }
moratGames                        OBJECT IDENTIFIER ::= { enterprises 8098 }
alexWilsonColdstream              OBJECT IDENTIFIER ::= { enterprises 8099 }
softricity                        OBJECT IDENTIFIER ::= { enterprises 8100 }
zambeel                           OBJECT IDENTIFIER ::= { enterprises 8101 }
markMorganEnterprises             OBJECT IDENTIFIER ::= { enterprises 8102 }
winstechnetCo                     OBJECT IDENTIFIER ::= { enterprises 8103 }
sunMicrosystemsProfessionalServices OBJECT IDENTIFIER ::= { enterprises 8104 }
appilog                           OBJECT IDENTIFIER ::= { enterprises 8105 }
luxmateControlsGmbH               OBJECT IDENTIFIER ::= { enterprises 8106 }
kabira                            OBJECT IDENTIFIER ::= { enterprises 8107 }
vhi                               OBJECT IDENTIFIER ::= { enterprises 8108 }
priceExpress                      OBJECT IDENTIFIER ::= { enterprises 8109 }
messageCentralPlc                 OBJECT IDENTIFIER ::= { enterprises 8110 }
pacificTradeAndTechnology         OBJECT IDENTIFIER ::= { enterprises 8111 }
greenShieldCanada                 OBJECT IDENTIFIER ::= { enterprises 8112 }
bellanetInternationalSecretariat  OBJECT IDENTIFIER ::= { enterprises 8113 }
navalAmmunitionLogisticsCenter    OBJECT IDENTIFIER ::= { enterprises 8114 }
birchTelecom                      OBJECT IDENTIFIER ::= { enterprises 8115 }
danwareDataAS                     OBJECT IDENTIFIER ::= { enterprises 8116 }
nafem                             OBJECT IDENTIFIER ::= { enterprises 8117 }
capitolSystemsCorporation         OBJECT IDENTIFIER ::= { enterprises 8118 }
missionValleyRegionalOccupationalProgram OBJECT IDENTIFIER ::= { enterprises 8119 }
transvirtualTechnologies          OBJECT IDENTIFIER ::= { enterprises 8120 }
ridgewaySystemsAndSoftware        OBJECT IDENTIFIER ::= { enterprises 8121 }
kbImpulsServiceGmbH               OBJECT IDENTIFIER ::= { enterprises 8122 }
kompetenznetzMaligneLymphome      OBJECT IDENTIFIER ::= { enterprises 8123 }
carrefour                         OBJECT IDENTIFIER ::= { enterprises 8124 }
internetServices                  OBJECT IDENTIFIER ::= { enterprises 8125 }
myDocsOnline                      OBJECT IDENTIFIER ::= { enterprises 8126 }
effinityLabs                      OBJECT IDENTIFIER ::= { enterprises 8127 }
boco2                             OBJECT IDENTIFIER ::= { enterprises 8128 }
jadebirdHuaGuang                  OBJECT IDENTIFIER ::= { enterprises 8129 }
heimannBiometricSystemsGmbH       OBJECT IDENTIFIER ::= { enterprises 8130 }
gloryTelecomCo                    OBJECT IDENTIFIER ::= { enterprises 8131 }
nasikWeldingProductsPvt           OBJECT IDENTIFIER ::= { enterprises 8132 }
fsscLondon                        OBJECT IDENTIFIER ::= { enterprises 8133 }
insitel                           OBJECT IDENTIFIER ::= { enterprises 8134 }
andongNationalUniversity          OBJECT IDENTIFIER ::= { enterprises 8135 }
centrulDePregatireInInformatica   OBJECT IDENTIFIER ::= { enterprises 8136 }
palisadeSystems                   OBJECT IDENTIFIER ::= { enterprises 8137 }
deRoeckSoftwareEngineeringBVBA    OBJECT IDENTIFIER ::= { enterprises 8138 }
aaxionSoftwareCorporation         OBJECT IDENTIFIER ::= { enterprises 8139 }
c2Technologies                    OBJECT IDENTIFIER ::= { enterprises 8140 }
kashpureffBolingLaboratories      OBJECT IDENTIFIER ::= { enterprises 8141 }
hcaTheHealthcareCompany           OBJECT IDENTIFIER ::= { enterprises 8142 }
ictv                              OBJECT IDENTIFIER ::= { enterprises 8143 }
fiberxon                          OBJECT IDENTIFIER ::= { enterprises 8144 }
universityOfSalzburg              OBJECT IDENTIFIER ::= { enterprises 8145 }
snakegully                        OBJECT IDENTIFIER ::= { enterprises 8146 }
mercuryTelecommunications         OBJECT IDENTIFIER ::= { enterprises 8147 }
niragongoTechnologies             OBJECT IDENTIFIER ::= { enterprises 8148 }
generalitatValenciana             OBJECT IDENTIFIER ::= { enterprises 8149 }
secaronAG                         OBJECT IDENTIFIER ::= { enterprises 8150 }
worldwebnet                       OBJECT IDENTIFIER ::= { enterprises 8151 }
viair                             OBJECT IDENTIFIER ::= { enterprises 8152 }
jguildInternation                 OBJECT IDENTIFIER ::= { enterprises 8153 }
riserManagementSystems            OBJECT IDENTIFIER ::= { enterprises 8154 }
transcept                         OBJECT IDENTIFIER ::= { enterprises 8155 }
agencyworks                       OBJECT IDENTIFIER ::= { enterprises 8156 }
syncomNetwork                     OBJECT IDENTIFIER ::= { enterprises 8157 }
mspLUB                            OBJECT IDENTIFIER ::= { enterprises 8158 }
shinSATELLITEPUBLICCOMPANY        OBJECT IDENTIFIER ::= { enterprises 8159 }
digitalPlatformSupportServices    OBJECT IDENTIFIER ::= { enterprises 8160 }
starHomeGMBH                      OBJECT IDENTIFIER ::= { enterprises 8161 }
dexia                             OBJECT IDENTIFIER ::= { enterprises 8162 }
doubleDElectronics                OBJECT IDENTIFIER ::= { enterprises 8163 }
starentNetworks                   OBJECT IDENTIFIER ::= { enterprises 8164 }
boutemycom                        OBJECT IDENTIFIER ::= { enterprises 8165 }
viagInterkom                      OBJECT IDENTIFIER ::= { enterprises 8166 }
transversal                       OBJECT IDENTIFIER ::= { enterprises 8167 }
nectarcom                         OBJECT IDENTIFIER ::= { enterprises 8168 }
carrollLutheranVillage            OBJECT IDENTIFIER ::= { enterprises 8169 }
monitorGroup                      OBJECT IDENTIFIER ::= { enterprises 8170 }
oniSolutions                      OBJECT IDENTIFIER ::= { enterprises 8171 }
johnsHopkinsUniversity            OBJECT IDENTIFIER ::= { enterprises 8172 }
indraSistemas                     OBJECT IDENTIFIER ::= { enterprises 8173 }
netburner                         OBJECT IDENTIFIER ::= { enterprises 8174 }
carrier9Networks                  OBJECT IDENTIFIER ::= { enterprises 8175 }
astrodesign                       OBJECT IDENTIFIER ::= { enterprises 8176 }
hclCommunications                 OBJECT IDENTIFIER ::= { enterprises 8177 }
justInnovativeSoftwareGmbH        OBJECT IDENTIFIER ::= { enterprises 8178 }
--                                OBJECT IDENTIFIER ::= { enterprises 8179 }
spirea                            OBJECT IDENTIFIER ::= { enterprises 8180 }
scholzAndFriendsDresdenGmbH       OBJECT IDENTIFIER ::= { enterprises 8181 }
theBostonBitCo                    OBJECT IDENTIFIER ::= { enterprises 8182 }
netsourceAmerica                  OBJECT IDENTIFIER ::= { enterprises 8183 }
inspiraSL                         OBJECT IDENTIFIER ::= { enterprises 8184 }
onlineCreation                    OBJECT IDENTIFIER ::= { enterprises 8185 }
californiaInstituteOfTechnology   OBJECT IDENTIFIER ::= { enterprises 8186 }
sharingaNetworks                  OBJECT IDENTIFIER ::= { enterprises 8187 }
winterthurVersicherungen          OBJECT IDENTIFIER ::= { enterprises 8188 }
gerichhausen                      OBJECT IDENTIFIER ::= { enterprises 8189 }
quante                            OBJECT IDENTIFIER ::= { enterprises 8190 }
glutamat                          OBJECT IDENTIFIER ::= { enterprises 8191 }
symbiontNetworks                  OBJECT IDENTIFIER ::= { enterprises 8192 }
telemetryTechnologies             OBJECT IDENTIFIER ::= { enterprises 8193 }
targetnetcom                      OBJECT IDENTIFIER ::= { enterprises 8194 }
effinityNet                       OBJECT IDENTIFIER ::= { enterprises 8195 }
teldarCorporation                 OBJECT IDENTIFIER ::= { enterprises 8196 }
learningsoftCorp                  OBJECT IDENTIFIER ::= { enterprises 8197 }
ebuilt                            OBJECT IDENTIFIER ::= { enterprises 8198 }
--                                OBJECT IDENTIFIER ::= { enterprises 8199 }
unnatiCOMPUTERS                   OBJECT IDENTIFIER ::= { enterprises 8200 }
xcelaronPty                       OBJECT IDENTIFIER ::= { enterprises 8201 }
toroAssicurazioniSpA              OBJECT IDENTIFIER ::= { enterprises 8202 }
lpgInnovations                    OBJECT IDENTIFIER ::= { enterprises 8203 }
cymtecSystems                     OBJECT IDENTIFIER ::= { enterprises 8204 }
agentspring                       OBJECT IDENTIFIER ::= { enterprises 8205 }
--                                OBJECT IDENTIFIER ::= { enterprises 8206 }
integratus                        OBJECT IDENTIFIER ::= { enterprises 8207 }
bestWesternInternational          OBJECT IDENTIFIER ::= { enterprises 8208 }
centegy                           OBJECT IDENTIFIER ::= { enterprises 8210 }
shenzhenTCLCommunicationTech      OBJECT IDENTIFIER ::= { enterprises 8211 }
harbourNetworksCo                 OBJECT IDENTIFIER ::= { enterprises 8212 }
facultyOfMedicine                 OBJECT IDENTIFIER ::= { enterprises 8213 }
atomica                           OBJECT IDENTIFIER ::= { enterprises 8214 }
authentified                      OBJECT IDENTIFIER ::= { enterprises 8215 }
cyzenTech                         OBJECT IDENTIFIER ::= { enterprises 8216 }
slaonlinecom                      OBJECT IDENTIFIER ::= { enterprises 8217 }
ecErdoelchemieGmbH                OBJECT IDENTIFIER ::= { enterprises 8218 }
ecomda                            OBJECT IDENTIFIER ::= { enterprises 8219 }
tclHoldingsCo                     OBJECT IDENTIFIER ::= { enterprises 8220 }
baeSYSTEMS3                       OBJECT IDENTIFIER ::= { enterprises 8221 }
matthewWhite                      OBJECT IDENTIFIER ::= { enterprises 8222 }
atlasCommerce                     OBJECT IDENTIFIER ::= { enterprises 8223 }
aero9                             OBJECT IDENTIFIER ::= { enterprises 8224 }
openConnectAG                     OBJECT IDENTIFIER ::= { enterprises 8225 }
giganewscom                       OBJECT IDENTIFIER ::= { enterprises 8226 }
cyberobjectCorp                   OBJECT IDENTIFIER ::= { enterprises 8227 }
jalanNetworkServices              OBJECT IDENTIFIER ::= { enterprises 8228 }
philSystems                       OBJECT IDENTIFIER ::= { enterprises 8229 }
ringROSAProductsBv                OBJECT IDENTIFIER ::= { enterprises 8230 }
lineo                             OBJECT IDENTIFIER ::= { enterprises 8231 }
fachhochschuleGiessenFriedberg    OBJECT IDENTIFIER ::= { enterprises 8232 }
ibasis                            OBJECT IDENTIFIER ::= { enterprises 8233 }
ecetInternational                 OBJECT IDENTIFIER ::= { enterprises 8234 }
cenitAGSystemhaus                 OBJECT IDENTIFIER ::= { enterprises 8235 }
whiteHorseInteractive             OBJECT IDENTIFIER ::= { enterprises 8236 }
nccGmbH                           OBJECT IDENTIFIER ::= { enterprises 8237 }
lutheranBrotherhood               OBJECT IDENTIFIER ::= { enterprises 8238 }
peribitNetworks                   OBJECT IDENTIFIER ::= { enterprises 8239 }
path1                             OBJECT IDENTIFIER ::= { enterprises 8240 }
securantTechnologies              OBJECT IDENTIFIER ::= { enterprises 8241 }
securityPortal                    OBJECT IDENTIFIER ::= { enterprises 8242 }
ipass2                            OBJECT IDENTIFIER ::= { enterprises 8243 }
saneraSystems                     OBJECT IDENTIFIER ::= { enterprises 8244 }
vsovt                             OBJECT IDENTIFIER ::= { enterprises 8245 }
cistronInternetServices           OBJECT IDENTIFIER ::= { enterprises 8246 }
universityOfRostock               OBJECT IDENTIFIER ::= { enterprises 8247 }
turinNetworks                     OBJECT IDENTIFIER ::= { enterprises 8248 }
vereinFurComputergenealogieEV     OBJECT IDENTIFIER ::= { enterprises 8249 }
shirenetLLC                       OBJECT IDENTIFIER ::= { enterprises 8250 }
iigaCo                            OBJECT IDENTIFIER ::= { enterprises 8251 }
digitalStrategies                 OBJECT IDENTIFIER ::= { enterprises 8252 }
awolartcom                        OBJECT IDENTIFIER ::= { enterprises 8253 }
alephNull                         OBJECT IDENTIFIER ::= { enterprises 8254 }
tejasNetworks                     OBJECT IDENTIFIER ::= { enterprises 8255 }
solutionTheComputerPeopleEK       OBJECT IDENTIFIER ::= { enterprises 8256 }
southernUralStateUniversity       OBJECT IDENTIFIER ::= { enterprises 8257 }
kukSystemprogrammierung           OBJECT IDENTIFIER ::= { enterprises 8258 }
bancoDeSabadell                   OBJECT IDENTIFIER ::= { enterprises 8259 }
intrexaCorp                       OBJECT IDENTIFIER ::= { enterprises 8260 }
mediacast                         OBJECT IDENTIFIER ::= { enterprises 8261 }
wavion                            OBJECT IDENTIFIER ::= { enterprises 8262 }
jambyBV                           OBJECT IDENTIFIER ::= { enterprises 8263 }
recreativosFranco                 OBJECT IDENTIFIER ::= { enterprises 8264 }
entradaNetworks                   OBJECT IDENTIFIER ::= { enterprises 8265 }
intelnetSA                        OBJECT IDENTIFIER ::= { enterprises 8266 }
arulaSystems                      OBJECT IDENTIFIER ::= { enterprises 8267 }
markTippetts                      OBJECT IDENTIFIER ::= { enterprises 8268 }
cjscMalva                         OBJECT IDENTIFIER ::= { enterprises 8269 }
mjlTechnology                     OBJECT IDENTIFIER ::= { enterprises 8270 }
fachhochschuleVorarlberg          OBJECT IDENTIFIER ::= { enterprises 8271 }
nameplanet                        OBJECT IDENTIFIER ::= { enterprises 8272 }
standardCommunications            OBJECT IDENTIFIER ::= { enterprises 8273 }
interadnet                        OBJECT IDENTIFIER ::= { enterprises 8274 }
insaToulouse                      OBJECT IDENTIFIER ::= { enterprises 8275 }
mpathix                           OBJECT IDENTIFIER ::= { enterprises 8276 }
pscITSolutionsNET                 OBJECT IDENTIFIER ::= { enterprises 8277 }
stElisabethGmbH                   OBJECT IDENTIFIER ::= { enterprises 8278 }
f3pu5net                          OBJECT IDENTIFIER ::= { enterprises 8279 }
fiverLightComCo                   OBJECT IDENTIFIER ::= { enterprises 8280 }
movelife                          OBJECT IDENTIFIER ::= { enterprises 8281 }
tenixDefenceSystemsSystems        OBJECT IDENTIFIER ::= { enterprises 8282 }
tsmtMagicTouch                    OBJECT IDENTIFIER ::= { enterprises 8283 }
actl                              OBJECT IDENTIFIER ::= { enterprises 8284 }
flexlight                         OBJECT IDENTIFIER ::= { enterprises 8285 }
incirco                           OBJECT IDENTIFIER ::= { enterprises 8286 }
--                                OBJECT IDENTIFIER ::= { enterprises 8287 }
jungVonMattWerbeagenturGmbH       OBJECT IDENTIFIER ::= { enterprises 8288 }
universita2                       OBJECT IDENTIFIER ::= { enterprises 8289 }
certusTechnology                  OBJECT IDENTIFIER ::= { enterprises 8290 }
digistamp                         OBJECT IDENTIFIER ::= { enterprises 8291 }
mtHolyokeCollege                  OBJECT IDENTIFIER ::= { enterprises 8292 }
bangNetworks                      OBJECT IDENTIFIER ::= { enterprises 8293 }
infoman                           OBJECT IDENTIFIER ::= { enterprises 8294 }
bwa                               OBJECT IDENTIFIER ::= { enterprises 8295 }
dialogos3Srl                      OBJECT IDENTIFIER ::= { enterprises 8296 }
irisonlinecomBV                   OBJECT IDENTIFIER ::= { enterprises 8297 }
vHNictoglobe                      OBJECT IDENTIFIER ::= { enterprises 8298 }
secunetSecurityNetworksAG         OBJECT IDENTIFIER ::= { enterprises 8299 }
stateOfWisconsinTomBrei           OBJECT IDENTIFIER ::= { enterprises 8300 }
tuDarmstadt                       OBJECT IDENTIFIER ::= { enterprises 8301 }
edenetCommunications              OBJECT IDENTIFIER ::= { enterprises 8302 }
gelcoInformationNetwork           OBJECT IDENTIFIER ::= { enterprises 8303 }
atomicBlueBear                    OBJECT IDENTIFIER ::= { enterprises 8304 }
oarnet                            OBJECT IDENTIFIER ::= { enterprises 8305 }
goLocalConsulting                 OBJECT IDENTIFIER ::= { enterprises 8306 }
tecnetdev                         OBJECT IDENTIFIER ::= { enterprises 8307 }
gtran                             OBJECT IDENTIFIER ::= { enterprises 8308 }
virtelaCommunications             OBJECT IDENTIFIER ::= { enterprises 8309 }
trakSystems                       OBJECT IDENTIFIER ::= { enterprises 8310 }
policeInformationTechnologyOrg    OBJECT IDENTIFIER ::= { enterprises 8311 }
oskolnetJSC                       OBJECT IDENTIFIER ::= { enterprises 8312 }
jardixAG                          OBJECT IDENTIFIER ::= { enterprises 8313 }
peusSystemsGmbH                   OBJECT IDENTIFIER ::= { enterprises 8314 }
minacomLabs                       OBJECT IDENTIFIER ::= { enterprises 8315 }
staffwell                         OBJECT IDENTIFIER ::= { enterprises 8316 }
fibercycleNetworks                OBJECT IDENTIFIER ::= { enterprises 8317 }
twistedPairSolutions              OBJECT IDENTIFIER ::= { enterprises 8318 }
blueWaveSystems                   OBJECT IDENTIFIER ::= { enterprises 8319 }
vonovaCorporation                 OBJECT IDENTIFIER ::= { enterprises 8320 }
acec                              OBJECT IDENTIFIER ::= { enterprises 8321 }
educationNetworksOfAmerica        OBJECT IDENTIFIER ::= { enterprises 8322 }
gemteqSoftware                    OBJECT IDENTIFIER ::= { enterprises 8323 }
theUniversityOfWesternAustralia   OBJECT IDENTIFIER ::= { enterprises 8324 }
wanadooSpain                      OBJECT IDENTIFIER ::= { enterprises 8325 }
unrealTechnologySpolSRo           OBJECT IDENTIFIER ::= { enterprises 8326 }
iufmReims                         OBJECT IDENTIFIER ::= { enterprises 8327 }
gydIberica                        OBJECT IDENTIFIER ::= { enterprises 8328 }
ipromogroup                       OBJECT IDENTIFIER ::= { enterprises 8329 }
omnexusNV                         OBJECT IDENTIFIER ::= { enterprises 8330 }
mattiValtuustoon                  OBJECT IDENTIFIER ::= { enterprises 8331 }
--                                OBJECT IDENTIFIER ::= { enterprises 8332 }
growco                            OBJECT IDENTIFIER ::= { enterprises 8333 }
dynamicsoft                       OBJECT IDENTIFIER ::= { enterprises 8334 }
--                                OBJECT IDENTIFIER ::= { enterprises 8335 }
superiorConsultantHoldingsCorp    OBJECT IDENTIFIER ::= { enterprises 8336 }
hybriconCorp                      OBJECT IDENTIFIER ::= { enterprises 8337 }
phonetics                         OBJECT IDENTIFIER ::= { enterprises 8338 }
youngAndLaramore                  OBJECT IDENTIFIER ::= { enterprises 8339 }
imageComputing                    OBJECT IDENTIFIER ::= { enterprises 8340 }
utilityDataSystems                OBJECT IDENTIFIER ::= { enterprises 8341 }
ntruCryptosystems                 OBJECT IDENTIFIER ::= { enterprises 8342 }
nextraCzechRepublicSro            OBJECT IDENTIFIER ::= { enterprises 8343 }
apparateNetworks                  OBJECT IDENTIFIER ::= { enterprises 8344 }
healthNet                         OBJECT IDENTIFIER ::= { enterprises 8345 }
--                                OBJECT IDENTIFIER ::= { enterprises 8346 }
technocage                        OBJECT IDENTIFIER ::= { enterprises 8347 }
dataAvenue                        OBJECT IDENTIFIER ::= { enterprises 8348 }
connectscape                      OBJECT IDENTIFIER ::= { enterprises 8349 }
debisITServicesUnisoftwareKft     OBJECT IDENTIFIER ::= { enterprises 8350 }
iLandInternetServices             OBJECT IDENTIFIER ::= { enterprises 8351 }
pronymSARL                        OBJECT IDENTIFIER ::= { enterprises 8352 }
excelsiorSystemsLimited           OBJECT IDENTIFIER ::= { enterprises 8353 }
gib                               OBJECT IDENTIFIER ::= { enterprises 8354 }
sarfata                           OBJECT IDENTIFIER ::= { enterprises 8355 }
visualRevolutions                 OBJECT IDENTIFIER ::= { enterprises 8356 }
mangosoftCorporation              OBJECT IDENTIFIER ::= { enterprises 8357 }
telosTechnology                   OBJECT IDENTIFIER ::= { enterprises 8358 }
ipBlue                            OBJECT IDENTIFIER ::= { enterprises 8359 }
mirantCorporation                 OBJECT IDENTIFIER ::= { enterprises 8360 }
portailDesIUFM                    OBJECT IDENTIFIER ::= { enterprises 8361 }
msafe                             OBJECT IDENTIFIER ::= { enterprises 8362 }
storeOMatic                       OBJECT IDENTIFIER ::= { enterprises 8363 }
lichenHosting                     OBJECT IDENTIFIER ::= { enterprises 8364 }
advancedInformationManagement     OBJECT IDENTIFIER ::= { enterprises 8365 }
fiberlinkCommunications           OBJECT IDENTIFIER ::= { enterprises 8366 }
nationnetcom                      OBJECT IDENTIFIER ::= { enterprises 8367 }
boarderlessTechnologies           OBJECT IDENTIFIER ::= { enterprises 8368 }
ntikorea                          OBJECT IDENTIFIER ::= { enterprises 8369 }
nextset                           OBJECT IDENTIFIER ::= { enterprises 8370 }
agenda                            OBJECT IDENTIFIER ::= { enterprises 8371 }
universityOfSussex                OBJECT IDENTIFIER ::= { enterprises 8372 }
seppAGAndCoKG                     OBJECT IDENTIFIER ::= { enterprises 8373 }
--                                OBJECT IDENTIFIER ::= { enterprises 8374 }
outercurveTechnologies            OBJECT IDENTIFIER ::= { enterprises 8375 }
universiteDeBourgogne             OBJECT IDENTIFIER ::= { enterprises 8376 }
reefedge                          OBJECT IDENTIFIER ::= { enterprises 8377 }
texasMemorySystems                OBJECT IDENTIFIER ::= { enterprises 8378 }
broadriverCommunications          OBJECT IDENTIFIER ::= { enterprises 8379 }
mentumGroup                       OBJECT IDENTIFIER ::= { enterprises 8380 }
certaintySolutions                OBJECT IDENTIFIER ::= { enterprises 8381 }
cAndcEngineering                  OBJECT IDENTIFIER ::= { enterprises 8382 }
sigmasoft                         OBJECT IDENTIFIER ::= { enterprises 8383 }
ebay                              OBJECT IDENTIFIER ::= { enterprises 8384 }
ensamCERDeMetz                    OBJECT IDENTIFIER ::= { enterprises 8385 }
lionBioscienceAG                  OBJECT IDENTIFIER ::= { enterprises 8386 }
globeInternetSro                  OBJECT IDENTIFIER ::= { enterprises 8387 }
technikerKrankenkasse             OBJECT IDENTIFIER ::= { enterprises 8388 }
ergonInformatik                   OBJECT IDENTIFIER ::= { enterprises 8389 }
mettlerToledo                     OBJECT IDENTIFIER ::= { enterprises 8390 }
bicmanNetologies                  OBJECT IDENTIFIER ::= { enterprises 8391 }
xmission                          OBJECT IDENTIFIER ::= { enterprises 8392 }
gimasMbH                          OBJECT IDENTIFIER ::= { enterprises 8393 }
privadorAS                        OBJECT IDENTIFIER ::= { enterprises 8394 }
tulaneUniversity                  OBJECT IDENTIFIER ::= { enterprises 8395 }
--                                OBJECT IDENTIFIER ::= { enterprises 8396 }
vecerina                          OBJECT IDENTIFIER ::= { enterprises 8397 }
universityOfWestFlorida           OBJECT IDENTIFIER ::= { enterprises 8398 }
iveaTechnologies                  OBJECT IDENTIFIER ::= { enterprises 8399 }
evercomSystems                    OBJECT IDENTIFIER ::= { enterprises 8400 }
foxtravel                         OBJECT IDENTIFIER ::= { enterprises 8401 }
eplus                             OBJECT IDENTIFIER ::= { enterprises 8402 }
araNetworkTechnologies            OBJECT IDENTIFIER ::= { enterprises 8403 }
akambaCorporation                 OBJECT IDENTIFIER ::= { enterprises 8404 }
tohonoConsulting                  OBJECT IDENTIFIER ::= { enterprises 8405 }
morningstarSystems                OBJECT IDENTIFIER ::= { enterprises 8406 }
mybaucom                          OBJECT IDENTIFIER ::= { enterprises 8407 }
intercomponentwareAG              OBJECT IDENTIFIER ::= { enterprises 8408 }
ztevision                         OBJECT IDENTIFIER ::= { enterprises 8409 }
landisAndGyrCommunicationsSAS     OBJECT IDENTIFIER ::= { enterprises 8410 }
eQual                             OBJECT IDENTIFIER ::= { enterprises 8411 }
satyamComputerServices            OBJECT IDENTIFIER ::= { enterprises 8412 }
globalnaps                        OBJECT IDENTIFIER ::= { enterprises 8413 }
cedacrinordSpA                    OBJECT IDENTIFIER ::= { enterprises 8414 }
cyberelanLLC                      OBJECT IDENTIFIER ::= { enterprises 8415 }
shawCablesystems                  OBJECT IDENTIFIER ::= { enterprises 8416 }
storageapps                       OBJECT IDENTIFIER ::= { enterprises 8417 }
listlessEnnui                     OBJECT IDENTIFIER ::= { enterprises 8418 }
collinsAvionics                   OBJECT IDENTIFIER ::= { enterprises 8419 }
digiSignCertificationServices     OBJECT IDENTIFIER ::= { enterprises 8420 }
vodtelCOMMUNICATIONSINC           OBJECT IDENTIFIER ::= { enterprises 8421 }
libritas                          OBJECT IDENTIFIER ::= { enterprises 8422 }
twisdAG                           OBJECT IDENTIFIER ::= { enterprises 8423 }
icubeSRL                          OBJECT IDENTIFIER ::= { enterprises 8424 }
apEngines                         OBJECT IDENTIFIER ::= { enterprises 8425 }
watlow                            OBJECT IDENTIFIER ::= { enterprises 8426 }
worldgateNetworksPrivateLimited   OBJECT IDENTIFIER ::= { enterprises 8427 }
turtleEntertainmentGmbH           OBJECT IDENTIFIER ::= { enterprises 8428 }
netfx                             OBJECT IDENTIFIER ::= { enterprises 8429 }
transwitchCorporation             OBJECT IDENTIFIER ::= { enterprises 8430 }
broadcastingInterestEnterprise    OBJECT IDENTIFIER ::= { enterprises 8431 }
teraglobalCommunications          OBJECT IDENTIFIER ::= { enterprises 8432 }
threeETechnologiesInternational   OBJECT IDENTIFIER ::= { enterprises 8433 }
foxChaseCancerCenter              OBJECT IDENTIFIER ::= { enterprises 8434 }
hyperedge                         OBJECT IDENTIFIER ::= { enterprises 8435 }
requisiteTechnology               OBJECT IDENTIFIER ::= { enterprises 8436 }
bolderInternetGroup               OBJECT IDENTIFIER ::= { enterprises 8437 }
reflexCommunications              OBJECT IDENTIFIER ::= { enterprises 8438 }
cadreDesign                       OBJECT IDENTIFIER ::= { enterprises 8439 }
tsudaCollege                      OBJECT IDENTIFIER ::= { enterprises 8440 }
shanghaiWaiGaoQiaoFreeTradeZone   OBJECT IDENTIFIER ::= { enterprises 8441 }
sendtekCorporation                OBJECT IDENTIFIER ::= { enterprises 8442 }
telisma                           OBJECT IDENTIFIER ::= { enterprises 8443 }
iie                               OBJECT IDENTIFIER ::= { enterprises 8444 }
bilstone                          OBJECT IDENTIFIER ::= { enterprises 8445 }
barclaycard                       OBJECT IDENTIFIER ::= { enterprises 8446 }
rivergladeConsultants             OBJECT IDENTIFIER ::= { enterprises 8447 }
avantisGmbH                       OBJECT IDENTIFIER ::= { enterprises 8448 }
epuredataINC                      OBJECT IDENTIFIER ::= { enterprises 8449 }
cetaceanNetworks                  OBJECT IDENTIFIER ::= { enterprises 8450 }
petriLaitinen                     OBJECT IDENTIFIER ::= { enterprises 8451 }
--Unassigned                      OBJECT IDENTIFIER ::= { enterprises 8452 }
personalPathSystems               OBJECT IDENTIFIER ::= { enterprises 9000 }
goltierMediaGroup                 OBJECT IDENTIFIER ::= { enterprises 9001 }
lxprocom                          OBJECT IDENTIFIER ::= { enterprises 9002 }
slimjones                         OBJECT IDENTIFIER ::= { enterprises 9003 }
suseLinuxVenezuela                OBJECT IDENTIFIER ::= { enterprises 9004 }
videoNetworksLimited              OBJECT IDENTIFIER ::= { enterprises 9005 }
apacheConsulting                  OBJECT IDENTIFIER ::= { enterprises 9006 }
finegroundNetworks                OBJECT IDENTIFIER ::= { enterprises 9007 }
digitalRoute                      OBJECT IDENTIFIER ::= { enterprises 9008 }
agniSystemsLimited                OBJECT IDENTIFIER ::= { enterprises 9009 }
liebenzellMission                 OBJECT IDENTIFIER ::= { enterprises 9010 }
laminarSoftware                   OBJECT IDENTIFIER ::= { enterprises 9011 }
mailvision3                       OBJECT IDENTIFIER ::= { enterprises 9012 }
spiritsoft                        OBJECT IDENTIFIER ::= { enterprises 9013 }
belenos                           OBJECT IDENTIFIER ::= { enterprises 9014 }
worldStreamingNetwork             OBJECT IDENTIFIER ::= { enterprises 9015 }
freereinCorporation               OBJECT IDENTIFIER ::= { enterprises 9016 }
cogentSystems                     OBJECT IDENTIFIER ::= { enterprises 9017 }
cqrData                           OBJECT IDENTIFIER ::= { enterprises 9018 }
capGeminiTelecomMediaAndNetworks  OBJECT IDENTIFIER ::= { enterprises 9019 }
computerAdaptiveTechnologies      OBJECT IDENTIFIER ::= { enterprises 9020 }
wideopenwestLLC                   OBJECT IDENTIFIER ::= { enterprises 9021 }
truesanNetworks                   OBJECT IDENTIFIER ::= { enterprises 9022 }
netsanity                         OBJECT IDENTIFIER ::= { enterprises 9023 }
teliaInternet                     OBJECT IDENTIFIER ::= { enterprises 9024 }
netcologne                        OBJECT IDENTIFIER ::= { enterprises 9025 }
isoftGmbH                         OBJECT IDENTIFIER ::= { enterprises 9026 }
softnerd                          OBJECT IDENTIFIER ::= { enterprises 9027 }
lendx                             OBJECT IDENTIFIER ::= { enterprises 9028 }
bsdUsersGroupItalia               OBJECT IDENTIFIER ::= { enterprises 9029 }
ivmg                              OBJECT IDENTIFIER ::= { enterprises 9030 }
nexterInformationTechnology       OBJECT IDENTIFIER ::= { enterprises 9031 }
ivstel                            OBJECT IDENTIFIER ::= { enterprises 9032 }
estonianTelephoneCompanyLimited   OBJECT IDENTIFIER ::= { enterprises 9033 }
jabbercom                         OBJECT IDENTIFIER ::= { enterprises 9034 }
carlisleFoodServiceProducts       OBJECT IDENTIFIER ::= { enterprises 9035 }
jimDutton                         OBJECT IDENTIFIER ::= { enterprises 9036 }
everydayOffice                    OBJECT IDENTIFIER ::= { enterprises 9037 }
wellDiagnostics                   OBJECT IDENTIFIER ::= { enterprises 9038 }
chengduIdealTelecomTechnology     OBJECT IDENTIFIER ::= { enterprises 9039 }
chengduIdealInformationIndustryCo OBJECT IDENTIFIER ::= { enterprises 9040 }
cambridgeUniversityEngineeringDep OBJECT IDENTIFIER ::= { enterprises 9041 }
teinos                            OBJECT IDENTIFIER ::= { enterprises 9042 }
execulink                         OBJECT IDENTIFIER ::= { enterprises 9043 }
necEluminantTechnologies          OBJECT IDENTIFIER ::= { enterprises 9044 }
enetsecure                        OBJECT IDENTIFIER ::= { enterprises 9045 }
amecisco                          OBJECT IDENTIFIER ::= { enterprises 9046 }
blueCrossBlueShieldOfFlorida      OBJECT IDENTIFIER ::= { enterprises 9047 }
openSystemConsultants             OBJECT IDENTIFIER ::= { enterprises 9048 }
integrityOnline                   OBJECT IDENTIFIER ::= { enterprises 9049 }
telenorLinkAS                     OBJECT IDENTIFIER ::= { enterprises 9050 }
--                                OBJECT IDENTIFIER ::= { enterprises 9051 }
sunbaySoftwareAG                  OBJECT IDENTIFIER ::= { enterprises 9052 }
tovaris                           OBJECT IDENTIFIER ::= { enterprises 9053 }
tokheim                           OBJECT IDENTIFIER ::= { enterprises 9054 }
riverscom                         OBJECT IDENTIFIER ::= { enterprises 9055 }
telstratInt                       OBJECT IDENTIFIER ::= { enterprises 9056 }
millenniumCommunicationNetwork    OBJECT IDENTIFIER ::= { enterprises 9057 }
jamcracker                        OBJECT IDENTIFIER ::= { enterprises 9058 }
vectradNetworksCorporation        OBJECT IDENTIFIER ::= { enterprises 9059 }
rulespace                         OBJECT IDENTIFIER ::= { enterprises 9060 }
deutscherGoBund                   OBJECT IDENTIFIER ::= { enterprises 9061 }
srsMicrosystems                   OBJECT IDENTIFIER ::= { enterprises 9062 }
ihiveTechnologyPte                OBJECT IDENTIFIER ::= { enterprises 9063 }
atmComputerSystemeGmbH            OBJECT IDENTIFIER ::= { enterprises 9064 }
nettaskingTechnology              OBJECT IDENTIFIER ::= { enterprises 9065 }
globalSecurityTechnologies        OBJECT IDENTIFIER ::= { enterprises 9066 }
cambiaNetworks                    OBJECT IDENTIFIER ::= { enterprises 9067 }
delphiAssociates                  OBJECT IDENTIFIER ::= { enterprises 9068 }
phillip                           OBJECT IDENTIFIER ::= { enterprises 9069 }
symmetricom                       OBJECT IDENTIFIER ::= { enterprises 9070 }
spirianTechnologies               OBJECT IDENTIFIER ::= { enterprises 9071 }
ackleynet                         OBJECT IDENTIFIER ::= { enterprises 9072 }
sunnyvaleCommunityPlayers         OBJECT IDENTIFIER ::= { enterprises 9073 }
johnMSutherland                   OBJECT IDENTIFIER ::= { enterprises 9074 }
novexSolutions                    OBJECT IDENTIFIER ::= { enterprises 9075 }
tokyoMetallicCommuynicationsCorp  OBJECT IDENTIFIER ::= { enterprises 9076 }
dekart                            OBJECT IDENTIFIER ::= { enterprises 9077 }
beConnected                       OBJECT IDENTIFIER ::= { enterprises 9078 }
theSanjyotBharathanDesignAssociation OBJECT IDENTIFIER ::= { enterprises 9079 }
babelComAustralia                 OBJECT IDENTIFIER ::= { enterprises 9080 }
eachnet                           OBJECT IDENTIFIER ::= { enterprises 9081 }
extremail                         OBJECT IDENTIFIER ::= { enterprises 9082 }
eteamconsultingcom                OBJECT IDENTIFIER ::= { enterprises 9083 }
keynoteSystems                    OBJECT IDENTIFIER ::= { enterprises 9084 }
opticalSwitchCorporation          OBJECT IDENTIFIER ::= { enterprises 9085 }
usRobotics                        OBJECT IDENTIFIER ::= { enterprises 9086 }
brightmail                        OBJECT IDENTIFIER ::= { enterprises 9087 }
osoGrandeTechnologies             OBJECT IDENTIFIER ::= { enterprises 9088 }
newMexicoTechnet                  OBJECT IDENTIFIER ::= { enterprises 9089 }
datagrove                         OBJECT IDENTIFIER ::= { enterprises 9090 }
microSTARINT                      OBJECT IDENTIFIER ::= { enterprises 9091 }
veenstraGraphicSolutions          OBJECT IDENTIFIER ::= { enterprises 9092 }
innovateITLogisticsBV             OBJECT IDENTIFIER ::= { enterprises 9093 }
amberArcherConsultingCo           OBJECT IDENTIFIER ::= { enterprises 9094 }
nipponMITSUBISHIOILCORPORATION    OBJECT IDENTIFIER ::= { enterprises 9095 }
zentrumFurProduktEntwicklung      OBJECT IDENTIFIER ::= { enterprises 9096 }
cdftel                            OBJECT IDENTIFIER ::= { enterprises 9097 }
dwSystems                         OBJECT IDENTIFIER ::= { enterprises 9098 }
centralSystemsInternational       OBJECT IDENTIFIER ::= { enterprises 9099 }
mstel                             OBJECT IDENTIFIER ::= { enterprises 9100 }
optumComputingSolutions           OBJECT IDENTIFIER ::= { enterprises 9101 }
telecashFrankfurt                 OBJECT IDENTIFIER ::= { enterprises 9102 }
yuSheiRealEstateCo                OBJECT IDENTIFIER ::= { enterprises 9103 }
chuShenCo                         OBJECT IDENTIFIER ::= { enterprises 9104 }
mist                              OBJECT IDENTIFIER ::= { enterprises 9105 }
eliosInformatique                 OBJECT IDENTIFIER ::= { enterprises 9106 }
fergusonEnterprises               OBJECT IDENTIFIER ::= { enterprises 9107 }
randomWalkComputing               OBJECT IDENTIFIER ::= { enterprises 9108 }
infogear                          OBJECT IDENTIFIER ::= { enterprises 9109 }
netAsiaAngelesCIty                OBJECT IDENTIFIER ::= { enterprises 9110 }
newwayTech                        OBJECT IDENTIFIER ::= { enterprises 9111 }
palamedesGmbH                     OBJECT IDENTIFIER ::= { enterprises 9112 }
wiral                             OBJECT IDENTIFIER ::= { enterprises 9113 }
ylineWebAccessServices            OBJECT IDENTIFIER ::= { enterprises 9114 }
archonTechnologies                OBJECT IDENTIFIER ::= { enterprises 9115 }
ubicom                            OBJECT IDENTIFIER ::= { enterprises 9116 }
lewizCommunications               OBJECT IDENTIFIER ::= { enterprises 9117 }
ci                                OBJECT IDENTIFIER ::= { enterprises 9118 }
advancedRotorcraftTechnology      OBJECT IDENTIFIER ::= { enterprises 9119 }
naradaNetworks                    OBJECT IDENTIFIER ::= { enterprises 9120 }
eduquipLimited                    OBJECT IDENTIFIER ::= { enterprises 9121 }
upctvInteractive                  OBJECT IDENTIFIER ::= { enterprises 9122 }
universit                         OBJECT IDENTIFIER ::= { enterprises 9123 }
intellitactics                    OBJECT IDENTIFIER ::= { enterprises 9124 }
inspirationTechnologyPty          OBJECT IDENTIFIER ::= { enterprises 9125 }
aetianNetworks                    OBJECT IDENTIFIER ::= { enterprises 9126 }
advancedPERIPHERALSTECH           OBJECT IDENTIFIER ::= { enterprises 9127 }
centreDeTraductionDesOrganesDeL   OBJECT IDENTIFIER ::= { enterprises 9128 }
linkvestSA                        OBJECT IDENTIFIER ::= { enterprises 9129 }
hemisphereTechnologies            OBJECT IDENTIFIER ::= { enterprises 9130 }
rolandFelnhofer                   OBJECT IDENTIFIER ::= { enterprises 9131 }
hutchisonOPTELTelecomTechnologyCO OBJECT IDENTIFIER ::= { enterprises 9132 }
microraabElectronics              OBJECT IDENTIFIER ::= { enterprises 9133 }
telenetVlaanderenNV               OBJECT IDENTIFIER ::= { enterprises 9134 }
heydeAG                           OBJECT IDENTIFIER ::= { enterprises 9135 }
isdnCommunications                OBJECT IDENTIFIER ::= { enterprises 9136 }
anatelCommunications              OBJECT IDENTIFIER ::= { enterprises 9137 }
antefacto                         OBJECT IDENTIFIER ::= { enterprises 9138 }
petroleumBusinessInstitute        OBJECT IDENTIFIER ::= { enterprises 9139 }
mediaGeneral                      OBJECT IDENTIFIER ::= { enterprises 9140 }
riptech                           OBJECT IDENTIFIER ::= { enterprises 9141 }
infopaqApS                        OBJECT IDENTIFIER ::= { enterprises 9142 }
edmundscom                        OBJECT IDENTIFIER ::= { enterprises 9143 }
traderElectronicMedia             OBJECT IDENTIFIER ::= { enterprises 9144 }
accesspt                          OBJECT IDENTIFIER ::= { enterprises 9145 }
reporterTimes                     OBJECT IDENTIFIER ::= { enterprises 9146 }
tealeafTechnology                 OBJECT IDENTIFIER ::= { enterprises 9147 }
acmePacket                        OBJECT IDENTIFIER ::= { enterprises 9148 }
locusCorporation                  OBJECT IDENTIFIER ::= { enterprises 9149 }
metromediaFiberNetwork            OBJECT IDENTIFIER ::= { enterprises 9150 }
wiral                             OBJECT IDENTIFIER ::= { enterprises 9151 }
ditCompanyLimited                 OBJECT IDENTIFIER ::= { enterprises 9152 }
sodielecTelecom                   OBJECT IDENTIFIER ::= { enterprises 9153 }
figmentTechnologies               OBJECT IDENTIFIER ::= { enterprises 9154 }
bluenetworkx                      OBJECT IDENTIFIER ::= { enterprises 9155 }
egurkhaPvt                        OBJECT IDENTIFIER ::= { enterprises 9156 }
corecomm                          OBJECT IDENTIFIER ::= { enterprises 9157 }
theInternetGroup                  OBJECT IDENTIFIER ::= { enterprises 9158 }
shad0wsnet                        OBJECT IDENTIFIER ::= { enterprises 9159 }
dgtSpZOo                          OBJECT IDENTIFIER ::= { enterprises 9160 }
universidadDelPaisVasco           OBJECT IDENTIFIER ::= { enterprises 9161 }
p                                 OBJECT IDENTIFIER ::= { enterprises 9162 }
gnuRadiusProject                  OBJECT IDENTIFIER ::= { enterprises 9163 }
xwareAB                           OBJECT IDENTIFIER ::= { enterprises 9164 }
cabinetRemouit                    OBJECT IDENTIFIER ::= { enterprises 9165 }
universidadGalileo                OBJECT IDENTIFIER ::= { enterprises 9166 }
anxebusinessCorp                  OBJECT IDENTIFIER ::= { enterprises 9167 }
transaccess                       OBJECT IDENTIFIER ::= { enterprises 9168 }
novisTelecom                      OBJECT IDENTIFIER ::= { enterprises 9169 }
exaecon                           OBJECT IDENTIFIER ::= { enterprises 9170 }
nettone                           OBJECT IDENTIFIER ::= { enterprises 9171 }
hvcTechnologies                   OBJECT IDENTIFIER ::= { enterprises 9172 }
kohl                              OBJECT IDENTIFIER ::= { enterprises 9173 }
a2vIct                            OBJECT IDENTIFIER ::= { enterprises 9174 }
streamTheory                      OBJECT IDENTIFIER ::= { enterprises 9175 }
openIT                            OBJECT IDENTIFIER ::= { enterprises 9176 }
thinkfreecom                      OBJECT IDENTIFIER ::= { enterprises 9177 }
daesungCorp                       OBJECT IDENTIFIER ::= { enterprises 9178 }
intesabciSISTEMIESERVIZI          OBJECT IDENTIFIER ::= { enterprises 9179 }
marantiNetworks                   OBJECT IDENTIFIER ::= { enterprises 9180 }
airTechnologySystems              OBJECT IDENTIFIER ::= { enterprises 9181 }
filefish                          OBJECT IDENTIFIER ::= { enterprises 9182 }
sambaTNG                          OBJECT IDENTIFIER ::= { enterprises 9183 }
alterbox                          OBJECT IDENTIFIER ::= { enterprises 9184 }
msIntegrationServices             OBJECT IDENTIFIER ::= { enterprises 9185 }
logipolisPte                      OBJECT IDENTIFIER ::= { enterprises 9186 }
eastmanChemicalCompany            OBJECT IDENTIFIER ::= { enterprises 9187 }
forceComputers                    OBJECT IDENTIFIER ::= { enterprises 9188 }
promedicoGmbh                     OBJECT IDENTIFIER ::= { enterprises 9189 }
katanooTechnologies               OBJECT IDENTIFIER ::= { enterprises 9190 }
burgiesoft                        OBJECT IDENTIFIER ::= { enterprises 9191 }
pirkanTietokoneOy                 OBJECT IDENTIFIER ::= { enterprises 9192 }
cirpack                           OBJECT IDENTIFIER ::= { enterprises 9193 }
austlii                           OBJECT IDENTIFIER ::= { enterprises 9194 }
autocontcontrolSystems            OBJECT IDENTIFIER ::= { enterprises 9195 }
algotronics                       OBJECT IDENTIFIER ::= { enterprises 9196 }
lyndonStateCollege                OBJECT IDENTIFIER ::= { enterprises 9197 }
teletron                          OBJECT IDENTIFIER ::= { enterprises 9198 }
daumDatentechnik                  OBJECT IDENTIFIER ::= { enterprises 9199 }
obermeierSoftware                 OBJECT IDENTIFIER ::= { enterprises 9200 }
fasturn                           OBJECT IDENTIFIER ::= { enterprises 9201 }
ensurelink                        OBJECT IDENTIFIER ::= { enterprises 9202 }
seguridataPrivada                 OBJECT IDENTIFIER ::= { enterprises 9203 }
auroraNetworks                    OBJECT IDENTIFIER ::= { enterprises 9204 }
mojNetDoo                         OBJECT IDENTIFIER ::= { enterprises 9205 }
digitalspark                      OBJECT IDENTIFIER ::= { enterprises 9206 }
segnetTechnology                  OBJECT IDENTIFIER ::= { enterprises 9207 }
hamilcarDevelopment               OBJECT IDENTIFIER ::= { enterprises 9208 }
peaceTechnology                   OBJECT IDENTIFIER ::= { enterprises 9209 }
merlinITServices                  OBJECT IDENTIFIER ::= { enterprises 9210 }
rabobankICT                       OBJECT IDENTIFIER ::= { enterprises 9211 }
waviumAB                          OBJECT IDENTIFIER ::= { enterprises 9212 }
netsealTechnologies               OBJECT IDENTIFIER ::= { enterprises 9213 }
kemuriSystems                     OBJECT IDENTIFIER ::= { enterprises 9214 }
eridanInformatique                OBJECT IDENTIFIER ::= { enterprises 9215 }
universidadeDe                    OBJECT IDENTIFIER ::= { enterprises 9216 }
biobaseBiologicalDatabasesBiologischeDatenbanken OBJECT IDENTIFIER ::= { enterprises 9217 }
skysoftPortugal                   OBJECT IDENTIFIER ::= { enterprises 9218 }
juliaocom                         OBJECT IDENTIFIER ::= { enterprises 9219 }
openjcc                           OBJECT IDENTIFIER ::= { enterprises 9220 }
shawCommunications                OBJECT IDENTIFIER ::= { enterprises 9221 }
phillipsPetroleumCompany          OBJECT IDENTIFIER ::= { enterprises 9222 }
roskildeUniversity                OBJECT IDENTIFIER ::= { enterprises 9223 }
lawrenceUniversity                OBJECT IDENTIFIER ::= { enterprises 9224 }
fja                               OBJECT IDENTIFIER ::= { enterprises 9225 }
microtest                         OBJECT IDENTIFIER ::= { enterprises 9226 }
entrisphere                       OBJECT IDENTIFIER ::= { enterprises 9227 }
globetech                         OBJECT IDENTIFIER ::= { enterprises 9228 }
totilities                        OBJECT IDENTIFIER ::= { enterprises 9229 }
numb4madResearchLabOrganization   OBJECT IDENTIFIER ::= { enterprises 9230 }
adirTechnologies                  OBJECT IDENTIFIER ::= { enterprises 9231 }
norwegianMappingAuthority         OBJECT IDENTIFIER ::= { enterprises 9232 }
ierSA                             OBJECT IDENTIFIER ::= { enterprises 9233 }
snowshoreNetworks                 OBJECT IDENTIFIER ::= { enterprises 9234 }
fcbDirectMontreal                 OBJECT IDENTIFIER ::= { enterprises 9235 }
fundtechCorporation               OBJECT IDENTIFIER ::= { enterprises 9236 }
newisys                           OBJECT IDENTIFIER ::= { enterprises 9237 }
imagineBroadbandLimited           OBJECT IDENTIFIER ::= { enterprises 9238 }
jonesknowledgecom                 OBJECT IDENTIFIER ::= { enterprises 9239 }
internationalMRIAccreditationResources OBJECT IDENTIFIER ::= { enterprises 9240 }
uniXSoftwareAG                    OBJECT IDENTIFIER ::= { enterprises 9241 }
institutoDeMatem                  OBJECT IDENTIFIER ::= { enterprises 9242 }
air                               OBJECT IDENTIFIER ::= { enterprises 9243 }
purecarbon                        OBJECT IDENTIFIER ::= { enterprises 9244 }
neuromics                         OBJECT IDENTIFIER ::= { enterprises 9245 }
automatedHandlingSystems          OBJECT IDENTIFIER ::= { enterprises 9246 }
federalMogulCorporation           OBJECT IDENTIFIER ::= { enterprises 9247 }
paktronixSystemsLLC               OBJECT IDENTIFIER ::= { enterprises 9248 }
musambiCorporation                OBJECT IDENTIFIER ::= { enterprises 9249 }
strixSystems                      OBJECT IDENTIFIER ::= { enterprises 9250 }
trAssociates                      OBJECT IDENTIFIER ::= { enterprises 9251 }
h                                 OBJECT IDENTIFIER ::= { enterprises 9252 }
buildscape                        OBJECT IDENTIFIER ::= { enterprises 9253 }
pajunasInteractive                OBJECT IDENTIFIER ::= { enterprises 9254 }
vicinityCorporation               OBJECT IDENTIFIER ::= { enterprises 9255 }
lightpointeCommunications         OBJECT IDENTIFIER ::= { enterprises 9256 }
volera                            OBJECT IDENTIFIER ::= { enterprises 9257 }
xmlstrategiesnet                  OBJECT IDENTIFIER ::= { enterprises 9258 }
syspolCo                          OBJECT IDENTIFIER ::= { enterprises 9259 }
adtecCorporation                  OBJECT IDENTIFIER ::= { enterprises 9260 }
delphiAutomotiveSystemsInvestment OBJECT IDENTIFIER ::= { enterprises 9261 }
eastnetCo                         OBJECT IDENTIFIER ::= { enterprises 9262 }
cyberneticsTechnologyCo           OBJECT IDENTIFIER ::= { enterprises 9263 }
caerdroia                         OBJECT IDENTIFIER ::= { enterprises 9264 }
tdisie                            OBJECT IDENTIFIER ::= { enterprises 9265 }
parsoftSystemsPvt                 OBJECT IDENTIFIER ::= { enterprises 9266 }
inSysteme                         OBJECT IDENTIFIER ::= { enterprises 9267 }
ruhrverband                       OBJECT IDENTIFIER ::= { enterprises 9268 }
mediabroadcast                    OBJECT IDENTIFIER ::= { enterprises 9269 }
callsys                           OBJECT IDENTIFIER ::= { enterprises 9270 }
siemensNGNI                       OBJECT IDENTIFIER ::= { enterprises 9271 }
elektrobit                        OBJECT IDENTIFIER ::= { enterprises 9272 }
neuroTelecom                      OBJECT IDENTIFIER ::= { enterprises 9273 }
access-sevenCommunications        OBJECT IDENTIFIER ::= { enterprises 9274 }
genesys                           OBJECT IDENTIFIER ::= { enterprises 9275 }
semaSpainNEG                      OBJECT IDENTIFIER ::= { enterprises 9276 }
logicoSmartCardSolutionsAG        OBJECT IDENTIFIER ::= { enterprises 9277 }
econiacom                         OBJECT IDENTIFIER ::= { enterprises 9278 }
arqanaTechnologies                OBJECT IDENTIFIER ::= { enterprises 9279 }
accesslineCommunicationsCorporation OBJECT IDENTIFIER ::= { enterprises 9280 }
standardInsuranceCompany          OBJECT IDENTIFIER ::= { enterprises 9281 }
nocpulse                          OBJECT IDENTIFIER ::= { enterprises 9282 }
costaRicaInstituteOfTechnology    OBJECT IDENTIFIER ::= { enterprises 9283 }
westernIllinoisUniversity         OBJECT IDENTIFIER ::= { enterprises 9284 }
internetcds                       OBJECT IDENTIFIER ::= { enterprises 9285 }
maximumThroughput                 OBJECT IDENTIFIER ::= { enterprises 9286 }
zeusCommunications                OBJECT IDENTIFIER ::= { enterprises 9287 }
hostpro                           OBJECT IDENTIFIER ::= { enterprises 9288 }
unirez                            OBJECT IDENTIFIER ::= { enterprises 9289 }
firinnorg                         OBJECT IDENTIFIER ::= { enterprises 9290 }
rainfinity                        OBJECT IDENTIFIER ::= { enterprises 9291 }
webleySystem                      OBJECT IDENTIFIER ::= { enterprises 9292 }
staturnComputer                   OBJECT IDENTIFIER ::= { enterprises 9293 }
w4yDoBrasil                       OBJECT IDENTIFIER ::= { enterprises 9294 }
workersCompensationFund           OBJECT IDENTIFIER ::= { enterprises 9295 }
xlightPhotonics                   OBJECT IDENTIFIER ::= { enterprises 9296 }
ayeca                             OBJECT IDENTIFIER ::= { enterprises 9297 }
universityOfCompi                 OBJECT IDENTIFIER ::= { enterprises 9298 }
hellasOnLine                      OBJECT IDENTIFIER ::= { enterprises 9299 }
hypostasis                        OBJECT IDENTIFIER ::= { enterprises 9300 }
spiderSoftware                    OBJECT IDENTIFIER ::= { enterprises 9301 }
esiSrl                            OBJECT IDENTIFIER ::= { enterprises 9302 }
packetfrontSwedenAB               OBJECT IDENTIFIER ::= { enterprises 9303 }
connectionTechnologySystems       OBJECT IDENTIFIER ::= { enterprises 9304 }
westernMichiganUniversity         OBJECT IDENTIFIER ::= { enterprises 9305 }
octaveCommunications              OBJECT IDENTIFIER ::= { enterprises 9306 }
rclEnterprises                    OBJECT IDENTIFIER ::= { enterprises 9307 }
oasisTechnology                   OBJECT IDENTIFIER ::= { enterprises 9308 }
urzadMiastaPabianic               OBJECT IDENTIFIER ::= { enterprises 9309 }
abitabSA                          OBJECT IDENTIFIER ::= { enterprises 9310 }
diTrute                           OBJECT IDENTIFIER ::= { enterprises 9311 }
truthConsultingAndTechnology      OBJECT IDENTIFIER ::= { enterprises 9312 }
dakoma                            OBJECT IDENTIFIER ::= { enterprises 9313 }
curtisFamily                      OBJECT IDENTIFIER ::= { enterprises 9314 }
cartelSECURITE                    OBJECT IDENTIFIER ::= { enterprises 9315 }
netvoyager                        OBJECT IDENTIFIER ::= { enterprises 9316 }
tech2work                         OBJECT IDENTIFIER ::= { enterprises 9317 }
debekaVersicherung                OBJECT IDENTIFIER ::= { enterprises 9318 }
netaktiv                          OBJECT IDENTIFIER ::= { enterprises 9319 }
nanningTelecom                    OBJECT IDENTIFIER ::= { enterprises 9320 }
screenpeaks                       OBJECT IDENTIFIER ::= { enterprises 9321 }
nettechSA                         OBJECT IDENTIFIER ::= { enterprises 9322 }
pcAway                            OBJECT IDENTIFIER ::= { enterprises 9323 }
divisionFoCancerStudies           OBJECT IDENTIFIER ::= { enterprises 9324 }
universityOfCalifornia            OBJECT IDENTIFIER ::= { enterprises 9325 }
lewisAndClarkCollege              OBJECT IDENTIFIER ::= { enterprises 9326 }
hygeiaCorporation                 OBJECT IDENTIFIER ::= { enterprises 9327 }
nih                               OBJECT IDENTIFIER ::= { enterprises 9328 }
crusoeCommunications              OBJECT IDENTIFIER ::= { enterprises 9329 }
selestaSpA                        OBJECT IDENTIFIER ::= { enterprises 9330 }
maxwareInternationalAS            OBJECT IDENTIFIER ::= { enterprises 9331 }
appliedSNMP                       OBJECT IDENTIFIER ::= { enterprises 9332 }
lincomWireless                    OBJECT IDENTIFIER ::= { enterprises 9333 }
ipdrorg                           OBJECT IDENTIFIER ::= { enterprises 9334 }
powersoft                         OBJECT IDENTIFIER ::= { enterprises 9335 }
publixSuperMarkets                OBJECT IDENTIFIER ::= { enterprises 9336 }
minterCorp                        OBJECT IDENTIFIER ::= { enterprises 9337 }
petersenVenturesLLC               OBJECT IDENTIFIER ::= { enterprises 9338 }
leftCoastSystemsCorp              OBJECT IDENTIFIER ::= { enterprises 9339 }
networkInfinity                   OBJECT IDENTIFIER ::= { enterprises 9340 }
cyberfuseTechnologies             OBJECT IDENTIFIER ::= { enterprises 9341 }
penguinComputing                  OBJECT IDENTIFIER ::= { enterprises 9342 }
comcelSA                          OBJECT IDENTIFIER ::= { enterprises 9343 }
kavalWirelessTechnologies         OBJECT IDENTIFIER ::= { enterprises 9344 }
infinetivity                      OBJECT IDENTIFIER ::= { enterprises 9345 }
igeek                             OBJECT IDENTIFIER ::= { enterprises 9346 }
avazNetworks                      OBJECT IDENTIFIER ::= { enterprises 9347 }
goldenTelecomUkraine              OBJECT IDENTIFIER ::= { enterprises 9348 }
wizlan                            OBJECT IDENTIFIER ::= { enterprises 9349 }
netmagicSolutionsPvt              OBJECT IDENTIFIER ::= { enterprises 9350 }
forthnetSA                        OBJECT IDENTIFIER ::= { enterprises 9351 }
conundrumcommunications           OBJECT IDENTIFIER ::= { enterprises 9352 }
universiteDeMetz                  OBJECT IDENTIFIER ::= { enterprises 9353 }
greyInteractiveFrance             OBJECT IDENTIFIER ::= { enterprises 9354 }
krivorozhskiyHlebokombinatN1      OBJECT IDENTIFIER ::= { enterprises 9355 }
npassage                          OBJECT IDENTIFIER ::= { enterprises 9356 }
itBeratungSchaffert               OBJECT IDENTIFIER ::= { enterprises 9357 }
wicomCommunications               OBJECT IDENTIFIER ::= { enterprises 9358 }
symekoDatasystemsBv               OBJECT IDENTIFIER ::= { enterprises 9359 }
greenLight                        OBJECT IDENTIFIER ::= { enterprises 9360 }
oc                                OBJECT IDENTIFIER ::= { enterprises 9361 }
enseirb                           OBJECT IDENTIFIER ::= { enterprises 9362 }
spelio                            OBJECT IDENTIFIER ::= { enterprises 9363 }
interpark                         OBJECT IDENTIFIER ::= { enterprises 9364 }
mindsurfNetworks                  OBJECT IDENTIFIER ::= { enterprises 9365 }
cifra                             OBJECT IDENTIFIER ::= { enterprises 9366 }
fastsignsInternational            OBJECT IDENTIFIER ::= { enterprises 9367 }
storageXstreams                   OBJECT IDENTIFIER ::= { enterprises 9368 }
micahJSchehl                      OBJECT IDENTIFIER ::= { enterprises 9369 }
spaceTelescopeScienceInstitute    OBJECT IDENTIFIER ::= { enterprises 9370 }
okolonaChristianChurch            OBJECT IDENTIFIER ::= { enterprises 9371 }
ikadega                           OBJECT IDENTIFIER ::= { enterprises 9372 }
clearInk                          OBJECT IDENTIFIER ::= { enterprises 9373 }
hermaionorg                       OBJECT IDENTIFIER ::= { enterprises 9374 }
baslerKantonalbank                OBJECT IDENTIFIER ::= { enterprises 9375 }
cvsPharmacyRussell                OBJECT IDENTIFIER ::= { enterprises 9376 }
voyagerComputerCorporation        OBJECT IDENTIFIER ::= { enterprises 9377 }
ilexSystems                       OBJECT IDENTIFIER ::= { enterprises 9378 }
eumitcomTechnology                OBJECT IDENTIFIER ::= { enterprises 9379 }
octogonGesellschaftF              OBJECT IDENTIFIER ::= { enterprises 9380 }
walterBiering                     OBJECT IDENTIFIER ::= { enterprises 9381 }
worahnet                          OBJECT IDENTIFIER ::= { enterprises 9382 }
angelesDesignSystems              OBJECT IDENTIFIER ::= { enterprises 9383 }
d2k                               OBJECT IDENTIFIER ::= { enterprises 9384 }
jasonWood                         OBJECT IDENTIFIER ::= { enterprises 9385 }
claytonCollegeAndStateUniversity  OBJECT IDENTIFIER ::= { enterprises 9386 }
companiaMea                       OBJECT IDENTIFIER ::= { enterprises 9387 }
asiainfo                          OBJECT IDENTIFIER ::= { enterprises 9388 }
magicalFruit                      OBJECT IDENTIFIER ::= { enterprises 9389 }
wtServices                        OBJECT IDENTIFIER ::= { enterprises 9390 }
audientia                         OBJECT IDENTIFIER ::= { enterprises 9391 }
cannonHillAnglicanCollege         OBJECT IDENTIFIER ::= { enterprises 9392 }
intecsInformation                 OBJECT IDENTIFIER ::= { enterprises 9393 }
visanaServicesAG                  OBJECT IDENTIFIER ::= { enterprises 9394 }
uecTechnologies                   OBJECT IDENTIFIER ::= { enterprises 9395 }
waltDisneyInternational           OBJECT IDENTIFIER ::= { enterprises 9396 }
vartechSolutions                  OBJECT IDENTIFIER ::= { enterprises 9397 }
tokyoMetallicCommunicationsCorp   OBJECT IDENTIFIER ::= { enterprises 9398 }
consulRiskManagementDirkWisse     OBJECT IDENTIFIER ::= { enterprises 9399 }
fachhochschuleKonstanz            OBJECT IDENTIFIER ::= { enterprises 9400 }
amlWirelessSystems                OBJECT IDENTIFIER ::= { enterprises 9401 }
dcrypt                            OBJECT IDENTIFIER ::= { enterprises 9402 }
allinstant                        OBJECT IDENTIFIER ::= { enterprises 9403 }
dewpoint                          OBJECT IDENTIFIER ::= { enterprises 9404 }
kinglandSystemsCorporation        OBJECT IDENTIFIER ::= { enterprises 9405 }
synchrologic                      OBJECT IDENTIFIER ::= { enterprises 9406 }
broadataCommunications            OBJECT IDENTIFIER ::= { enterprises 9407 }
chesterEnterprises                OBJECT IDENTIFIER ::= { enterprises 9408 }
clickservices                     OBJECT IDENTIFIER ::= { enterprises 9409 }
axeOnlinePtyLimited               OBJECT IDENTIFIER ::= { enterprises 9410 }
hitwisePty                        OBJECT IDENTIFIER ::= { enterprises 9411 }
contela                           OBJECT IDENTIFIER ::= { enterprises 9412 }
operaxAB                          OBJECT IDENTIFIER ::= { enterprises 9413 }
digitalGlobe                      OBJECT IDENTIFIER ::= { enterprises 9414 }
archimed                          OBJECT IDENTIFIER ::= { enterprises 9415 }
accordantConsulting               OBJECT IDENTIFIER ::= { enterprises 9416 }
egg                               OBJECT IDENTIFIER ::= { enterprises 9417 }
ivistarAG                         OBJECT IDENTIFIER ::= { enterprises 9418 }
siemensSiNiA                      OBJECT IDENTIFIER ::= { enterprises 9419 }
baltimoreTechnologies             OBJECT IDENTIFIER ::= { enterprises 9420 }
vodafoneD2                        OBJECT IDENTIFIER ::= { enterprises 9421 }
atanion                           OBJECT IDENTIFIER ::= { enterprises 9422 }
msaInforSistemasEAutomacao        OBJECT IDENTIFIER ::= { enterprises 9423 }
aAndcAutomacaoEControle           OBJECT IDENTIFIER ::= { enterprises 9424 }
rotterdamSchoolOfManagement       OBJECT IDENTIFIER ::= { enterprises 9425 }
adigidaSolutions                  OBJECT IDENTIFIER ::= { enterprises 9426 }
categoricSoftware                 OBJECT IDENTIFIER ::= { enterprises 9427 }
orgenicSoftware                   OBJECT IDENTIFIER ::= { enterprises 9428 }
mariinskyTheatre                  OBJECT IDENTIFIER ::= { enterprises 9429 }
progressTelecom                   OBJECT IDENTIFIER ::= { enterprises 9430 }
push                              OBJECT IDENTIFIER ::= { enterprises 9431 }
vingageCorporation                OBJECT IDENTIFIER ::= { enterprises 9432 }
vaticor                           OBJECT IDENTIFIER ::= { enterprises 9433 }
telergyNetworkServices            OBJECT IDENTIFIER ::= { enterprises 9434 }
boletinOficialDelEstado           OBJECT IDENTIFIER ::= { enterprises 9435 }
crysbergAS                        OBJECT IDENTIFIER ::= { enterprises 9436 }
lancerInsuranceCompany            OBJECT IDENTIFIER ::= { enterprises 9437 }
yellowshirt                       OBJECT IDENTIFIER ::= { enterprises 9438 }
greenPointPty                     OBJECT IDENTIFIER ::= { enterprises 9439 }
ekoSystem                         OBJECT IDENTIFIER ::= { enterprises 9440 }
wallStreetSystems                 OBJECT IDENTIFIER ::= { enterprises 9441 }
atherosCommunications             OBJECT IDENTIFIER ::= { enterprises 9442 }
virage                            OBJECT IDENTIFIER ::= { enterprises 9443 }
firemon                           OBJECT IDENTIFIER ::= { enterprises 9444 }
tjb                               OBJECT IDENTIFIER ::= { enterprises 9445 }
indianaUniversity                 OBJECT IDENTIFIER ::= { enterprises 9446 }
redFernSoftware                   OBJECT IDENTIFIER ::= { enterprises 9447 }
zyfer                             OBJECT IDENTIFIER ::= { enterprises 9448 }
floridaStateUniversity            OBJECT IDENTIFIER ::= { enterprises 9449 }
zyoptics                          OBJECT IDENTIFIER ::= { enterprises 9450 }
digeo                             OBJECT IDENTIFIER ::= { enterprises 9451 }
netlabsSRL                        OBJECT IDENTIFIER ::= { enterprises 9452 }
barnardosNewZealand               OBJECT IDENTIFIER ::= { enterprises 9453 }
futureGateSoftware                OBJECT IDENTIFIER ::= { enterprises 9454 }
intelliclaim                      OBJECT IDENTIFIER ::= { enterprises 9455 }
allegroNetworks                   OBJECT IDENTIFIER ::= { enterprises 9456 }
broadbandStorage                  OBJECT IDENTIFIER ::= { enterprises 9457 }
tcsi                              OBJECT IDENTIFIER ::= { enterprises 9458 }
nilesoft                          OBJECT IDENTIFIER ::= { enterprises 9459 }
saltaMonteSolutions               OBJECT IDENTIFIER ::= { enterprises 9460 }
y2funcom                          OBJECT IDENTIFIER ::= { enterprises 9461 }
mmlabKTU                          OBJECT IDENTIFIER ::= { enterprises 9462 }
geyerUndWeinig                    OBJECT IDENTIFIER ::= { enterprises 9463 }
sielSpA                           OBJECT IDENTIFIER ::= { enterprises 9464 }
oldenburgischeLandesbankAG        OBJECT IDENTIFIER ::= { enterprises 9465 }
cilea                             OBJECT IDENTIFIER ::= { enterprises 9466 }
ibanxBV                           OBJECT IDENTIFIER ::= { enterprises 9467 }
universiteDeLaMediterranee        OBJECT IDENTIFIER ::= { enterprises 9468 }
starlabNvSa                       OBJECT IDENTIFIER ::= { enterprises 9469 }
alfaconTeamSpA                    OBJECT IDENTIFIER ::= { enterprises 9470 }
lemonPlanet                       OBJECT IDENTIFIER ::= { enterprises 9471 }
jejeorg                           OBJECT IDENTIFIER ::= { enterprises 9472 }
safestoneTechnologiesPLC          OBJECT IDENTIFIER ::= { enterprises 9473 }
sirt                              OBJECT IDENTIFIER ::= { enterprises 9474 }
three65Corporation                OBJECT IDENTIFIER ::= { enterprises 9475 }
esrf                              OBJECT IDENTIFIER ::= { enterprises 9476 }
marketCentral                     OBJECT IDENTIFIER ::= { enterprises 9477 }
myluckyworld                      OBJECT IDENTIFIER ::= { enterprises 9478 }
webcollage                        OBJECT IDENTIFIER ::= { enterprises 9479 }
notusKeyLimited                   OBJECT IDENTIFIER ::= { enterprises 9480 }
backerSoftwareResearch            OBJECT IDENTIFIER ::= { enterprises 9481 }
ensLyon                           OBJECT IDENTIFIER ::= { enterprises 9482 }
psiAG                             OBJECT IDENTIFIER ::= { enterprises 9483 }
isionFrance                       OBJECT IDENTIFIER ::= { enterprises 9484 }
futurocom                         OBJECT IDENTIFIER ::= { enterprises 9485 }
powwowGermany                     OBJECT IDENTIFIER ::= { enterprises 9486 }
saardata                          OBJECT IDENTIFIER ::= { enterprises 9487 }
circuitCityStores                 OBJECT IDENTIFIER ::= { enterprises 9488 }
taikoElectricWorks                OBJECT IDENTIFIER ::= { enterprises 9489 }
scoreconInternational             OBJECT IDENTIFIER ::= { enterprises 9490 }
vectan                            OBJECT IDENTIFIER ::= { enterprises 9491 }
theCobaltGroup                    OBJECT IDENTIFIER ::= { enterprises 9492 }
iopenTechnologies                 OBJECT IDENTIFIER ::= { enterprises 9493 }
ifilm                             OBJECT IDENTIFIER ::= { enterprises 9494 }
etee2knet                         OBJECT IDENTIFIER ::= { enterprises 9495 }
atAndtEnhancedNetworkServices     OBJECT IDENTIFIER ::= { enterprises 9496 }
idiniCorporation                  OBJECT IDENTIFIER ::= { enterprises 9497 }
telekommunikationMittleresRuhrgebiet OBJECT IDENTIFIER ::= { enterprises 9498 }
exacubeSystem                     OBJECT IDENTIFIER ::= { enterprises 9499 }
byteAlliance                      OBJECT IDENTIFIER ::= { enterprises 9500 }
svaINTRUSIONCOMCoLTD              OBJECT IDENTIFIER ::= { enterprises 9501 }
rossTechnologyGroup               OBJECT IDENTIFIER ::= { enterprises 9502 }
telemovilElSalvador               OBJECT IDENTIFIER ::= { enterprises 9503 }
topsnet                           OBJECT IDENTIFIER ::= { enterprises 9504 }
boneLabs                          OBJECT IDENTIFIER ::= { enterprises 9505 }
realSolutions                     OBJECT IDENTIFIER ::= { enterprises 9506 }
whartonElectronics                OBJECT IDENTIFIER ::= { enterprises 9507 }
mobilespear                       OBJECT IDENTIFIER ::= { enterprises 9508 }
enkashPaymentNetwork              OBJECT IDENTIFIER ::= { enterprises 9509 }
konsys                            OBJECT IDENTIFIER ::= { enterprises 9510 }
vulkanTechnic                     OBJECT IDENTIFIER ::= { enterprises 9511 }
onlineConsulting                  OBJECT IDENTIFIER ::= { enterprises 9512 }
exacommSystems                    OBJECT IDENTIFIER ::= { enterprises 9513 }
konicaBusinessTechnologies        OBJECT IDENTIFIER ::= { enterprises 9514 }
sugarCreekPackingCo               OBJECT IDENTIFIER ::= { enterprises 9515 }
digitalWorldServices              OBJECT IDENTIFIER ::= { enterprises 9516 }
sanrise                           OBJECT IDENTIFIER ::= { enterprises 9517 }
prattAndWhitney                   OBJECT IDENTIFIER ::= { enterprises 9518 }
sowardNetworkSolutions            OBJECT IDENTIFIER ::= { enterprises 9519 }
phase2SoftwareCorp                OBJECT IDENTIFIER ::= { enterprises 9520 }
pedComputers                      OBJECT IDENTIFIER ::= { enterprises 9521 }
personeta                         OBJECT IDENTIFIER ::= { enterprises 9522 }
stE15                             OBJECT IDENTIFIER ::= { enterprises 9523 }
andiamoSystems                    OBJECT IDENTIFIER ::= { enterprises 9524 }
bbcMonitoring                     OBJECT IDENTIFIER ::= { enterprises 9525 }
shawmutDesignAndConstruction      OBJECT IDENTIFIER ::= { enterprises 9526 }
inkrasNetworksCorporation         OBJECT IDENTIFIER ::= { enterprises 9527 }
iyago                             OBJECT IDENTIFIER ::= { enterprises 9528 }
globalRelay                       OBJECT IDENTIFIER ::= { enterprises 9529 }
cqurCOM                           OBJECT IDENTIFIER ::= { enterprises 9530 }
integraTelecom                    OBJECT IDENTIFIER ::= { enterprises 9531 }
group1Software                    OBJECT IDENTIFIER ::= { enterprises 9532 }
truedisk                          OBJECT IDENTIFIER ::= { enterprises 9533 }
handrew                           OBJECT IDENTIFIER ::= { enterprises 9534 }
zuritaSolutions                   OBJECT IDENTIFIER ::= { enterprises 9535 }
masseyUniversity                  OBJECT IDENTIFIER ::= { enterprises 9536 }
navoxCorporation                  OBJECT IDENTIFIER ::= { enterprises 9537 }
storageway                        OBJECT IDENTIFIER ::= { enterprises 9538 }
stsn                              OBJECT IDENTIFIER ::= { enterprises 9539 }
altentia                          OBJECT IDENTIFIER ::= { enterprises 9540 }
lokaalNetwerkGravenstraat         OBJECT IDENTIFIER ::= { enterprises 9541 }
collegeOfEngineeringAndComputerScience OBJECT IDENTIFIER ::= { enterprises 9542 }
schwoo                            OBJECT IDENTIFIER ::= { enterprises 9543 }
electricalAndComputerEngineeringDept OBJECT IDENTIFIER ::= { enterprises 9544 }
stateStreetCorp                   OBJECT IDENTIFIER ::= { enterprises 9545 }
dominetSystems                    OBJECT IDENTIFIER ::= { enterprises 9546 }
fooCorporation                    OBJECT IDENTIFIER ::= { enterprises 9547 }
datachron                         OBJECT IDENTIFIER ::= { enterprises 9548 }
southernNetworkServices           OBJECT IDENTIFIER ::= { enterprises 9549 }
vox2voxCommunications             OBJECT IDENTIFIER ::= { enterprises 9550 }
kompuArtStudiuKomputerowe         OBJECT IDENTIFIER ::= { enterprises 9551 }
financialIQPty                    OBJECT IDENTIFIER ::= { enterprises 9552 }
automaton                         OBJECT IDENTIFIER ::= { enterprises 9553 }
clearRiverTechnologies            OBJECT IDENTIFIER ::= { enterprises 9554 }
asiainfoTechnologies              OBJECT IDENTIFIER ::= { enterprises 9555 }
greatWallBroadbankNetworkServiceCoLt OBJECT IDENTIFIER ::= { enterprises 9556 }
synso                             OBJECT IDENTIFIER ::= { enterprises 9557 }
kentRidgeDigitalLabs              OBJECT IDENTIFIER ::= { enterprises 9558 }
nationalSecurityResearchInstitute OBJECT IDENTIFIER ::= { enterprises 9559 }
secuicomCorporation               OBJECT IDENTIFIER ::= { enterprises 9560 }
netiaTelekomSA                    OBJECT IDENTIFIER ::= { enterprises 9561 }
magnumImperiumLimited             OBJECT IDENTIFIER ::= { enterprises 9562 }
suffolkCollege                    OBJECT IDENTIFIER ::= { enterprises 9563 }
mediaways                         OBJECT IDENTIFIER ::= { enterprises 9564 }
xeroxMobileSolutions              OBJECT IDENTIFIER ::= { enterprises 9565 }
hboCE                             OBJECT IDENTIFIER ::= { enterprises 9566 }
skilldealAG                       OBJECT IDENTIFIER ::= { enterprises 9567 }
datagrid                          OBJECT IDENTIFIER ::= { enterprises 9568 }
mgfLogistique                     OBJECT IDENTIFIER ::= { enterprises 9569 }
universityOfLeobenAustria         OBJECT IDENTIFIER ::= { enterprises 9570 }
erskineSystems                    OBJECT IDENTIFIER ::= { enterprises 9571 }
alienthingcom                     OBJECT IDENTIFIER ::= { enterprises 9572 }
mbComputrexMichaelBussmannEDVDienstleistungen OBJECT IDENTIFIER ::= { enterprises 9573 }
ncicClinicalTrials                OBJECT IDENTIFIER ::= { enterprises 9574 }
grupoDePrograma                   OBJECT IDENTIFIER ::= { enterprises 9575 }
cr                                OBJECT IDENTIFIER ::= { enterprises 9576 }
xtelligentITConsulting            OBJECT IDENTIFIER ::= { enterprises 9577 }
missionCriticalLinux              OBJECT IDENTIFIER ::= { enterprises 9578 }
followap                          OBJECT IDENTIFIER ::= { enterprises 9579 }
newHemisphereComputerServices     OBJECT IDENTIFIER ::= { enterprises 9580 }
quadOneTechnologiesPvt            OBJECT IDENTIFIER ::= { enterprises 9581 }
ccsCommunicationsPty              OBJECT IDENTIFIER ::= { enterprises 9582 }
bbcTechnologySupply               OBJECT IDENTIFIER ::= { enterprises 9583 }
lucentTechnologiesNADP            OBJECT IDENTIFIER ::= { enterprises 9584 }
nationalEnhanceTechnologyCorp     OBJECT IDENTIFIER ::= { enterprises 9585 }
debian                            OBJECT IDENTIFIER ::= { enterprises 9586 }
globalTrustAuthority              OBJECT IDENTIFIER ::= { enterprises 9587 }
swissLife                         OBJECT IDENTIFIER ::= { enterprises 9588 }
currenex                          OBJECT IDENTIFIER ::= { enterprises 9589 }
theMathWorks                      OBJECT IDENTIFIER ::= { enterprises 9590 }
thinkingCatEnterprises            OBJECT IDENTIFIER ::= { enterprises 9591 }
lukeCrawfordEnterprises           OBJECT IDENTIFIER ::= { enterprises 9592 }
sysnetInform                      OBJECT IDENTIFIER ::= { enterprises 9593 }
tapeProductsCompany               OBJECT IDENTIFIER ::= { enterprises 9594 }
zephionNetworks                   OBJECT IDENTIFIER ::= { enterprises 9595 }
pimpcode                          OBJECT IDENTIFIER ::= { enterprises 9596 }
blueSilicon                       OBJECT IDENTIFIER ::= { enterprises 9597 }
mbnaAmerica                       OBJECT IDENTIFIER ::= { enterprises 9598 }
ldapgurucom                       OBJECT IDENTIFIER ::= { enterprises 9599 }
williamsTechnologyConsultingServices OBJECT IDENTIFIER ::= { enterprises 9600 }
keewaytinookOkimakanak            OBJECT IDENTIFIER ::= { enterprises 9601 }
zoftech                           OBJECT IDENTIFIER ::= { enterprises 9602 }
afEnterprises                     OBJECT IDENTIFIER ::= { enterprises 9603 }
afuu                              OBJECT IDENTIFIER ::= { enterprises 9604 }
xyterraComputing                  OBJECT IDENTIFIER ::= { enterprises 9605 }
linvisionBV                       OBJECT IDENTIFIER ::= { enterprises 9606 }
mstc                              OBJECT IDENTIFIER ::= { enterprises 9607 }
ntelsoh                           OBJECT IDENTIFIER ::= { enterprises 9608 }
impasterCo                        OBJECT IDENTIFIER ::= { enterprises 9609 }
miloschnet                        OBJECT IDENTIFIER ::= { enterprises 9610 }
infosim                           OBJECT IDENTIFIER ::= { enterprises 9611 }
kobeSteel                         OBJECT IDENTIFIER ::= { enterprises 9612 }
nlsde                             OBJECT IDENTIFIER ::= { enterprises 9613 }
gocruisedirectcom                 OBJECT IDENTIFIER ::= { enterprises 9614 }
danfossAS                         OBJECT IDENTIFIER ::= { enterprises 9615 }
kreatelCommunicationsAB           OBJECT IDENTIFIER ::= { enterprises 9616 }
gsxGroupwareSolutions             OBJECT IDENTIFIER ::= { enterprises 9617 }
utrechtseWerkbedrijven            OBJECT IDENTIFIER ::= { enterprises 9618 }
nextraAustria                     OBJECT IDENTIFIER ::= { enterprises 9619 }
nationalLandSurveyOfFinland       OBJECT IDENTIFIER ::= { enterprises 9620 }
moloAFRIKASPEECHTECHNOLOGIES      OBJECT IDENTIFIER ::= { enterprises 9621 }
quescom                           OBJECT IDENTIFIER ::= { enterprises 9622 }
copenhagenAirports                OBJECT IDENTIFIER ::= { enterprises 9623 }
radianz                           OBJECT IDENTIFIER ::= { enterprises 9624 }
utesch                            OBJECT IDENTIFIER ::= { enterprises 9625 }
alessandroTriglia                 OBJECT IDENTIFIER ::= { enterprises 9626 }
sJShipinskiServices               OBJECT IDENTIFIER ::= { enterprises 9627 }
groupeCASINO                      OBJECT IDENTIFIER ::= { enterprises 9628 }
mastermindTechnologies            OBJECT IDENTIFIER ::= { enterprises 9629 }
eMoveum                           OBJECT IDENTIFIER ::= { enterprises 9630 }
esniff                            OBJECT IDENTIFIER ::= { enterprises 9631 }
individual                        OBJECT IDENTIFIER ::= { enterprises 9632 }
sedSystems                        OBJECT IDENTIFIER ::= { enterprises 9633 }
apiNetworks                       OBJECT IDENTIFIER ::= { enterprises 9634 }
tropicoSistemasETelecomunica      OBJECT IDENTIFIER ::= { enterprises 9635 }
netformat                         OBJECT IDENTIFIER ::= { enterprises 9636 }
allianceAndLeicesterPLC           OBJECT IDENTIFIER ::= { enterprises 9637 }
alphagraphics                     OBJECT IDENTIFIER ::= { enterprises 9638 }
appiumAB                          OBJECT IDENTIFIER ::= { enterprises 9639 }
astrolinkInternationalLLC         OBJECT IDENTIFIER ::= { enterprises 9640 }
azusaPacificUniversity            OBJECT IDENTIFIER ::= { enterprises 9641 }
bibopResearch                     OBJECT IDENTIFIER ::= { enterprises 9642 }
ceulpULBRA                        OBJECT IDENTIFIER ::= { enterprises 9643 }
cornwallInternetLimited           OBJECT IDENTIFIER ::= { enterprises 9644 }
courtadenet                       OBJECT IDENTIFIER ::= { enterprises 9645 }
cybectec                          OBJECT IDENTIFIER ::= { enterprises 9646 }
ewip                              OBJECT IDENTIFIER ::= { enterprises 9647 }
geekboneCoLTD                     OBJECT IDENTIFIER ::= { enterprises 9648 }
hochschuleBremen                  OBJECT IDENTIFIER ::= { enterprises 9649 }
infoclan                          OBJECT IDENTIFIER ::= { enterprises 9650 }
kele                              OBJECT IDENTIFIER ::= { enterprises 9651 }
lnsSA                             OBJECT IDENTIFIER ::= { enterprises 9652 }
mosotechLimited                   OBJECT IDENTIFIER ::= { enterprises 9653 }
nicFrance                         OBJECT IDENTIFIER ::= { enterprises 9654 }
optidevAB                         OBJECT IDENTIFIER ::= { enterprises 9655 }
routitBV                          OBJECT IDENTIFIER ::= { enterprises 9656 }
s-ScapeCommunications             OBJECT IDENTIFIER ::= { enterprises 9657 }
solers                            OBJECT IDENTIFIER ::= { enterprises 9658 }
synapsys                          OBJECT IDENTIFIER ::= { enterprises 9659 }
telecelComunica                   OBJECT IDENTIFIER ::= { enterprises 9660 }
teletronINC                       OBJECT IDENTIFIER ::= { enterprises 9661 }
tuevATTRUSTCenter                 OBJECT IDENTIFIER ::= { enterprises 9662 }
universiteLUMIERELYON2            OBJECT IDENTIFIER ::= { enterprises 9663 }
widgital                          OBJECT IDENTIFIER ::= { enterprises 9664 }
zygateCommunications              OBJECT IDENTIFIER ::= { enterprises 9665 }
alcatelOptronics                  OBJECT IDENTIFIER ::= { enterprises 9666 }
austarUnited                      OBJECT IDENTIFIER ::= { enterprises 9667 }
talentNetworkSecurityTechnologyCo OBJECT IDENTIFIER ::= { enterprises 9668 }
universityOfLondon                OBJECT IDENTIFIER ::= { enterprises 9669 }
broadi                            OBJECT IDENTIFIER ::= { enterprises 9670 }
aolTimeWarner                     OBJECT IDENTIFIER ::= { enterprises 9671 }
aproposTechnology                 OBJECT IDENTIFIER ::= { enterprises 9672 }
denisonUniversity                 OBJECT IDENTIFIER ::= { enterprises 9673 }
fingerhut                         OBJECT IDENTIFIER ::= { enterprises 9674 }
grupoFinancieroUno                OBJECT IDENTIFIER ::= { enterprises 9675 }
hottisde                          OBJECT IDENTIFIER ::= { enterprises 9676 }
hydriads                          OBJECT IDENTIFIER ::= { enterprises 9677 }
kuLeuven                          OBJECT IDENTIFIER ::= { enterprises 9678 }
mbalance                          OBJECT IDENTIFIER ::= { enterprises 9679 }
selectmetrics                     OBJECT IDENTIFIER ::= { enterprises 9680 }
mortgageSystemsInternational      OBJECT IDENTIFIER ::= { enterprises 9681 }
novadeck                          OBJECT IDENTIFIER ::= { enterprises 9682 }
plattsburghStateUniversity        OBJECT IDENTIFIER ::= { enterprises 9683 }
powerisenet                       OBJECT IDENTIFIER ::= { enterprises 9684 }
ranchNetworks                     OBJECT IDENTIFIER ::= { enterprises 9685 }
rubyNetworks                      OBJECT IDENTIFIER ::= { enterprises 9686 }
sapropertycom                     OBJECT IDENTIFIER ::= { enterprises 9687 }
tahoeNetworks                     OBJECT IDENTIFIER ::= { enterprises 9688 }
tbdNetworks                       OBJECT IDENTIFIER ::= { enterprises 9689 }
terralab                          OBJECT IDENTIFIER ::= { enterprises 9690 }
theChildren                       OBJECT IDENTIFIER ::= { enterprises 9691 }
toolObject                        OBJECT IDENTIFIER ::= { enterprises 9692 }
undSchoolOfMedicineAndHealthSciences OBJECT IDENTIFIER ::= { enterprises 9693 }
arborNetworks                     OBJECT IDENTIFIER ::= { enterprises 9694 }
encotone                          OBJECT IDENTIFIER ::= { enterprises 9695 }
uffizioIndiaSoftwareConsultantsPvt OBJECT IDENTIFIER ::= { enterprises 9696 }
accelance                         OBJECT IDENTIFIER ::= { enterprises 9697 }
aiaAustralia                      OBJECT IDENTIFIER ::= { enterprises 9698 }
axisConsulting                    OBJECT IDENTIFIER ::= { enterprises 9699 }
boehringerIngelheim               OBJECT IDENTIFIER ::= { enterprises 9700 }
commerceNTI                       OBJECT IDENTIFIER ::= { enterprises 9701 }
comtechBelgium                    OBJECT IDENTIFIER ::= { enterprises 9702 }
datafoundation                    OBJECT IDENTIFIER ::= { enterprises 9703 }
diversifiedResourcefulSolutions   OBJECT IDENTIFIER ::= { enterprises 9704 }
ecosGmbh                          OBJECT IDENTIFIER ::= { enterprises 9705 }
hackerslab                        OBJECT IDENTIFIER ::= { enterprises 9706 }
institutNationalPolytechniqueDeLorraine OBJECT IDENTIFIER ::= { enterprises 9707 }
jackMortonWorldwide               OBJECT IDENTIFIER ::= { enterprises 9708 }
microConnectPty                   OBJECT IDENTIFIER ::= { enterprises 9709 }
monzoonNetworksAG                 OBJECT IDENTIFIER ::= { enterprises 9710 }
novedia                           OBJECT IDENTIFIER ::= { enterprises 9711 }
obzen                             OBJECT IDENTIFIER ::= { enterprises 9712 }
operaSoftwareAS                   OBJECT IDENTIFIER ::= { enterprises 9713 }
ruhrsoft                          OBJECT IDENTIFIER ::= { enterprises 9714 }
sigmaAB                           OBJECT IDENTIFIER ::= { enterprises 9715 }
stateOfNorthDakota                OBJECT IDENTIFIER ::= { enterprises 9716 }
telecaAB                          OBJECT IDENTIFIER ::= { enterprises 9717 }
transactCommunications            OBJECT IDENTIFIER ::= { enterprises 9718 }
tronicplanetOnlineDatendienst     OBJECT IDENTIFIER ::= { enterprises 9719 }
tryx                              OBJECT IDENTIFIER ::= { enterprises 9720 }
vwrInternational                  OBJECT IDENTIFIER ::= { enterprises 9721 }
workhorseComputing                OBJECT IDENTIFIER ::= { enterprises 9722 }
coradiant                         OBJECT IDENTIFIER ::= { enterprises 9723 }
datacast                          OBJECT IDENTIFIER ::= { enterprises 9724 }
infoservice                       OBJECT IDENTIFIER ::= { enterprises 9725 }
nitroba                           OBJECT IDENTIFIER ::= { enterprises 9726 }
tryllian                          OBJECT IDENTIFIER ::= { enterprises 9727 }
wwfWortTon                        OBJECT IDENTIFIER ::= { enterprises 9728 }
everelite                         OBJECT IDENTIFIER ::= { enterprises 9729 }
solutusPtyLimited                 OBJECT IDENTIFIER ::= { enterprises 9730 }
down                              OBJECT IDENTIFIER ::= { enterprises 9731 }
adrenalineIngenierieMultimedia    OBJECT IDENTIFIER ::= { enterprises 9732 }
aralSystems                       OBJECT IDENTIFIER ::= { enterprises 9733 }
astrumSoftwareCorporation         OBJECT IDENTIFIER ::= { enterprises 9734 }
coredumpKy                        OBJECT IDENTIFIER ::= { enterprises 9735 }
dublinCityUniversity              OBJECT IDENTIFIER ::= { enterprises 9736 }
fourtheye                         OBJECT IDENTIFIER ::= { enterprises 9737 }
gedoplan                          OBJECT IDENTIFIER ::= { enterprises 9738 }
hobnobbersnet                     OBJECT IDENTIFIER ::= { enterprises 9739 }
ibeamBroadcastingCorporation      OBJECT IDENTIFIER ::= { enterprises 9740 }
keiren                            OBJECT IDENTIFIER ::= { enterprises 9741 }
descomCONSULTING                  OBJECT IDENTIFIER ::= { enterprises 9742 }
nchica                            OBJECT IDENTIFIER ::= { enterprises 9743 }
peoplecallcom                     OBJECT IDENTIFIER ::= { enterprises 9744 }
radixControls                     OBJECT IDENTIFIER ::= { enterprises 9745 }
rfnetTechnologiesPte              OBJECT IDENTIFIER ::= { enterprises 9746 }
roamingtest                       OBJECT IDENTIFIER ::= { enterprises 9747 }
rowSoftwareAndWebDesign           OBJECT IDENTIFIER ::= { enterprises 9748 }
spectralinkCorporation            OBJECT IDENTIFIER ::= { enterprises 9749 }
thePillars                        OBJECT IDENTIFIER ::= { enterprises 9750 }
trevilonCorp                      OBJECT IDENTIFIER ::= { enterprises 9751 }
universityOfMissouri              OBJECT IDENTIFIER ::= { enterprises 9752 }
vernierNetworks                   OBJECT IDENTIFIER ::= { enterprises 9753 }
vertisDSGChicago                  OBJECT IDENTIFIER ::= { enterprises 9754 }
webastoInformationssysteme        OBJECT IDENTIFIER ::= { enterprises 9755 }
woerdErdmengerAndWolterGbR        OBJECT IDENTIFIER ::= { enterprises 9756 }
aralAktiengesellschaftAndCoKG     OBJECT IDENTIFIER ::= { enterprises 9757 }
metadigm                          OBJECT IDENTIFIER ::= { enterprises 9758 }
aplicacionesYConsultoria          OBJECT IDENTIFIER ::= { enterprises 9759 }
cellcast                          OBJECT IDENTIFIER ::= { enterprises 9760 }
corporateExpress                  OBJECT IDENTIFIER ::= { enterprises 9761 }
datacomSystems                    OBJECT IDENTIFIER ::= { enterprises 9762 }
eonite                            OBJECT IDENTIFIER ::= { enterprises 9763 }
forschungszentrumRossendorfEV     OBJECT IDENTIFIER ::= { enterprises 9764 }
ilryungTELESYS                    OBJECT IDENTIFIER ::= { enterprises 9765 }
josephSDovganDDSMS                OBJECT IDENTIFIER ::= { enterprises 9766 }
lectronCO                         OBJECT IDENTIFIER ::= { enterprises 9767 }
lynchburgCollege                  OBJECT IDENTIFIER ::= { enterprises 9768 }
nuanceCommunications              OBJECT IDENTIFIER ::= { enterprises 9769 }
openofficeorg                     OBJECT IDENTIFIER ::= { enterprises 9770 }
paionCo                           OBJECT IDENTIFIER ::= { enterprises 9771 }
pentasecurity                     OBJECT IDENTIFIER ::= { enterprises 9772 }
spunheadIndustries                OBJECT IDENTIFIER ::= { enterprises 9773 }
streetsOnline                     OBJECT IDENTIFIER ::= { enterprises 9774 }
tntTechnology                     OBJECT IDENTIFIER ::= { enterprises 9775 }
wirelessNetworkServices           OBJECT IDENTIFIER ::= { enterprises 9776 }
arelnet                           OBJECT IDENTIFIER ::= { enterprises 9777 }
axonlink                          OBJECT IDENTIFIER ::= { enterprises 9778 }
empireStateCollege                OBJECT IDENTIFIER ::= { enterprises 9779 }
entrepriseDesPostesEtT            OBJECT IDENTIFIER ::= { enterprises 9780 }
jerntorgetSverigeAB               OBJECT IDENTIFIER ::= { enterprises 9781 }
jmFamilyEnterprises               OBJECT IDENTIFIER ::= { enterprises 9782 }
vayusphere                        OBJECT IDENTIFIER ::= { enterprises 9783 }
icoserveInformationTechnologies   OBJECT IDENTIFIER ::= { enterprises 9784 }
praxisTechnicalGroup              OBJECT IDENTIFIER ::= { enterprises 9785 }
aisAngewandteInformationsSysteme  OBJECT IDENTIFIER ::= { enterprises 9786 }
activestateCorp                   OBJECT IDENTIFIER ::= { enterprises 9787 }
advisorTechnologiesLimited        OBJECT IDENTIFIER ::= { enterprises 9788 }
astaroAG                          OBJECT IDENTIFIER ::= { enterprises 9789 }
australiaOnLine                   OBJECT IDENTIFIER ::= { enterprises 9790 }
centreDeTelecomunicacionsITecnologiesDeLaInformacio OBJECT IDENTIFIER ::= { enterprises 9791 }
clayhillKG                        OBJECT IDENTIFIER ::= { enterprises 9792 }
cloudshieldTechnologies           OBJECT IDENTIFIER ::= { enterprises 9793 }
cytben                            OBJECT IDENTIFIER ::= { enterprises 9794 }
ebsDealingResources               OBJECT IDENTIFIER ::= { enterprises 9795 }
europeanNetworkExchange           OBJECT IDENTIFIER ::= { enterprises 9796 }
everSpZOo                         OBJECT IDENTIFIER ::= { enterprises 9797 }
griffIT                           OBJECT IDENTIFIER ::= { enterprises 9798 }
holosSoftware                     OBJECT IDENTIFIER ::= { enterprises 9799 }
init8                             OBJECT IDENTIFIER ::= { enterprises 9800 }
isisFrontierCommunications        OBJECT IDENTIFIER ::= { enterprises 9801 }
iufmDeRouen                       OBJECT IDENTIFIER ::= { enterprises 9802 }
l3CommunicationSystemsEast        OBJECT IDENTIFIER ::= { enterprises 9803 }
lefthandNetworks                  OBJECT IDENTIFIER ::= { enterprises 9804 }
nevedaCitySchoolDistrict          OBJECT IDENTIFIER ::= { enterprises 9805 }
prideIndustries                   OBJECT IDENTIFIER ::= { enterprises 9806 }
prismHoldingLimited               OBJECT IDENTIFIER ::= { enterprises 9807 }
rockleaSpinningMillsPty           OBJECT IDENTIFIER ::= { enterprises 9808 }
root                              OBJECT IDENTIFIER ::= { enterprises 9809 }
sagent                            OBJECT IDENTIFIER ::= { enterprises 9810 }
secureApplianceSystems            OBJECT IDENTIFIER ::= { enterprises 9811 }
solnet                            OBJECT IDENTIFIER ::= { enterprises 9812 }
tabQueenslandLimited              OBJECT IDENTIFIER ::= { enterprises 9813 }
teliaITServiceAB                  OBJECT IDENTIFIER ::= { enterprises 9814 }
vspace                            OBJECT IDENTIFIER ::= { enterprises 9815 }
wanwall                           OBJECT IDENTIFIER ::= { enterprises 9816 }
wavenet                           OBJECT IDENTIFIER ::= { enterprises 9817 }
xwave                             OBJECT IDENTIFIER ::= { enterprises 9818 }
ylezTechnologiesPte               OBJECT IDENTIFIER ::= { enterprises 9819 }
zoxIT                             OBJECT IDENTIFIER ::= { enterprises 9820 }
zoznamSro                         OBJECT IDENTIFIER ::= { enterprises 9821 }
accellaTechnologiesCo             OBJECT IDENTIFIER ::= { enterprises 9822 }
diageo                            OBJECT IDENTIFIER ::= { enterprises 9823 }
gentek                            OBJECT IDENTIFIER ::= { enterprises 9824 }
geospiza                          OBJECT IDENTIFIER ::= { enterprises 9825 }
imagicodeStudios                  OBJECT IDENTIFIER ::= { enterprises 9826 }
neocles                           OBJECT IDENTIFIER ::= { enterprises 9827 }
pgamapd                           OBJECT IDENTIFIER ::= { enterprises 9828 }
sait                              OBJECT IDENTIFIER ::= { enterprises 9829 }
thunderbird                       OBJECT IDENTIFIER ::= { enterprises 9830 }
vivre                             OBJECT IDENTIFIER ::= { enterprises 9831 }
solobird                          OBJECT IDENTIFIER ::= { enterprises 9832 }
legendHoldings                    OBJECT IDENTIFIER ::= { enterprises 9833 }
agencjaUslugInformatycznychARTCOMP OBJECT IDENTIFIER ::= { enterprises 9834 }
alienNetwork                      OBJECT IDENTIFIER ::= { enterprises 9835 }
aokBayern                         OBJECT IDENTIFIER ::= { enterprises 9836 }
ballStateUniversity               OBJECT IDENTIFIER ::= { enterprises 9837 }
broadviewNetworks                 OBJECT IDENTIFIER ::= { enterprises 9838 }
carel                             OBJECT IDENTIFIER ::= { enterprises 9839 }
carreregroup                      OBJECT IDENTIFIER ::= { enterprises 9840 }
christianDusekEDVDienstleistungen OBJECT IDENTIFIER ::= { enterprises 9841 }
etNetworks                        OBJECT IDENTIFIER ::= { enterprises 9842 }
kaiIndustries                     OBJECT IDENTIFIER ::= { enterprises 9843 }
kansasStateUniversity             OBJECT IDENTIFIER ::= { enterprises 9844 }
lanbirdTechnologyCo               OBJECT IDENTIFIER ::= { enterprises 9845 }
lipLaborat                        OBJECT IDENTIFIER ::= { enterprises 9846 }
listencom                         OBJECT IDENTIFIER ::= { enterprises 9847 }
louJohnson                        OBJECT IDENTIFIER ::= { enterprises 9848 }
mWebIndonesia                     OBJECT IDENTIFIER ::= { enterprises 9849 }
nextgig                           OBJECT IDENTIFIER ::= { enterprises 9850 }
nttSOFT                           OBJECT IDENTIFIER ::= { enterprises 9851 }
odigo                             OBJECT IDENTIFIER ::= { enterprises 9852 }
paymentTechnologies               OBJECT IDENTIFIER ::= { enterprises 9853 }
redBoxRecordersLimited            OBJECT IDENTIFIER ::= { enterprises 9854 }
shawsoft                          OBJECT IDENTIFIER ::= { enterprises 9855 }
uclaCommunicationsTechnologyServices OBJECT IDENTIFIER ::= { enterprises 9856 }
unicomAnESecurityCompany          OBJECT IDENTIFIER ::= { enterprises 9857 }
universityOfMaryland              OBJECT IDENTIFIER ::= { enterprises 9858 }
universityOfMedicineAndDentistryOfNewJersey OBJECT IDENTIFIER ::= { enterprises 9859 }
vizionalTechnologies              OBJECT IDENTIFIER ::= { enterprises 9860 }
webdesignInternetService          OBJECT IDENTIFIER ::= { enterprises 9861 }
clarediCorporation                OBJECT IDENTIFIER ::= { enterprises 9862 }
datarojahnAS                      OBJECT IDENTIFIER ::= { enterprises 9863 }
jWalterThomposonCompany           OBJECT IDENTIFIER ::= { enterprises 9864 }
karmanosCancerInstitute           OBJECT IDENTIFIER ::= { enterprises 9865 }
outokumpuOyj                      OBJECT IDENTIFIER ::= { enterprises 9866 }
thirdRailAmericas                 OBJECT IDENTIFIER ::= { enterprises 9867 }
millinetCo                        OBJECT IDENTIFIER ::= { enterprises 9868 }
networkLaboratoryOfNankaiUniversity OBJECT IDENTIFIER ::= { enterprises 9869 }
graviton                          OBJECT IDENTIFIER ::= { enterprises 9870 }
findlaterWineMerchants            OBJECT IDENTIFIER ::= { enterprises 9871 }
gez                               OBJECT IDENTIFIER ::= { enterprises 9872 }
viterraAG                         OBJECT IDENTIFIER ::= { enterprises 9873 }
boAkademiUniversity               OBJECT IDENTIFIER ::= { enterprises 9874 }
availableSUPPLY                   OBJECT IDENTIFIER ::= { enterprises 9875 }
b2iToulouse                       OBJECT IDENTIFIER ::= { enterprises 9876 }
californiaStateUniversity         OBJECT IDENTIFIER ::= { enterprises 9877 }
caregroupHealthCareSystem         OBJECT IDENTIFIER ::= { enterprises 9878 }
coxCommunications                 OBJECT IDENTIFIER ::= { enterprises 9879 }
dataJunctionCorporation           OBJECT IDENTIFIER ::= { enterprises 9880 }
eitaTechnologies                  OBJECT IDENTIFIER ::= { enterprises 9881 }
flashTechnology                   OBJECT IDENTIFIER ::= { enterprises 9882 }
freeTradeOnline                   OBJECT IDENTIFIER ::= { enterprises 9883 }
frostEDV                          OBJECT IDENTIFIER ::= { enterprises 9884 }
greenPacket                       OBJECT IDENTIFIER ::= { enterprises 9885 }
incendiaryNetworks                OBJECT IDENTIFIER ::= { enterprises 9886 }
kristinaInternetBusinessSolutions OBJECT IDENTIFIER ::= { enterprises 9887 }
linuxTerminalServerProject        OBJECT IDENTIFIER ::= { enterprises 9888 }
maxxioTechnologiesAG              OBJECT IDENTIFIER ::= { enterprises 9889 }
mediaGeneral2                     OBJECT IDENTIFIER ::= { enterprises 9890 }
mensatec                          OBJECT IDENTIFIER ::= { enterprises 9891 }
oregonGraduateInstituteOfScienceAndTechnology OBJECT IDENTIFIER ::= { enterprises 9892 }
paranormalSweden                  OBJECT IDENTIFIER ::= { enterprises 9893 }
polestarCorp                      OBJECT IDENTIFIER ::= { enterprises 9894 }
project49AG                       OBJECT IDENTIFIER ::= { enterprises 9895 }
rAndrAssoci                       OBJECT IDENTIFIER ::= { enterprises 9896 }
seranoaNetworks                   OBJECT IDENTIFIER ::= { enterprises 9897 }
shindengenElectricMfgCo           OBJECT IDENTIFIER ::= { enterprises 9898 }
stinnesAG                         OBJECT IDENTIFIER ::= { enterprises 9899 }
telekomAppliedBusinessSdnBhd      OBJECT IDENTIFIER ::= { enterprises 9900 }
theCollegeOfWilliamAndMary        OBJECT IDENTIFIER ::= { enterprises 9901 }
theUniversityOfChicago            OBJECT IDENTIFIER ::= { enterprises 9902 }
tiSQUARETechnology                OBJECT IDENTIFIER ::= { enterprises 9903 }
universityOfNebraskaLincoln       OBJECT IDENTIFIER ::= { enterprises 9904 }
volubill                          OBJECT IDENTIFIER ::= { enterprises 9905 }
xteraCommunications               OBJECT IDENTIFIER ::= { enterprises 9906 }
akkayaConsulting                  OBJECT IDENTIFIER ::= { enterprises 9907 }
hitrustcom                        OBJECT IDENTIFIER ::= { enterprises 9908 }
pacificTechnologyServices         OBJECT IDENTIFIER ::= { enterprises 9909 }
absoluteSoftwareCorp              OBJECT IDENTIFIER ::= { enterprises 9910 }
bantu                             OBJECT IDENTIFIER ::= { enterprises 9911 }
baragaTelephoneCompany            OBJECT IDENTIFIER ::= { enterprises 9912 }
cerebraIntergratedTechnologies    OBJECT IDENTIFIER ::= { enterprises 9913 }
charterCommunications             OBJECT IDENTIFIER ::= { enterprises 9914 }
commtouchSoftware                 OBJECT IDENTIFIER ::= { enterprises 9915 }
datekOnlineHoldingsCorp           OBJECT IDENTIFIER ::= { enterprises 9916 }
delosPaymentSystems               OBJECT IDENTIFIER ::= { enterprises 9917 }
docNOAANESDISNODC                 OBJECT IDENTIFIER ::= { enterprises 9918 }
earth9comPte                      OBJECT IDENTIFIER ::= { enterprises 9919 }
enetco                            OBJECT IDENTIFIER ::= { enterprises 9920 }
ergoVersicherungsgruppeAG         OBJECT IDENTIFIER ::= { enterprises 9921 }
esignAustraliaLimited             OBJECT IDENTIFIER ::= { enterprises 9922 }
europeanSouthernObservatory       OBJECT IDENTIFIER ::= { enterprises 9923 }
exciteUK                          OBJECT IDENTIFIER ::= { enterprises 9924 }
finestWebs                        OBJECT IDENTIFIER ::= { enterprises 9925 }
genieNetworkResourceManagement    OBJECT IDENTIFIER ::= { enterprises 9926 }
icehouseNetServices               OBJECT IDENTIFIER ::= { enterprises 9927 }
inetrify                          OBJECT IDENTIFIER ::= { enterprises 9928 }
integralConcepts                  OBJECT IDENTIFIER ::= { enterprises 9929 }
internexusPlc                     OBJECT IDENTIFIER ::= { enterprises 9930 }
inti                              OBJECT IDENTIFIER ::= { enterprises 9931 }
ipfilter                          OBJECT IDENTIFIER ::= { enterprises 9932 }
jaars                             OBJECT IDENTIFIER ::= { enterprises 9933 }
janusResearchGroup                OBJECT IDENTIFIER ::= { enterprises 9934 }
louisianaTechUniversity           OBJECT IDENTIFIER ::= { enterprises 9935 }
massconfusioncom                  OBJECT IDENTIFIER ::= { enterprises 9936 }
maxxanSystems                     OBJECT IDENTIFIER ::= { enterprises 9937 }
mercuryCorporation                OBJECT IDENTIFIER ::= { enterprises 9938 }
mernetSecurity                    OBJECT IDENTIFIER ::= { enterprises 9939 }
nineTilesNetworks                 OBJECT IDENTIFIER ::= { enterprises 9940 }
objectiveRealityComputerLLC       OBJECT IDENTIFIER ::= { enterprises 9941 }
optimationSoftwareEngineering     OBJECT IDENTIFIER ::= { enterprises 9942 }
prometheon                        OBJECT IDENTIFIER ::= { enterprises 9943 }
sias                              OBJECT IDENTIFIER ::= { enterprises 9944 }
siemensBusinessServicesAB         OBJECT IDENTIFIER ::= { enterprises 9945 }
softsolIndiaLimitedn              OBJECT IDENTIFIER ::= { enterprises 9946 }
swalesAerospace                   OBJECT IDENTIFIER ::= { enterprises 9947 }
telekurierGesmbHAndCoKG           OBJECT IDENTIFIER ::= { enterprises 9948 }
ubiquitousCorp                    OBJECT IDENTIFIER ::= { enterprises 9949 }
visionaryCommunications           OBJECT IDENTIFIER ::= { enterprises 9950 }
wirelessM2M                       OBJECT IDENTIFIER ::= { enterprises 9951 }
wuhantit                          OBJECT IDENTIFIER ::= { enterprises 9952 }
bertelsmannGamechannel            OBJECT IDENTIFIER ::= { enterprises 9953 }
craigbuchekcom                    OBJECT IDENTIFIER ::= { enterprises 9954 }
crispHughesEvansLLP               OBJECT IDENTIFIER ::= { enterprises 9955 }
planarSystems                     OBJECT IDENTIFIER ::= { enterprises 9956 }
dynamicEquilibriumPty             OBJECT IDENTIFIER ::= { enterprises 9957 }
formula400                        OBJECT IDENTIFIER ::= { enterprises 9958 }
nods                              OBJECT IDENTIFIER ::= { enterprises 9959 }
nuisyscom                         OBJECT IDENTIFIER ::= { enterprises 9960 }
fundsxpressFinancialNetwork       OBJECT IDENTIFIER ::= { enterprises 9961 }
vircio                            OBJECT IDENTIFIER ::= { enterprises 9962 }
advancedComputerTechnologies      OBJECT IDENTIFIER ::= { enterprises 9963 }
km                                OBJECT IDENTIFIER ::= { enterprises 9964 }
amministrazioneProvincialeDiGrosseto OBJECT IDENTIFIER ::= { enterprises 9965 }
beijingHuahuanElectronics         OBJECT IDENTIFIER ::= { enterprises 9966 }
bluesocket                        OBJECT IDENTIFIER ::= { enterprises 9967 }
britishAntarcticSurvey            OBJECT IDENTIFIER ::= { enterprises 9968 }
condatAG                          OBJECT IDENTIFIER ::= { enterprises 9969 }
custodixNV                        OBJECT IDENTIFIER ::= { enterprises 9970 }
cybertel                          OBJECT IDENTIFIER ::= { enterprises 9971 }
emuliveImagingCorporation         OBJECT IDENTIFIER ::= { enterprises 9972 }
flexsys                           OBJECT IDENTIFIER ::= { enterprises 9973 }
internetTransactionServices       OBJECT IDENTIFIER ::= { enterprises 9974 }
jwJensen                          OBJECT IDENTIFIER ::= { enterprises 9975 }
flexsys2                          OBJECT IDENTIFIER ::= { enterprises 9976 }
jobpilotAG                        OBJECT IDENTIFIER ::= { enterprises 9977 }
linuxkorea                        OBJECT IDENTIFIER ::= { enterprises 9978 }
mabusede                          OBJECT IDENTIFIER ::= { enterprises 9979 }
mWebSouthAfrica                   OBJECT IDENTIFIER ::= { enterprises 9980 }
netAndtrade                       OBJECT IDENTIFIER ::= { enterprises 9981 }
netengine                         OBJECT IDENTIFIER ::= { enterprises 9982 }
netstech                          OBJECT IDENTIFIER ::= { enterprises 9983 }
osmosislatina                     OBJECT IDENTIFIER ::= { enterprises 9984 }
ric                               OBJECT IDENTIFIER ::= { enterprises 9985 }
sencore                           OBJECT IDENTIFIER ::= { enterprises 9986 }
signet                            OBJECT IDENTIFIER ::= { enterprises 9987 }
smartTechnologyEnablers           OBJECT IDENTIFIER ::= { enterprises 9988 }
stochastix                        OBJECT IDENTIFIER ::= { enterprises 9989 }
stonebranch                       OBJECT IDENTIFIER ::= { enterprises 9990 }
synchrone                         OBJECT IDENTIFIER ::= { enterprises 9991 }
terion                            OBJECT IDENTIFIER ::= { enterprises 9992 }
terumoMedicalCorporation          OBJECT IDENTIFIER ::= { enterprises 9993 }
theLinuxBoxCorporation            OBJECT IDENTIFIER ::= { enterprises 9994 }
thinkengineNetworks               OBJECT IDENTIFIER ::= { enterprises 9995 }
villanovaUniversity               OBJECT IDENTIFIER ::= { enterprises 9996 }
virtualELearningGroup             OBJECT IDENTIFIER ::= { enterprises 9997 }
wyndCommunications                OBJECT IDENTIFIER ::= { enterprises 9998 }
zerna                             OBJECT IDENTIFIER ::= { enterprises 9999 }
mapinfoCorporation                OBJECT IDENTIFIER ::= { enterprises 10000 }
blioCorporation                   OBJECT IDENTIFIER ::= { enterprises 10001 }
frogfootNetworks                  OBJECT IDENTIFIER ::= { enterprises 10002 }
ipONE                             OBJECT IDENTIFIER ::= { enterprises 10003 }
johnchildresscom                  OBJECT IDENTIFIER ::= { enterprises 10004 }
pureNetworX                       OBJECT IDENTIFIER ::= { enterprises 10005 }
santon                            OBJECT IDENTIFIER ::= { enterprises 10006 }
rfInnovationsPty                  OBJECT IDENTIFIER ::= { enterprises 10007 }
groupeESIEEParis                  OBJECT IDENTIFIER ::= { enterprises 10008 }
krystalboxTechnologies            OBJECT IDENTIFIER ::= { enterprises 10009 }
networkStorageSolutions           OBJECT IDENTIFIER ::= { enterprises 10010 }
advancedSimulationTechnology      OBJECT IDENTIFIER ::= { enterprises 10011 }
alterniumSA                       OBJECT IDENTIFIER ::= { enterprises 10012 }
caledo                            OBJECT IDENTIFIER ::= { enterprises 10013 }
cerias                            OBJECT IDENTIFIER ::= { enterprises 10014 }
certificationCentre               OBJECT IDENTIFIER ::= { enterprises 10015 }
computerAndCommunicationsInnovations OBJECT IDENTIFIER ::= { enterprises 10016 }
crewaveCo                         OBJECT IDENTIFIER ::= { enterprises 10017 }
doublePrecision                   OBJECT IDENTIFIER ::= { enterprises 10018 }
fenSystems                        OBJECT IDENTIFIER ::= { enterprises 10019 }
globe                             OBJECT IDENTIFIER ::= { enterprises 10020 }
goodTechnology                    OBJECT IDENTIFIER ::= { enterprises 10021 }
iconnect                          OBJECT IDENTIFIER ::= { enterprises 10022 }
ima                               OBJECT IDENTIFIER ::= { enterprises 10023 }
integratedTechnologyExpress       OBJECT IDENTIFIER ::= { enterprises 10024 }
interland                         OBJECT IDENTIFIER ::= { enterprises 10025 }
interloci                         OBJECT IDENTIFIER ::= { enterprises 10026 }
internetDataSystemsSA             OBJECT IDENTIFIER ::= { enterprises 10027 }
level42Networks                   OBJECT IDENTIFIER ::= { enterprises 10028 }
menAndMice                        OBJECT IDENTIFIER ::= { enterprises 10029 }
mudiagaObada                      OBJECT IDENTIFIER ::= { enterprises 10030 }
niiefaCTCCYCLONE                  OBJECT IDENTIFIER ::= { enterprises 10031 }
onemedia                          OBJECT IDENTIFIER ::= { enterprises 10032 }
opensosSB                         OBJECT IDENTIFIER ::= { enterprises 10033 }
osixAB                            OBJECT IDENTIFIER ::= { enterprises 10034 }
sayTechnologies                   OBJECT IDENTIFIER ::= { enterprises 10035 }
timesNSystems                     OBJECT IDENTIFIER ::= { enterprises 10036 }
ultimatePeopleCompany             OBJECT IDENTIFIER ::= { enterprises 10037 }
universityOfTexasHealthScienceCenterAtSanAntonio OBJECT IDENTIFIER ::= { enterprises 10038 }
videotek                          OBJECT IDENTIFIER ::= { enterprises 10039 }
yonseiUniversity                  OBJECT IDENTIFIER ::= { enterprises 10040 }
zonePLSc                          OBJECT IDENTIFIER ::= { enterprises 10041 }
commaFlex                         OBJECT IDENTIFIER ::= { enterprises 10042 }
etimeCapital                      OBJECT IDENTIFIER ::= { enterprises 10043 }
frbPar                            OBJECT IDENTIFIER ::= { enterprises 10044 }
netformfiveInformationstechnologie OBJECT IDENTIFIER ::= { enterprises 10045 }
protek                            OBJECT IDENTIFIER ::= { enterprises 10046 }
servocomp                         OBJECT IDENTIFIER ::= { enterprises 10047 }
vxlETech                          OBJECT IDENTIFIER ::= { enterprises 10048 }
webrelay                          OBJECT IDENTIFIER ::= { enterprises 10049 }
danaCorporation                   OBJECT IDENTIFIER ::= { enterprises 10050 }
eftiaOSSSolutions                 OBJECT IDENTIFIER ::= { enterprises 10051 }
electronicCommerceLink            OBJECT IDENTIFIER ::= { enterprises 10052 }
keys                              OBJECT IDENTIFIER ::= { enterprises 10053 }
netvalueSA                        OBJECT IDENTIFIER ::= { enterprises 10054 }
roaringPenguinSoftware            OBJECT IDENTIFIER ::= { enterprises 10055 }
appdancerNetworks                 OBJECT IDENTIFIER ::= { enterprises 10056 }
emteSistemas                      OBJECT IDENTIFIER ::= { enterprises 10057 }
hauri                             OBJECT IDENTIFIER ::= { enterprises 10058 }
sanrad                            OBJECT IDENTIFIER ::= { enterprises 10059 }
seltaTelematica                   OBJECT IDENTIFIER ::= { enterprises 10060 }
pacificInfoTechCorp               OBJECT IDENTIFIER ::= { enterprises 10061 }
comsquaredSystems                 OBJECT IDENTIFIER ::= { enterprises 10062 }
aaronGroskyAndAssociates          OBJECT IDENTIFIER ::= { enterprises 10063 }
ash                               OBJECT IDENTIFIER ::= { enterprises 10064 }
ironoakSoftware                   OBJECT IDENTIFIER ::= { enterprises 10065 }
digitalMultimediaTechnologies     OBJECT IDENTIFIER ::= { enterprises 10066 }
dvtel                             OBJECT IDENTIFIER ::= { enterprises 10067 }
eOfficeServices                   OBJECT IDENTIFIER ::= { enterprises 10068 }
epsilonAB                         OBJECT IDENTIFIER ::= { enterprises 10069 }
flashwave                         OBJECT IDENTIFIER ::= { enterprises 10070 }
ginkoAG                           OBJECT IDENTIFIER ::= { enterprises 10071 }
gwTechnologiesCo                  OBJECT IDENTIFIER ::= { enterprises 10072 }
hansenetTelekommunikation         OBJECT IDENTIFIER ::= { enterprises 10073 }
ikimbo                            OBJECT IDENTIFIER ::= { enterprises 10074 }
infodyneCorporation               OBJECT IDENTIFIER ::= { enterprises 10075 }
institutionsOfTheEuropeanUnion    OBJECT IDENTIFIER ::= { enterprises 10076 }
mbyn                              OBJECT IDENTIFIER ::= { enterprises 10077 }
medienprojektvereinSteiermark     OBJECT IDENTIFIER ::= { enterprises 10078 }
metrosource                       OBJECT IDENTIFIER ::= { enterprises 10079 }
microcellI5                       OBJECT IDENTIFIER ::= { enterprises 10080 }
nrjcorporation                    OBJECT IDENTIFIER ::= { enterprises 10081 }
oculusTechnologiesCorporation     OBJECT IDENTIFIER ::= { enterprises 10082 }
pandaVista                        OBJECT IDENTIFIER ::= { enterprises 10083 }
priorityTelecomNVRoger            OBJECT IDENTIFIER ::= { enterprises 10084 }
proveIT                           OBJECT IDENTIFIER ::= { enterprises 10085 }
segueSoftware                     OBJECT IDENTIFIER ::= { enterprises 10086 }
silentoneLimited                  OBJECT IDENTIFIER ::= { enterprises 10087 }
technoValleyCo                    OBJECT IDENTIFIER ::= { enterprises 10088 }
tekTools                          OBJECT IDENTIFIER ::= { enterprises 10089 }
theClueNetProject                 OBJECT IDENTIFIER ::= { enterprises 10090 }
transfar                          OBJECT IDENTIFIER ::= { enterprises 10091 }
unassigned                        OBJECT IDENTIFIER ::= { enterprises 10092 }
unamite                           OBJECT IDENTIFIER ::= { enterprises 10093 }
universityOfNoviSad               OBJECT IDENTIFIER ::= { enterprises 10094 }
wickanderAndAssociates            OBJECT IDENTIFIER ::= { enterprises 10095 }
baxterHealthcareCorporation       OBJECT IDENTIFIER ::= { enterprises 10096 }
eciIP                             OBJECT IDENTIFIER ::= { enterprises 10097 }
gonicus                           OBJECT IDENTIFIER ::= { enterprises 10098 }
humanit                           OBJECT IDENTIFIER ::= { enterprises 10099 }
ondeviceCorporation               OBJECT IDENTIFIER ::= { enterprises 10100 }
miraiEspana                       OBJECT IDENTIFIER ::= { enterprises 10101 }
altNTechnologies                  OBJECT IDENTIFIER ::= { enterprises 10102 }
lewisCurtisConsulting             OBJECT IDENTIFIER ::= { enterprises 10103 }
eboa                              OBJECT IDENTIFIER ::= { enterprises 10104 }
lawsonSoftware                    OBJECT IDENTIFIER ::= { enterprises 10105 }
albal                             OBJECT IDENTIFIER ::= { enterprises 10106 }
stcomTechnologiesCorp             OBJECT IDENTIFIER ::= { enterprises 10107 }
global                            OBJECT IDENTIFIER ::= { enterprises 10108 }
activeTelecom                     OBJECT IDENTIFIER ::= { enterprises 10109 }
agileStorage                      OBJECT IDENTIFIER ::= { enterprises 10110 }
getConnected                      OBJECT IDENTIFIER ::= { enterprises 10111 }
aplcompOy                         OBJECT IDENTIFIER ::= { enterprises 10112 }
applianceware                     OBJECT IDENTIFIER ::= { enterprises 10113 }
artesiaTechnologies               OBJECT IDENTIFIER ::= { enterprises 10114 }
artful                            OBJECT IDENTIFIER ::= { enterprises 10115 }
augaApS                           OBJECT IDENTIFIER ::= { enterprises 10116 }
axerraNetworks                    OBJECT IDENTIFIER ::= { enterprises 10117 }
benefitsxml                       OBJECT IDENTIFIER ::= { enterprises 10118 }
bigbangwidth                      OBJECT IDENTIFIER ::= { enterprises 10119 }
brtech                            OBJECT IDENTIFIER ::= { enterprises 10120 }
clearCommunications               OBJECT IDENTIFIER ::= { enterprises 10121 }
creatiaCorporation                OBJECT IDENTIFIER ::= { enterprises 10122 }
crimcoConsulting                  OBJECT IDENTIFIER ::= { enterprises 10123 }
custUniversit                     OBJECT IDENTIFIER ::= { enterprises 10124 }
cyberpixie                        OBJECT IDENTIFIER ::= { enterprises 10125 }
daasiInternational                OBJECT IDENTIFIER ::= { enterprises 10126 }
desanaSystems                     OBJECT IDENTIFIER ::= { enterprises 10127 }
disa                              OBJECT IDENTIFIER ::= { enterprises 10128 }
discovernet                       OBJECT IDENTIFIER ::= { enterprises 10129 }
ecoleCentraleDeLyon               OBJECT IDENTIFIER ::= { enterprises 10130 }
eink                              OBJECT IDENTIFIER ::= { enterprises 10131 }
emSolutionsPty                    OBJECT IDENTIFIER ::= { enterprises 10132 }
fedex                             OBJECT IDENTIFIER ::= { enterprises 10133 }
ferraralug                        OBJECT IDENTIFIER ::= { enterprises 10134 }
frontPorch                        OBJECT IDENTIFIER ::= { enterprises 10135 }
godotCommunicationTechnologiesGmbh OBJECT IDENTIFIER ::= { enterprises 10136 }
gtmpFoundation                    OBJECT IDENTIFIER ::= { enterprises 10137 }
i2pi                              OBJECT IDENTIFIER ::= { enterprises 10138 }
i3sp                              OBJECT IDENTIFIER ::= { enterprises 10139 }
incoSystems                       OBJECT IDENTIFIER ::= { enterprises 10140 }
infinisysPty                      OBJECT IDENTIFIER ::= { enterprises 10141 }
interdimensions                   OBJECT IDENTIFIER ::= { enterprises 10142 }
introutConsulting                 OBJECT IDENTIFIER ::= { enterprises 10143 }
iormyx                            OBJECT IDENTIFIER ::= { enterprises 10144 }
justInTimeConsulting              OBJECT IDENTIFIER ::= { enterprises 10145 }
kernAutomatiseringsdienstenBV     OBJECT IDENTIFIER ::= { enterprises 10146 }
lancasterLebanonIntermediateUnit13 OBJECT IDENTIFIER ::= { enterprises 10147 }
lightelSystemsCorporation         OBJECT IDENTIFIER ::= { enterprises 10148 }
lineone                           OBJECT IDENTIFIER ::= { enterprises 10149 }
logicOne                          OBJECT IDENTIFIER ::= { enterprises 10150 }
multimediaUniversity              OBJECT IDENTIFIER ::= { enterprises 10151 }
muspellsheim                      OBJECT IDENTIFIER ::= { enterprises 10152 }
net2phone                         OBJECT IDENTIFIER ::= { enterprises 10153 }
netplay                           OBJECT IDENTIFIER ::= { enterprises 10154 }
northernParklife                  OBJECT IDENTIFIER ::= { enterprises 10155 }
novoforum                         OBJECT IDENTIFIER ::= { enterprises 10156 }
onnetTechnologiesCo               OBJECT IDENTIFIER ::= { enterprises 10157 }
panamsat                          OBJECT IDENTIFIER ::= { enterprises 10158 }
panasas                           OBJECT IDENTIFIER ::= { enterprises 10159 }
pennStateOutreachInformationSystems OBJECT IDENTIFIER ::= { enterprises 10160 }
pictureiq                         OBJECT IDENTIFIER ::= { enterprises 10161 }
polandcomSA                       OBJECT IDENTIFIER ::= { enterprises 10162 }
remedyCorporation                 OBJECT IDENTIFIER ::= { enterprises 10163 }
roadsAndTrafficAuthority          OBJECT IDENTIFIER ::= { enterprises 10164 }
robertWilliamsConsulting          OBJECT IDENTIFIER ::= { enterprises 10165 }
secureSoftwareServices            OBJECT IDENTIFIER ::= { enterprises 10166 }
siemensCommunicationsLimited      OBJECT IDENTIFIER ::= { enterprises 10167 }
spaceBiomedicalCenter             OBJECT IDENTIFIER ::= { enterprises 10168 }
suayanDesign                      OBJECT IDENTIFIER ::= { enterprises 10169 }
telemigCelularSA                  OBJECT IDENTIFIER ::= { enterprises 10170 }
telsey                            OBJECT IDENTIFIER ::= { enterprises 10171 }
territoryBusinessSolutionsPty     OBJECT IDENTIFIER ::= { enterprises 10172 }
texil                             OBJECT IDENTIFIER ::= { enterprises 10173 }
theChubbGroupOfInsuranceCompanies OBJECT IDENTIFIER ::= { enterprises 10174 }
traffionTechnologies              OBJECT IDENTIFIER ::= { enterprises 10175 }
univention                        OBJECT IDENTIFIER ::= { enterprises 10176 }
universityOfNorthernIowa          OBJECT IDENTIFIER ::= { enterprises 10177 }
westernKentuckyUniversity         OBJECT IDENTIFIER ::= { enterprises 10178 }
wirelessSolutions                 OBJECT IDENTIFIER ::= { enterprises 10179 }
amUtilsOrganization               OBJECT IDENTIFIER ::= { enterprises 10180 }
cardinalHealth                    OBJECT IDENTIFIER ::= { enterprises 10181 }
futurelabAG                       OBJECT IDENTIFIER ::= { enterprises 10182 }
masterQualitySnc                  OBJECT IDENTIFIER ::= { enterprises 10183 }
qcomTV                            OBJECT IDENTIFIER ::= { enterprises 10184 }
smp                               OBJECT IDENTIFIER ::= { enterprises 10185 }
weinbrennerMediaConsult           OBJECT IDENTIFIER ::= { enterprises 10186 }
teleview                          OBJECT IDENTIFIER ::= { enterprises 10187 }
piolink                           OBJECT IDENTIFIER ::= { enterprises 10188 }
congruency                        OBJECT IDENTIFIER ::= { enterprises 10189 }
aegmis                            OBJECT IDENTIFIER ::= { enterprises 10190 }
divergenet                        OBJECT IDENTIFIER ::= { enterprises 10191 }
eONEnergieAG                      OBJECT IDENTIFIER ::= { enterprises 10192 }
erkle                             OBJECT IDENTIFIER ::= { enterprises 10193 }
is-energy                         OBJECT IDENTIFIER ::= { enterprises 10194 }
shSoft                            OBJECT IDENTIFIER ::= { enterprises 10195 }
wwwthinkingmachinescom            OBJECT IDENTIFIER ::= { enterprises 10196 }
vovtelNetworks                    OBJECT IDENTIFIER ::= { enterprises 10197 }
carrollNet                        OBJECT IDENTIFIER ::= { enterprises 10198 }
klamannSoftwareAndBeratung        OBJECT IDENTIFIER ::= { enterprises 10199 }
iMailBoxProject                   OBJECT IDENTIFIER ::= { enterprises 10200 }
eftel                             OBJECT IDENTIFIER ::= { enterprises 10201 }
gftSolutions                      OBJECT IDENTIFIER ::= { enterprises 10202 }
winterAG                          OBJECT IDENTIFIER ::= { enterprises 10203 }
shanghaiSCOPPhotonicsTechnologyCo OBJECT IDENTIFIER ::= { enterprises 10204 }
apama                             OBJECT IDENTIFIER ::= { enterprises 10205 }
epik                              OBJECT IDENTIFIER ::= { enterprises 10206 }
hilgraeve                         OBJECT IDENTIFIER ::= { enterprises 10207 }
valnetSadoSA                      OBJECT IDENTIFIER ::= { enterprises 10208 }
andesNetworks                     OBJECT IDENTIFIER ::= { enterprises 10209 }
axsOne                            OBJECT IDENTIFIER ::= { enterprises 10210 }
benauAS                           OBJECT IDENTIFIER ::= { enterprises 10211 }
cutlerAndCompany                  OBJECT IDENTIFIER ::= { enterprises 10212 }
meritonNetworks                   OBJECT IDENTIFIER ::= { enterprises 10213 }
enigmaSOISPZOO                    OBJECT IDENTIFIER ::= { enterprises 10214 }
forwardTechnicalCo                OBJECT IDENTIFIER ::= { enterprises 10215 }
franticFilms                      OBJECT IDENTIFIER ::= { enterprises 10216 }
hotdiary                          OBJECT IDENTIFIER ::= { enterprises 10217 }
hsufarm                           OBJECT IDENTIFIER ::= { enterprises 10218 }
idealTechnologyCorporation        OBJECT IDENTIFIER ::= { enterprises 10219 }
ifwDresden                        OBJECT IDENTIFIER ::= { enterprises 10220 }
impactTECHNOLOGIES                OBJECT IDENTIFIER ::= { enterprises 10221 }
infiniconSystems                  OBJECT IDENTIFIER ::= { enterprises 10222 }
leoADalyCompany                   OBJECT IDENTIFIER ::= { enterprises 10223 }
lufthansaSystemsInfratec          OBJECT IDENTIFIER ::= { enterprises 10224 }
marrakech                         OBJECT IDENTIFIER ::= { enterprises 10225 }
mydn                              OBJECT IDENTIFIER ::= { enterprises 10226 }
neesusDatacom                     OBJECT IDENTIFIER ::= { enterprises 10227 }
netAndPublicationConsultance      OBJECT IDENTIFIER ::= { enterprises 10228 }
netgateSc                         OBJECT IDENTIFIER ::= { enterprises 10229 }
orioleCorporation                 OBJECT IDENTIFIER ::= { enterprises 10230 }
proficientNetworks                OBJECT IDENTIFIER ::= { enterprises 10231 }
signiantCorporation               OBJECT IDENTIFIER ::= { enterprises 10232 }
siliconGoblinTechnologies         OBJECT IDENTIFIER ::= { enterprises 10233 }
snortorg                          OBJECT IDENTIFIER ::= { enterprises 10234 }
startrackCommunications           OBJECT IDENTIFIER ::= { enterprises 10235 }
studioKomputeroweAWA              OBJECT IDENTIFIER ::= { enterprises 10236 }
sullins                           OBJECT IDENTIFIER ::= { enterprises 10237 }
technischeUniversitaetBerlin      OBJECT IDENTIFIER ::= { enterprises 10238 }
tessSA                            OBJECT IDENTIFIER ::= { enterprises 10239 }
transnationalComputerTechnology   OBJECT IDENTIFIER ::= { enterprises 10240 }
trpgAssociation                   OBJECT IDENTIFIER ::= { enterprises 10241 }
universityOfBrighton              OBJECT IDENTIFIER ::= { enterprises 10242 }
uplogixcom                        OBJECT IDENTIFIER ::= { enterprises 10243 }
validata                          OBJECT IDENTIFIER ::= { enterprises 10244 }
valiosysSA                        OBJECT IDENTIFIER ::= { enterprises 10245 }
virtualEducationSpace             OBJECT IDENTIFIER ::= { enterprises 10246 }
collegeunitscom                   OBJECT IDENTIFIER ::= { enterprises 10247 }
ecentral                          OBJECT IDENTIFIER ::= { enterprises 10248 }
cintelIntelligentTelecomSystemCo  OBJECT IDENTIFIER ::= { enterprises 10249 }
negativetwenty                    OBJECT IDENTIFIER ::= { enterprises 10250 }
warlock                           OBJECT IDENTIFIER ::= { enterprises 10251 }
diagnosticLaboratoryServices      OBJECT IDENTIFIER ::= { enterprises 10252 }
napster                           OBJECT IDENTIFIER ::= { enterprises 10253 }
texunaTechnologiesMoscow          OBJECT IDENTIFIER ::= { enterprises 10254 }
infoquenzITDienstleistungen       OBJECT IDENTIFIER ::= { enterprises 10255 }
sciobyte                          OBJECT IDENTIFIER ::= { enterprises 10256 }
hadithi                           OBJECT IDENTIFIER ::= { enterprises 10257 }
aracnetInternetServices           OBJECT IDENTIFIER ::= { enterprises 10258 }
avtecSystems                      OBJECT IDENTIFIER ::= { enterprises 10259 }
beamreachNetworks                 OBJECT IDENTIFIER ::= { enterprises 10260 }
cedarPointCommunications          OBJECT IDENTIFIER ::= { enterprises 10261 }
cncSystems                        OBJECT IDENTIFIER ::= { enterprises 10262 }
customLinuxSolutions              OBJECT IDENTIFIER ::= { enterprises 10263 }
dataAndINFORMATIONTECHNOLOGYLTD   OBJECT IDENTIFIER ::= { enterprises 10264 }
deltathree                        OBJECT IDENTIFIER ::= { enterprises 10265 }
dizRheinlandPfalz                 OBJECT IDENTIFIER ::= { enterprises 10266 }
electroOpticSystems               OBJECT IDENTIFIER ::= { enterprises 10267 }
enterpriseCommerce                OBJECT IDENTIFIER ::= { enterprises 10268 }
epropose                          OBJECT IDENTIFIER ::= { enterprises 10269 }
esNetze                           OBJECT IDENTIFIER ::= { enterprises 10270 }
forgent                           OBJECT IDENTIFIER ::= { enterprises 10271 }
futureInstrumentAB                OBJECT IDENTIFIER ::= { enterprises 10272 }
giantStepProductionsLLC           OBJECT IDENTIFIER ::= { enterprises 10273 }
hexafluxSMS                       OBJECT IDENTIFIER ::= { enterprises 10274 }
masterADistancia                  OBJECT IDENTIFIER ::= { enterprises 10275 }
msiNetworkServices                OBJECT IDENTIFIER ::= { enterprises 10276 }
multnomahEducationServiceDistrict OBJECT IDENTIFIER ::= { enterprises 10277 }
netacquireCorporation             OBJECT IDENTIFIER ::= { enterprises 10278 }
objectValley                      OBJECT IDENTIFIER ::= { enterprises 10279 }
quixotechSystems                  OBJECT IDENTIFIER ::= { enterprises 10280 }
selectTechnology                  OBJECT IDENTIFIER ::= { enterprises 10281 }
speedkom                          OBJECT IDENTIFIER ::= { enterprises 10282 }
tabcorp                           OBJECT IDENTIFIER ::= { enterprises 10283 }
thomasJeffersonUniversity         OBJECT IDENTIFIER ::= { enterprises 10284 }
trenitaliaSpA                     OBJECT IDENTIFIER ::= { enterprises 10285 }
trintech                          OBJECT IDENTIFIER ::= { enterprises 10286 }
universityAtAlbany                OBJECT IDENTIFIER ::= { enterprises 10287 }
voxMobili                         OBJECT IDENTIFIER ::= { enterprises 10288 }
yukyungTelecomCo                  OBJECT IDENTIFIER ::= { enterprises 10289 }
internetBusinessConstellationSA   OBJECT IDENTIFIER ::= { enterprises 10290 }
jMFdemoncouk                      OBJECT IDENTIFIER ::= { enterprises 10291 }
laissezFaireCity                  OBJECT IDENTIFIER ::= { enterprises 10292 }
linkageSYSTEMINTEGERATIONCO       OBJECT IDENTIFIER ::= { enterprises 10293 }
dataSERVICESRL                    OBJECT IDENTIFIER ::= { enterprises 10294 }
isolution                         OBJECT IDENTIFIER ::= { enterprises 10295 }
iti                               OBJECT IDENTIFIER ::= { enterprises 10296 }
advantechCo                       OBJECT IDENTIFIER ::= { enterprises 10297 }
arbeitsgemeinschaftFuerTotalAbgehobeneTechnologie OBJECT IDENTIFIER ::= { enterprises 10298 }
avantia                           OBJECT IDENTIFIER ::= { enterprises 10299 }
avantronTechnologies              OBJECT IDENTIFIER ::= { enterprises 10300 }
bluesocket2                       OBJECT IDENTIFIER ::= { enterprises 10301 }
galaxySystems                     OBJECT IDENTIFIER ::= { enterprises 10302 }
istIsdnSupportTechnik             OBJECT IDENTIFIER ::= { enterprises 10303 }
lgtFinancialServices              OBJECT IDENTIFIER ::= { enterprises 10304 }
magnifixSdnBhd                    OBJECT IDENTIFIER ::= { enterprises 10305 }
msoTechnologies                   OBJECT IDENTIFIER ::= { enterprises 10306 }
opticalSolutions                  OBJECT IDENTIFIER ::= { enterprises 10307 }
osgi                              OBJECT IDENTIFIER ::= { enterprises 10308 }
sohoSkyway                        OBJECT IDENTIFIER ::= { enterprises 10309 }
tangITConsulting                  OBJECT IDENTIFIER ::= { enterprises 10310 }
kerioTechnologies                 OBJECT IDENTIFIER ::= { enterprises 10311 }
translogicSystems                 OBJECT IDENTIFIER ::= { enterprises 10312 }
autinform                         OBJECT IDENTIFIER ::= { enterprises 10313 }
provenir                          OBJECT IDENTIFIER ::= { enterprises 10314 }
primaEV                           OBJECT IDENTIFIER ::= { enterprises 10315 }
rafael                            OBJECT IDENTIFIER ::= { enterprises 10316 }
nanumTechnology                   OBJECT IDENTIFIER ::= { enterprises 10317 }
sasktelInternational              OBJECT IDENTIFIER ::= { enterprises 10318 }
semanticsAG                       OBJECT IDENTIFIER ::= { enterprises 10319 }
amherstCollege                    OBJECT IDENTIFIER ::= { enterprises 10320 }
aunet                             OBJECT IDENTIFIER ::= { enterprises 10321 }
centreForAdvancedTechnology       OBJECT IDENTIFIER ::= { enterprises 10322 }
convergenceNetworkResearch        OBJECT IDENTIFIER ::= { enterprises 10323 }
crabusldap                        OBJECT IDENTIFIER ::= { enterprises 10324 }
earthconnectCorporation           OBJECT IDENTIFIER ::= { enterprises 10325 }
ecoleNationaleSuperieureDesMinesDeParis OBJECT IDENTIFIER ::= { enterprises 10326 }
fibercityNetworks                 OBJECT IDENTIFIER ::= { enterprises 10327 }
globeflowSA                       OBJECT IDENTIFIER ::= { enterprises 10328 }
integraMicroSystems               OBJECT IDENTIFIER ::= { enterprises 10329 }
kavado                            OBJECT IDENTIFIER ::= { enterprises 10330 }
lightningDataNetworks             OBJECT IDENTIFIER ::= { enterprises 10331 }
maxhostingGBR                     OBJECT IDENTIFIER ::= { enterprises 10332 }
metanet                           OBJECT IDENTIFIER ::= { enterprises 10333 }
mischiefNetworking                OBJECT IDENTIFIER ::= { enterprises 10334 }
rlmSystemsPty                     OBJECT IDENTIFIER ::= { enterprises 10335 }
summitTechCommunications          OBJECT IDENTIFIER ::= { enterprises 10336 }
valisLTD                          OBJECT IDENTIFIER ::= { enterprises 10337 }
localeSystems                     OBJECT IDENTIFIER ::= { enterprises 10338 }
starremoteWireless                OBJECT IDENTIFIER ::= { enterprises 10339 }
indianaStateUniversity            OBJECT IDENTIFIER ::= { enterprises 10340 }
klinikLoewensteinG                OBJECT IDENTIFIER ::= { enterprises 10341 }
miamiUniversity                   OBJECT IDENTIFIER ::= { enterprises 10342 }
netexcell                         OBJECT IDENTIFIER ::= { enterprises 10343 }
netregistryPty                    OBJECT IDENTIFIER ::= { enterprises 10344 }
newportNetworksLimitd             OBJECT IDENTIFIER ::= { enterprises 10345 }
omegaband                         OBJECT IDENTIFIER ::= { enterprises 10346 }
plustream                         OBJECT IDENTIFIER ::= { enterprises 10347 }
softpro                           OBJECT IDENTIFIER ::= { enterprises 10348 }
sysgemAG                          OBJECT IDENTIFIER ::= { enterprises 10349 }
systemSoftwareSolutions           OBJECT IDENTIFIER ::= { enterprises 10350 }
oblivion                          OBJECT IDENTIFIER ::= { enterprises 10351 }
retevisi                          OBJECT IDENTIFIER ::= { enterprises 10352 }
innocom                           OBJECT IDENTIFIER ::= { enterprises 10353 }
brewsterAcademy                   OBJECT IDENTIFIER ::= { enterprises 10354 }
itaction                          OBJECT IDENTIFIER ::= { enterprises 10355 }
targetRevocableEMailCorporation   OBJECT IDENTIFIER ::= { enterprises 10356 }
roySRapoport                      OBJECT IDENTIFIER ::= { enterprises 10357 }
accelioCorporation                OBJECT IDENTIFIER ::= { enterprises 10358 }
adtelSoftware                     OBJECT IDENTIFIER ::= { enterprises 10359 }
agesmudTechnology                 OBJECT IDENTIFIER ::= { enterprises 10360 }
bharatHeavyElectricalsLimited     OBJECT IDENTIFIER ::= { enterprises 10361 }
bluware                           OBJECT IDENTIFIER ::= { enterprises 10362 }
catbirdNetworks                   OBJECT IDENTIFIER ::= { enterprises 10363 }
centralManchesterCityLearningCenter OBJECT IDENTIFIER ::= { enterprises 10364 }
davoxCorp                         OBJECT IDENTIFIER ::= { enterprises 10365 }
dialpadCommunications             OBJECT IDENTIFIER ::= { enterprises 10366 }
donnie21                          OBJECT IDENTIFIER ::= { enterprises 10367 }
fujitsuSiemensComputers           OBJECT IDENTIFIER ::= { enterprises 10368 }
fujitsuPrimeSoftwareTechnologies  OBJECT IDENTIFIER ::= { enterprises 10369 }
impulsesoft                       OBJECT IDENTIFIER ::= { enterprises 10370 }
inabyte                           OBJECT IDENTIFIER ::= { enterprises 10371 }
intelligentApplianceLab           OBJECT IDENTIFIER ::= { enterprises 10372 }
leReseau                          OBJECT IDENTIFIER ::= { enterprises 10373 }
lifelineSystems                   OBJECT IDENTIFIER ::= { enterprises 10374 }
makinaCorpus                      OBJECT IDENTIFIER ::= { enterprises 10375 }
netfront                          OBJECT IDENTIFIER ::= { enterprises 10376 }
onmobileSystem                    OBJECT IDENTIFIER ::= { enterprises 10377 }
packetvideo                       OBJECT IDENTIFIER ::= { enterprises 10378 }
princetonSolutionsGroup           OBJECT IDENTIFIER ::= { enterprises 10379 }
telesysSoftware                   OBJECT IDENTIFIER ::= { enterprises 10380 }
trendpointSystems                 OBJECT IDENTIFIER ::= { enterprises 10381 }
ucnet                             OBJECT IDENTIFIER ::= { enterprises 10382 }
universiteDeLiege                 OBJECT IDENTIFIER ::= { enterprises 10383 }
virginiaCommonwealthUniversity    OBJECT IDENTIFIER ::= { enterprises 10384 }
westronicSystems                  OBJECT IDENTIFIER ::= { enterprises 10385 }
youngwooTelecomCo                 OBJECT IDENTIFIER ::= { enterprises 10386 }
dongahElecomm                     OBJECT IDENTIFIER ::= { enterprises 10387 }
supportcommTeleinformaticaSA      OBJECT IDENTIFIER ::= { enterprises 10388 }
intabo                            OBJECT IDENTIFIER ::= { enterprises 10389 }
delta                             OBJECT IDENTIFIER ::= { enterprises 10390 }
bharatSancharNigamLimited         OBJECT IDENTIFIER ::= { enterprises 10391 }
abeonaNetworks                    OBJECT IDENTIFIER ::= { enterprises 10392 }
apeh                              OBJECT IDENTIFIER ::= { enterprises 10393 }
banamex                           OBJECT IDENTIFIER ::= { enterprises 10394 }
beloCorporation                   OBJECT IDENTIFIER ::= { enterprises 10395 }
californiaStateUniversity2        OBJECT IDENTIFIER ::= { enterprises 10396 }
cksoft                            OBJECT IDENTIFIER ::= { enterprises 10397 }
covasoft                          OBJECT IDENTIFIER ::= { enterprises 10398 }
datakey                           OBJECT IDENTIFIER ::= { enterprises 10399 }
electricLightwave                 OBJECT IDENTIFIER ::= { enterprises 10400 }
ideoConceptsCo                    OBJECT IDENTIFIER ::= { enterprises 10401 }
interdev                          OBJECT IDENTIFIER ::= { enterprises 10402 }
istitutoNazionaleDiFisicaNucleare OBJECT IDENTIFIER ::= { enterprises 10403 }
livinglogicAG                     OBJECT IDENTIFIER ::= { enterprises 10404 }
mentalHealthCooperative           OBJECT IDENTIFIER ::= { enterprises 10405 }
neuralAudio                       OBJECT IDENTIFIER ::= { enterprises 10406 }
northCoastSoftware                OBJECT IDENTIFIER ::= { enterprises 10407 }
perculaConsulting                 OBJECT IDENTIFIER ::= { enterprises 10408 }
tellurianPty                      OBJECT IDENTIFIER ::= { enterprises 10409 }
theFalcon                         OBJECT IDENTIFIER ::= { enterprises 10410 }
universityOfNorthCarolinaAtChapelHill OBJECT IDENTIFIER ::= { enterprises 10411 }
atelo                             OBJECT IDENTIFIER ::= { enterprises 10412 }
systemInnovations                 OBJECT IDENTIFIER ::= { enterprises 10413 }
brauereiCAndAVeltins              OBJECT IDENTIFIER ::= { enterprises 10414 }
threeGPP                          OBJECT IDENTIFIER ::= { enterprises 10415 }
abcVirtualCommunications          OBJECT IDENTIFIER ::= { enterprises 10416 }
amerion                           OBJECT IDENTIFIER ::= { enterprises 10417 }
avocentCorporation                OBJECT IDENTIFIER ::= { enterprises 10418 }
bactolTechnicalLimited            OBJECT IDENTIFIER ::= { enterprises 10419 }
bayerischesLandeskriminalamtAbtIuK OBJECT IDENTIFIER ::= { enterprises 10420 }
cCURECvba                         OBJECT IDENTIFIER ::= { enterprises 10421 }
chinaPTICInformationIndustryCorporation OBJECT IDENTIFIER ::= { enterprises 10422 }
cityxpressCorp                    OBJECT IDENTIFIER ::= { enterprises 10423 }
cricketCommunications             OBJECT IDENTIFIER ::= { enterprises 10424 }
electricityGeneratingAuthorityOfThailand OBJECT IDENTIFIER ::= { enterprises 10425 }
elexNV                            OBJECT IDENTIFIER ::= { enterprises 10426 }
embraceNetworks                   OBJECT IDENTIFIER ::= { enterprises 10427 }
furukawaIndustrialSACuritiba      OBJECT IDENTIFIER ::= { enterprises 10428 }
gelwargnet                        OBJECT IDENTIFIER ::= { enterprises 10429 }
globalremotecomAG                 OBJECT IDENTIFIER ::= { enterprises 10430 }
ingenieurbueroKittelberger        OBJECT IDENTIFIER ::= { enterprises 10431 }
mottCommunityCollege              OBJECT IDENTIFIER ::= { enterprises 10432 }
mutekSolution                     OBJECT IDENTIFIER ::= { enterprises 10433 }
nikhef                            OBJECT IDENTIFIER ::= { enterprises 10434 }
omnitel                           OBJECT IDENTIFIER ::= { enterprises 10435 }
oxfordUniversity                  OBJECT IDENTIFIER ::= { enterprises 10436 }
pepperconAG                       OBJECT IDENTIFIER ::= { enterprises 10437 }
portimaSC                         OBJECT IDENTIFIER ::= { enterprises 10438 }
powerMeasurement                  OBJECT IDENTIFIER ::= { enterprises 10439 }
roseITSolutions                   OBJECT IDENTIFIER ::= { enterprises 10440 }
silasTechnologies                 OBJECT IDENTIFIER ::= { enterprises 10441 }
spiderNetworks                    OBJECT IDENTIFIER ::= { enterprises 10442 }
threePillars                      OBJECT IDENTIFIER ::= { enterprises 10443 }
tichennet                         OBJECT IDENTIFIER ::= { enterprises 10444 }
trilliumPhotonics                 OBJECT IDENTIFIER ::= { enterprises 10445 }
trinityExpertSystemsPlc           OBJECT IDENTIFIER ::= { enterprises 10446 }
universityOfMississippi           OBJECT IDENTIFIER ::= { enterprises 10447 }
universityOfPugetSound            OBJECT IDENTIFIER ::= { enterprises 10448 }
xceedium                          OBJECT IDENTIFIER ::= { enterprises 10449 }
altamarNetworks                   OBJECT IDENTIFIER ::= { enterprises 10450 }
bostonMarketCorporation           OBJECT IDENTIFIER ::= { enterprises 10451 }
egtonMedicalInformationSystems    OBJECT IDENTIFIER ::= { enterprises 10452 }
ilJINTELECOMELECCO                OBJECT IDENTIFIER ::= { enterprises 10453 }
opticalCrossing                   OBJECT IDENTIFIER ::= { enterprises 10454 }
paradigm                          OBJECT IDENTIFIER ::= { enterprises 10455 }
planetTechnologyCorp              OBJECT IDENTIFIER ::= { enterprises 10456 }
dbInformatikDienste               OBJECT IDENTIFIER ::= { enterprises 10457 }
xTechnologies                     OBJECT IDENTIFIER ::= { enterprises 10458 }
hexinSoftware                     OBJECT IDENTIFIER ::= { enterprises 10459 }
hisolutionsAG                     OBJECT IDENTIFIER ::= { enterprises 10460 }
tixoConsulting                    OBJECT IDENTIFIER ::= { enterprises 10461 }
atek                              OBJECT IDENTIFIER ::= { enterprises 10462 }
devkVersicherungen                OBJECT IDENTIFIER ::= { enterprises 10463 }
elataPlc                          OBJECT IDENTIFIER ::= { enterprises 10464 }
flypaper                          OBJECT IDENTIFIER ::= { enterprises 10465 }
holimTechnology                   OBJECT IDENTIFIER ::= { enterprises 10466 }
ingenieurb                        OBJECT IDENTIFIER ::= { enterprises 10467 }
irtnogorg                         OBJECT IDENTIFIER ::= { enterprises 10468 }
lidcamTechnologyPty               OBJECT IDENTIFIER ::= { enterprises 10469 }
mediaBrokersInternational         OBJECT IDENTIFIER ::= { enterprises 10470 }
openfortress                      OBJECT IDENTIFIER ::= { enterprises 10471 }
recourseTechnologies              OBJECT IDENTIFIER ::= { enterprises 10472 }
remandoAB                         OBJECT IDENTIFIER ::= { enterprises 10473 }
servletsnetCorporation            OBJECT IDENTIFIER ::= { enterprises 10474 }
slovakUniversityOfAgriculture     OBJECT IDENTIFIER ::= { enterprises 10475 }
summitMediaPartners               OBJECT IDENTIFIER ::= { enterprises 10476 }
telephony                         OBJECT IDENTIFIER ::= { enterprises 10477 }
transeonicSystems                 OBJECT IDENTIFIER ::= { enterprises 10478 }
webServices                       OBJECT IDENTIFIER ::= { enterprises 10479 }
wilyTechnology                    OBJECT IDENTIFIER ::= { enterprises 10480 }
aljisrInformationServices         OBJECT IDENTIFIER ::= { enterprises 10481 }
priceWaterhosurCoopersBPO         OBJECT IDENTIFIER ::= { enterprises 10482 }
winalysisSoftware                 OBJECT IDENTIFIER ::= { enterprises 10483 }
tf1Sa                             OBJECT IDENTIFIER ::= { enterprises 10484 }
aboutWebServices                  OBJECT IDENTIFIER ::= { enterprises 10485 }
aspelle                           OBJECT IDENTIFIER ::= { enterprises 10486 }
businessInformationPublications   OBJECT IDENTIFIER ::= { enterprises 10487 }
chelsioCommunications             OBJECT IDENTIFIER ::= { enterprises 10488 }
designCombus                      OBJECT IDENTIFIER ::= { enterprises 10489 }
gnf                               OBJECT IDENTIFIER ::= { enterprises 10490 }
hampshireCollege                  OBJECT IDENTIFIER ::= { enterprises 10491 }
hstHighSoftTech                   OBJECT IDENTIFIER ::= { enterprises 10492 }
innovanceNetworks                 OBJECT IDENTIFIER ::= { enterprises 10493 }
inphomatch                        OBJECT IDENTIFIER ::= { enterprises 10494 }
interlink                         OBJECT IDENTIFIER ::= { enterprises 10495 }
linkSimulationAndTraining         OBJECT IDENTIFIER ::= { enterprises 10496 }
maly                              OBJECT IDENTIFIER ::= { enterprises 10497 }
michaeljcrawfordcom               OBJECT IDENTIFIER ::= { enterprises 10498 }
ministeriumDesInnernSachsenAnhalt OBJECT IDENTIFIER ::= { enterprises 10499 }
musicChoice                       OBJECT IDENTIFIER ::= { enterprises 10500 }
netmanCompany                     OBJECT IDENTIFIER ::= { enterprises 10501 }
northDakotaUniversitySystem       OBJECT IDENTIFIER ::= { enterprises 10502 }
powerInnovationsInternational     OBJECT IDENTIFIER ::= { enterprises 10503 }
printronix                        OBJECT IDENTIFIER ::= { enterprises 10504 }
quorusMedicalSystems              OBJECT IDENTIFIER ::= { enterprises 10505 }
radioshackCorporation             OBJECT IDENTIFIER ::= { enterprises 10506 }
reciproca                         OBJECT IDENTIFIER ::= { enterprises 10507 }
resModMan                         OBJECT IDENTIFIER ::= { enterprises 10508 }
rightvision                       OBJECT IDENTIFIER ::= { enterprises 10509 }
screamingmedia                    OBJECT IDENTIFIER ::= { enterprises 10510 }
simpledevices                     OBJECT IDENTIFIER ::= { enterprises 10511 }
spectrumImage                     OBJECT IDENTIFIER ::= { enterprises 10512 }
steltor                           OBJECT IDENTIFIER ::= { enterprises 10513 }
strongauth                        OBJECT IDENTIFIER ::= { enterprises 10514 }
terryNazon                        OBJECT IDENTIFIER ::= { enterprises 10515 }
tNova                             OBJECT IDENTIFIER ::= { enterprises 10516 }
torontoPOliceService              OBJECT IDENTIFIER ::= { enterprises 10517 }
trunknet                          OBJECT IDENTIFIER ::= { enterprises 10518 }
tsinghuaUnisplendourCo            OBJECT IDENTIFIER ::= { enterprises 10519 }
tycoElectronicsPowerSystems       OBJECT IDENTIFIER ::= { enterprises 10520 }
voiceplanet                       OBJECT IDENTIFIER ::= { enterprises 10521 }
voigtAndHaeffner                  OBJECT IDENTIFIER ::= { enterprises 10522 }
wanadooData                       OBJECT IDENTIFIER ::= { enterprises 10523 }
widevineTechnologies              OBJECT IDENTIFIER ::= { enterprises 10524 }
evangelischLutherischeKircheBayern OBJECT IDENTIFIER ::= { enterprises 10525 }
facultadDeIngenieria              OBJECT IDENTIFIER ::= { enterprises 10526 }
metrobilityOpticalSystems         OBJECT IDENTIFIER ::= { enterprises 10527 }
solidInformationTechnologyCorp    OBJECT IDENTIFIER ::= { enterprises 10528 }
gemtekSystemsHoldingBV            OBJECT IDENTIFIER ::= { enterprises 10529 }
ldapAmigoz                        OBJECT IDENTIFIER ::= { enterprises 10530 }
ctcom                             OBJECT IDENTIFIER ::= { enterprises 10531 }
rifetech                          OBJECT IDENTIFIER ::= { enterprises 10532 }
seitenbauOnlineAgenturGbmH        OBJECT IDENTIFIER ::= { enterprises 10533 }
secomCo                           OBJECT IDENTIFIER ::= { enterprises 10534 }
londonInternetExchange            OBJECT IDENTIFIER ::= { enterprises 10535 }
simon                             OBJECT IDENTIFIER ::= { enterprises 10536 }
abTravOchGalopp                   OBJECT IDENTIFIER ::= { enterprises 10537 }
abstraktDesign                    OBJECT IDENTIFIER ::= { enterprises 10538 }
alwayson                          OBJECT IDENTIFIER ::= { enterprises 10539 }
axlSoftware                       OBJECT IDENTIFIER ::= { enterprises 10540 }
caymasaElSendero                  OBJECT IDENTIFIER ::= { enterprises 10541 }
chongqingGRCTelecomCo             OBJECT IDENTIFIER ::= { enterprises 10542 }
dejarnetteResearchSystems         OBJECT IDENTIFIER ::= { enterprises 10543 }
factualData                       OBJECT IDENTIFIER ::= { enterprises 10544 }
genticsNetsolutions               OBJECT IDENTIFIER ::= { enterprises 10545 }
inturioPropertyRightsHoldingsLimited OBJECT IDENTIFIER ::= { enterprises 10546 }
matrixAppliedComputing            OBJECT IDENTIFIER ::= { enterprises 10547 }
netzwertAG                        OBJECT IDENTIFIER ::= { enterprises 10548 }
newvation                         OBJECT IDENTIFIER ::= { enterprises 10549 }
nTv                               OBJECT IDENTIFIER ::= { enterprises 10550 }
parergy                           OBJECT IDENTIFIER ::= { enterprises 10551 }
passlogix                         OBJECT IDENTIFIER ::= { enterprises 10552 }
qNetworks                         OBJECT IDENTIFIER ::= { enterprises 10553 }
qwestWireless                     OBJECT IDENTIFIER ::= { enterprises 10554 }
ramcarGroupOfCompanies            OBJECT IDENTIFIER ::= { enterprises 10555 }
recomp                            OBJECT IDENTIFIER ::= { enterprises 10556 }
sherwoodInternationalLimited      OBJECT IDENTIFIER ::= { enterprises 10557 }
silogix                           OBJECT IDENTIFIER ::= { enterprises 10558 }
softeck                           OBJECT IDENTIFIER ::= { enterprises 10559 }
southFloridaWaterManagementDistrict OBJECT IDENTIFIER ::= { enterprises 10560 }
starValleySolutions               OBJECT IDENTIFIER ::= { enterprises 10561 }
werkleitzGesellschaftEV           OBJECT IDENTIFIER ::= { enterprises 10562 }
portlandPublicSchools             OBJECT IDENTIFIER ::= { enterprises 10563 }
tiaScandinavia                    OBJECT IDENTIFIER ::= { enterprises 10564 }
universiteDeSavoie                OBJECT IDENTIFIER ::= { enterprises 10565 }
universitiPendidikanSultanIdris   OBJECT IDENTIFIER ::= { enterprises 10566 }
eyounetCorp                       OBJECT IDENTIFIER ::= { enterprises 10567 }
chinaSunboCorp                    OBJECT IDENTIFIER ::= { enterprises 10568 }
cokerNet                          OBJECT IDENTIFIER ::= { enterprises 10569 }
manlyManClub                      OBJECT IDENTIFIER ::= { enterprises 10570 }
merckKGaA                         OBJECT IDENTIFIER ::= { enterprises 10571 }
worldcomAG                        OBJECT IDENTIFIER ::= { enterprises 10572 }
aitechSpaceSystems                OBJECT IDENTIFIER ::= { enterprises 10573 }
carbonBasedPty                    OBJECT IDENTIFIER ::= { enterprises 10574 }
cumulusITAS                       OBJECT IDENTIFIER ::= { enterprises 10575 }
cygsoftLimited                    OBJECT IDENTIFIER ::= { enterprises 10576 }
eilatOnLine                       OBJECT IDENTIFIER ::= { enterprises 10577 }
electricInsuranceCompany          OBJECT IDENTIFIER ::= { enterprises 10578 }
eswoosh                           OBJECT IDENTIFIER ::= { enterprises 10579 }
handspring                        OBJECT IDENTIFIER ::= { enterprises 10580 }
icomera                           OBJECT IDENTIFIER ::= { enterprises 10581 }
linearSystems                     OBJECT IDENTIFIER ::= { enterprises 10582 }
netizenSA                         OBJECT IDENTIFIER ::= { enterprises 10583 }
nlriTechnology                    OBJECT IDENTIFIER ::= { enterprises 10584 }
parisAlesia                       OBJECT IDENTIFIER ::= { enterprises 10585 }
pennwellCorp                      OBJECT IDENTIFIER ::= { enterprises 10586 }
pharmapartnersBV                  OBJECT IDENTIFIER ::= { enterprises 10587 }
pixelboxx                         OBJECT IDENTIFIER ::= { enterprises 10588 }
rocketradercom                    OBJECT IDENTIFIER ::= { enterprises 10589 }
sageInformationConsultants        OBJECT IDENTIFIER ::= { enterprises 10590 }
salixTrainingLimited              OBJECT IDENTIFIER ::= { enterprises 10591 }
solutioninc                       OBJECT IDENTIFIER ::= { enterprises 10592 }
sybcom                            OBJECT IDENTIFIER ::= { enterprises 10593 }
transynergy                       OBJECT IDENTIFIER ::= { enterprises 10594 }
tyrellSoftwareCorporation         OBJECT IDENTIFIER ::= { enterprises 10595 }
vignonInformatiqueFrance          OBJECT IDENTIFIER ::= { enterprises 10596 }
allianceCapital                   OBJECT IDENTIFIER ::= { enterprises 10597 }
appliedSystemDesign               OBJECT IDENTIFIER ::= { enterprises 10598 }
departmentOfFamilies              OBJECT IDENTIFIER ::= { enterprises 10599 }
innovativeComputingLaboratory     OBJECT IDENTIFIER ::= { enterprises 10600 }
jataayuSoftwarePvt                OBJECT IDENTIFIER ::= { enterprises 10601 }
jiera                             OBJECT IDENTIFIER ::= { enterprises 10602 }
kafre                             OBJECT IDENTIFIER ::= { enterprises 10603 }
zarlinkSemiconductor              OBJECT IDENTIFIER ::= { enterprises 10604 }
infodeskSA                        OBJECT IDENTIFIER ::= { enterprises 10605 }
intracomAustraliaPty              OBJECT IDENTIFIER ::= { enterprises 10606 }
acgSolutions                      OBJECT IDENTIFIER ::= { enterprises 10607 }
alphaLab                          OBJECT IDENTIFIER ::= { enterprises 10608 }
appliedScienceFiction             OBJECT IDENTIFIER ::= { enterprises 10609 }
aubergiste                        OBJECT IDENTIFIER ::= { enterprises 10610 }
bluSPA                            OBJECT IDENTIFIER ::= { enterprises 10611 }
centralnyOsrodekInformatykiGornictwaSA OBJECT IDENTIFIER ::= { enterprises 10612 }
envivio                           OBJECT IDENTIFIER ::= { enterprises 10613 }
equityTechnologyGroup             OBJECT IDENTIFIER ::= { enterprises 10614 }
gartonworks                       OBJECT IDENTIFIER ::= { enterprises 10615 }
gedinfoScrl                       OBJECT IDENTIFIER ::= { enterprises 10616 }
infoConsulting                    OBJECT IDENTIFIER ::= { enterprises 10617 }
infostreamASP                     OBJECT IDENTIFIER ::= { enterprises 10618 }
innuworks                         OBJECT IDENTIFIER ::= { enterprises 10619 }
isoftel                           OBJECT IDENTIFIER ::= { enterprises 10620 }
bvbaMedKabDrSebrechtsE            OBJECT IDENTIFIER ::= { enterprises 10621 }
karmaDesigns                      OBJECT IDENTIFIER ::= { enterprises 10622 }
knowledgecube                     OBJECT IDENTIFIER ::= { enterprises 10623 }
richardLucassenElectronics        OBJECT IDENTIFIER ::= { enterprises 10624 }
maincube                          OBJECT IDENTIFIER ::= { enterprises 10625 }
mulveyFamily                      OBJECT IDENTIFIER ::= { enterprises 10626 }
nSOFT                             OBJECT IDENTIFIER ::= { enterprises 10627 }
project49AG2                      OBJECT IDENTIFIER ::= { enterprises 10628 }
questusGroup                      OBJECT IDENTIFIER ::= { enterprises 10629 }
scintecAG                         OBJECT IDENTIFIER ::= { enterprises 10630 }
seriqaNetworks                    OBJECT IDENTIFIER ::= { enterprises 10631 }
telecometInternational            OBJECT IDENTIFIER ::= { enterprises 10632 }
ticom                             OBJECT IDENTIFIER ::= { enterprises 10633 }
trioNetworks                      OBJECT IDENTIFIER ::= { enterprises 10634 }
tucows                            OBJECT IDENTIFIER ::= { enterprises 10635 }
universityOfAppliedSciencesCologne OBJECT IDENTIFIER ::= { enterprises 10636 }
vanderbiltUniversityMedicalCenter OBJECT IDENTIFIER ::= { enterprises 10637 }
venation                          OBJECT IDENTIFIER ::= { enterprises 10638 }
unassigned2                       OBJECT IDENTIFIER ::= { enterprises 10639 }
westInteractiveCorporation        OBJECT IDENTIFIER ::= { enterprises 10640 }
whiteEagleInformatics             OBJECT IDENTIFIER ::= { enterprises 10641 }
zebraTechnologiesCorporation      OBJECT IDENTIFIER ::= { enterprises 10642 }
ncSoft                            OBJECT IDENTIFIER ::= { enterprises 10643 }
interactiveSoftwareDesign         OBJECT IDENTIFIER ::= { enterprises 10644 }
pandanus                          OBJECT IDENTIFIER ::= { enterprises 10645 }
adiComputerSolutions              OBJECT IDENTIFIER ::= { enterprises 10646 }
advancedScienceAndTechnologyInstitute OBJECT IDENTIFIER ::= { enterprises 10647 }
blazenet                          OBJECT IDENTIFIER ::= { enterprises 10648 }
dstInnovis                        OBJECT IDENTIFIER ::= { enterprises 10649 }
easterEggs                        OBJECT IDENTIFIER ::= { enterprises 10650 }
enac                              OBJECT IDENTIFIER ::= { enterprises 10651 }
ezitrustLimited                   OBJECT IDENTIFIER ::= { enterprises 10652 }
fotreAndAssociates                OBJECT IDENTIFIER ::= { enterprises 10653 }
futureSpace                       OBJECT IDENTIFIER ::= { enterprises 10654 }
globalOfficeSoftwarePty           OBJECT IDENTIFIER ::= { enterprises 10655 }
hardyAndAssociates                OBJECT IDENTIFIER ::= { enterprises 10656 }
infocyclone                       OBJECT IDENTIFIER ::= { enterprises 10657 }
ipServices                        OBJECT IDENTIFIER ::= { enterprises 10658 }
isrGlobalTelecom                  OBJECT IDENTIFIER ::= { enterprises 10659 }
keytrendTechnology                OBJECT IDENTIFIER ::= { enterprises 10660 }
mainbrain                         OBJECT IDENTIFIER ::= { enterprises 10661 }
midHudsonCommunications           OBJECT IDENTIFIER ::= { enterprises 10662 }
mqs                               OBJECT IDENTIFIER ::= { enterprises 10663 }
netropolis                        OBJECT IDENTIFIER ::= { enterprises 10664 }
ocyrus                            OBJECT IDENTIFIER ::= { enterprises 10665 }
organizationOfResidenceStudents   OBJECT IDENTIFIER ::= { enterprises 10666 }
proximaTechnologyPty              OBJECT IDENTIFIER ::= { enterprises 10667 }
riodata                           OBJECT IDENTIFIER ::= { enterprises 10668 }
sanMiguelIndustrialSA             OBJECT IDENTIFIER ::= { enterprises 10669 }
solutionsETC                      OBJECT IDENTIFIER ::= { enterprises 10670 }
studioAlpha                       OBJECT IDENTIFIER ::= { enterprises 10671 }
swarthmoreCollege                 OBJECT IDENTIFIER ::= { enterprises 10672 }
telem                             OBJECT IDENTIFIER ::= { enterprises 10673 }
topKeskus                         OBJECT IDENTIFIER ::= { enterprises 10674 }
unesco                            OBJECT IDENTIFIER ::= { enterprises 10675 }
unidataCommunicationSystems       OBJECT IDENTIFIER ::= { enterprises 10676 }
universityOfDebrecen              OBJECT IDENTIFIER ::= { enterprises 10677 }
worldwidewatson                   OBJECT IDENTIFIER ::= { enterprises 10678 }
zzyzxTechnologies                 OBJECT IDENTIFIER ::= { enterprises 10679 }
capcomAG                          OBJECT IDENTIFIER ::= { enterprises 10680 }
kasys                             OBJECT IDENTIFIER ::= { enterprises 10681 }
udcast                            OBJECT IDENTIFIER ::= { enterprises 10682 }
heamanSystemCo                    OBJECT IDENTIFIER ::= { enterprises 10683 }
terabolic                         OBJECT IDENTIFIER ::= { enterprises 10684 }
objectToolsLimited                OBJECT IDENTIFIER ::= { enterprises 10685 }
thruportTechnologies              OBJECT IDENTIFIER ::= { enterprises 10686 }
townsendCommunications            OBJECT IDENTIFIER ::= { enterprises 10687 }
unassigned3                       OBJECT IDENTIFIER ::= { enterprises 10688 }
ahazaSystems                      OBJECT IDENTIFIER ::= { enterprises 10689 }
celltrexLTD                       OBJECT IDENTIFIER ::= { enterprises 10690 }
chataigner                        OBJECT IDENTIFIER ::= { enterprises 10691 }
freenetdeAG                       OBJECT IDENTIFIER ::= { enterprises 10692 }
itopia                            OBJECT IDENTIFIER ::= { enterprises 10693 }
measurableSolutions               OBJECT IDENTIFIER ::= { enterprises 10694 }
nixc                              OBJECT IDENTIFIER ::= { enterprises 10695 }
nuxeo                             OBJECT IDENTIFIER ::= { enterprises 10696 }
optioSoftware                     OBJECT IDENTIFIER ::= { enterprises 10697 }
sanit                             OBJECT IDENTIFIER ::= { enterprises 10698 }
spellcasterTelecommunications     OBJECT IDENTIFIER ::= { enterprises 10699 }
bulldogTechnologies               OBJECT IDENTIFIER ::= { enterprises 10700 }
telefonicaDataCorp                OBJECT IDENTIFIER ::= { enterprises 10701 }
solvare                           OBJECT IDENTIFIER ::= { enterprises 10702 }
atnet                             OBJECT IDENTIFIER ::= { enterprises 10703 }
phionInformationTechnologies      OBJECT IDENTIFIER ::= { enterprises 10704 }
vogtElectronicAG                  OBJECT IDENTIFIER ::= { enterprises 10705 }
acceleratedEncryptionProcessing   OBJECT IDENTIFIER ::= { enterprises 10706 }
adhersis                          OBJECT IDENTIFIER ::= { enterprises 10707 }
advancedSystemArchitectures       OBJECT IDENTIFIER ::= { enterprises 10708 }
atux                              OBJECT IDENTIFIER ::= { enterprises 10709 }
avanade                           OBJECT IDENTIFIER ::= { enterprises 10710 }
bawi                              OBJECT IDENTIFIER ::= { enterprises 10711 }
belkamneft                        OBJECT IDENTIFIER ::= { enterprises 10712 }
chevin                            OBJECT IDENTIFIER ::= { enterprises 10713 }
dimensionData                     OBJECT IDENTIFIER ::= { enterprises 10714 }
forwardpath                       OBJECT IDENTIFIER ::= { enterprises 10715 }
freedomlandITNSpA                 OBJECT IDENTIFIER ::= { enterprises 10716 }
genieTelecom                      OBJECT IDENTIFIER ::= { enterprises 10717 }
harrisWilderPty                   OBJECT IDENTIFIER ::= { enterprises 10718 }
aots                              OBJECT IDENTIFIER ::= { enterprises 10719 }
limsi                             OBJECT IDENTIFIER ::= { enterprises 10720 }
layerNNetworks                    OBJECT IDENTIFIER ::= { enterprises 10721 }
marqueD                           OBJECT IDENTIFIER ::= { enterprises 10722 }
mercuryPS                         OBJECT IDENTIFIER ::= { enterprises 10723 }
morpheusNet                       OBJECT IDENTIFIER ::= { enterprises 10724 }
pacificInternet                   OBJECT IDENTIFIER ::= { enterprises 10725 }
quantiva                          OBJECT IDENTIFIER ::= { enterprises 10726 }
redCientificaPeruana              OBJECT IDENTIFIER ::= { enterprises 10727 }
redlineCommunications             OBJECT IDENTIFIER ::= { enterprises 10728 }
redMCommunications                OBJECT IDENTIFIER ::= { enterprises 10729 }
seeTelecom                        OBJECT IDENTIFIER ::= { enterprises 10730 }
siliconEnergy                     OBJECT IDENTIFIER ::= { enterprises 10731 }
symbidiaLimited                   OBJECT IDENTIFIER ::= { enterprises 10732 }
theMercuryFileSystem              OBJECT IDENTIFIER ::= { enterprises 10733 }
tippingpointTechnologies          OBJECT IDENTIFIER ::= { enterprises 10734 }
unicornHoldingAs                  OBJECT IDENTIFIER ::= { enterprises 10735 }
universityOfDenver                OBJECT IDENTIFIER ::= { enterprises 10736 }
webSimulation                     OBJECT IDENTIFIER ::= { enterprises 10737 }
comuniq                           OBJECT IDENTIFIER ::= { enterprises 10738 }
delphicMedicalSystems             OBJECT IDENTIFIER ::= { enterprises 10739 }
neodev                            OBJECT IDENTIFIER ::= { enterprises 10740 }
verticalInversionSystems          OBJECT IDENTIFIER ::= { enterprises 10741 }
nozemaNV                          OBJECT IDENTIFIER ::= { enterprises 10742 }
riksf                             OBJECT IDENTIFIER ::= { enterprises 10743 }
kvarnb                            OBJECT IDENTIFIER ::= { enterprises 10744 }
csoLanifex                        OBJECT IDENTIFIER ::= { enterprises 10745 }
rechenzentrumDerBundesfinanzverwaltungFrankfurtAmMain OBJECT IDENTIFIER ::= { enterprises 10746 }
rowanUniversity                   OBJECT IDENTIFIER ::= { enterprises 10747 }
softwareFactory                   OBJECT IDENTIFIER ::= { enterprises 10748 }
devSecurePty                      OBJECT IDENTIFIER ::= { enterprises 10749 }
threeGScenePlc                    OBJECT IDENTIFIER ::= { enterprises 10750 }
threePlex                         OBJECT IDENTIFIER ::= { enterprises 10751 }
artimanOy                         OBJECT IDENTIFIER ::= { enterprises 10752 }
billingForEnterprises             OBJECT IDENTIFIER ::= { enterprises 10753 }
casTecnologiaSA                   OBJECT IDENTIFIER ::= { enterprises 10754 }
chipdata                          OBJECT IDENTIFIER ::= { enterprises 10755 }
chonghoInformationAndCommunicationsCo OBJECT IDENTIFIER ::= { enterprises 10756 }
diogenes                          OBJECT IDENTIFIER ::= { enterprises 10757 }
elyziumLimited                    OBJECT IDENTIFIER ::= { enterprises 10758 }
energosAsa                        OBJECT IDENTIFIER ::= { enterprises 10759 }
gravityHillTechnologies           OBJECT IDENTIFIER ::= { enterprises 10760 }
greenheckFan                      OBJECT IDENTIFIER ::= { enterprises 10761 }
horizonWebGraphics                OBJECT IDENTIFIER ::= { enterprises 10762 }
hansungTeliann                    OBJECT IDENTIFIER ::= { enterprises 10763 }
infotrek                          OBJECT IDENTIFIER ::= { enterprises 10764 }
inzenCo                           OBJECT IDENTIFIER ::= { enterprises 10765 }
isgSystemsAB                      OBJECT IDENTIFIER ::= { enterprises 10766 }
jamesMadisonUniversity            OBJECT IDENTIFIER ::= { enterprises 10767 }
l                                 OBJECT IDENTIFIER ::= { enterprises 10768 }
litBerlin                         OBJECT IDENTIFIER ::= { enterprises 10769 }
makeIngcomar                      OBJECT IDENTIFIER ::= { enterprises 10770 }
morrisonAcademy                   OBJECT IDENTIFIER ::= { enterprises 10771 }
novalisMedia                      OBJECT IDENTIFIER ::= { enterprises 10772 }
pacificNorthwestNetworks          OBJECT IDENTIFIER ::= { enterprises 10773 }
perforations                      OBJECT IDENTIFIER ::= { enterprises 10774 }
periFormworkSystems               OBJECT IDENTIFIER ::= { enterprises 10775 }
reactiveNetworkSolutions          OBJECT IDENTIFIER ::= { enterprises 10776 }
reviconSrl                        OBJECT IDENTIFIER ::= { enterprises 10777 }
rtclLab                           OBJECT IDENTIFIER ::= { enterprises 10778 }
sparkassenversicherungWiesbaden   OBJECT IDENTIFIER ::= { enterprises 10779 }
swan                              OBJECT IDENTIFIER ::= { enterprises 10780 }
tacAB                             OBJECT IDENTIFIER ::= { enterprises 10781 }
tazzNetworks                      OBJECT IDENTIFIER ::= { enterprises 10782 }
theChurchOfJesusChristOfLatterDaySaints OBJECT IDENTIFIER ::= { enterprises 10783 }
timeAndFrequencySolutions         OBJECT IDENTIFIER ::= { enterprises 10784 }
transtechNetworks                 OBJECT IDENTIFIER ::= { enterprises 10785 }
unswPhysicsAPT                    OBJECT IDENTIFIER ::= { enterprises 10786 }
verity                            OBJECT IDENTIFIER ::= { enterprises 10787 }
voltInformationSciences           OBJECT IDENTIFIER ::= { enterprises 10788 }
webagents                         OBJECT IDENTIFIER ::= { enterprises 10789 }
websilicon                        OBJECT IDENTIFIER ::= { enterprises 10790 }
westone                           OBJECT IDENTIFIER ::= { enterprises 10791 }
xelineCo                          OBJECT IDENTIFIER ::= { enterprises 10792 }
youraspPty                        OBJECT IDENTIFIER ::= { enterprises 10793 }
ztrControlSystem                  OBJECT IDENTIFIER ::= { enterprises 10794 }
bizzTechnologiesSAS               OBJECT IDENTIFIER ::= { enterprises 10795 }
crfConsulting                     OBJECT IDENTIFIER ::= { enterprises 10796 }
commercialDataSystems             OBJECT IDENTIFIER ::= { enterprises 10797 }
commtel                           OBJECT IDENTIFIER ::= { enterprises 10798 }
jungoSoftwareTechnologies         OBJECT IDENTIFIER ::= { enterprises 10799 }
kinor                             OBJECT IDENTIFIER ::= { enterprises 10800 }
rapid7                            OBJECT IDENTIFIER ::= { enterprises 10801 }
rbg                               OBJECT IDENTIFIER ::= { enterprises 10802 }
staudingerWels                    OBJECT IDENTIFIER ::= { enterprises 10803 }
unionBankOfCalifornia             OBJECT IDENTIFIER ::= { enterprises 10804 }
wedgetailCommunications           OBJECT IDENTIFIER ::= { enterprises 10805 }
xebeoCommunications               OBJECT IDENTIFIER ::= { enterprises 10806 }
centraleFinancienInstellingen     OBJECT IDENTIFIER ::= { enterprises 10807 }
chinaGreatwallComputerShenzhenCo  OBJECT IDENTIFIER ::= { enterprises 10808 }
dishaTechnologies                 OBJECT IDENTIFIER ::= { enterprises 10809 }
nobelmann                         OBJECT IDENTIFIER ::= { enterprises 10810 }
xiamenGoodFirstOpticsElectricityIntegrationCO OBJECT IDENTIFIER ::= { enterprises 10811 }
infotecs                          OBJECT IDENTIFIER ::= { enterprises 10812 }
centreNationalDeLaRechercheScientifique OBJECT IDENTIFIER ::= { enterprises 10813 }
unifiedTechnologies               OBJECT IDENTIFIER ::= { enterprises 10814 }
cybertrader                       OBJECT IDENTIFIER ::= { enterprises 10815 }
datangRadioCommunicationBranch    OBJECT IDENTIFIER ::= { enterprises 10816 }
heraeusInfosystems                OBJECT IDENTIFIER ::= { enterprises 10817 }
windhAB                           OBJECT IDENTIFIER ::= { enterprises 10818 }
lmSistemas                        OBJECT IDENTIFIER ::= { enterprises 10820 }
absolight                         OBJECT IDENTIFIER ::= { enterprises 10821 }
adtec                             OBJECT IDENTIFIER ::= { enterprises 10822 }
advancedResearchAndTechnology     OBJECT IDENTIFIER ::= { enterprises 10823 }
agavaSoftware                     OBJECT IDENTIFIER ::= { enterprises 10824 }
alectta                           OBJECT IDENTIFIER ::= { enterprises 10825 }
aliceSalomonFachhochschuleF       OBJECT IDENTIFIER ::= { enterprises 10826 }
alveTechnologyCorporation         OBJECT IDENTIFIER ::= { enterprises 10827 }
americanDataTechnology            OBJECT IDENTIFIER ::= { enterprises 10828 }
andoverControlsCorporation        OBJECT IDENTIFIER ::= { enterprises 10829 }
apcon                             OBJECT IDENTIFIER ::= { enterprises 10830 }
atOlivercom                       OBJECT IDENTIFIER ::= { enterprises 10831 }
b2c2                              OBJECT IDENTIFIER ::= { enterprises 10832 }
binarycoreNetworks                OBJECT IDENTIFIER ::= { enterprises 10833 }
cargobay                          OBJECT IDENTIFIER ::= { enterprises 10834 }
cartoonviolencenet                OBJECT IDENTIFIER ::= { enterprises 10835 }
commandETechnologyCo              OBJECT IDENTIFIER ::= { enterprises 10836 }
comphealth                        OBJECT IDENTIFIER ::= { enterprises 10837 }
contecCV                          OBJECT IDENTIFIER ::= { enterprises 10838 }
distributel                       OBJECT IDENTIFIER ::= { enterprises 10839 }
dragonComputerConsultants         OBJECT IDENTIFIER ::= { enterprises 10840 }
ejasent                           OBJECT IDENTIFIER ::= { enterprises 10841 }
enbwService                       OBJECT IDENTIFIER ::= { enterprises 10842 }
ferret                            OBJECT IDENTIFIER ::= { enterprises 10843 }
fidelia                           OBJECT IDENTIFIER ::= { enterprises 10844 }
grandmas                          OBJECT IDENTIFIER ::= { enterprises 10845 }
impactTechnologies                OBJECT IDENTIFIER ::= { enterprises 10846 }
insystek                          OBJECT IDENTIFIER ::= { enterprises 10847 }
ipfonix                           OBJECT IDENTIFIER ::= { enterprises 10848 }
ithirielSoftware                  OBJECT IDENTIFIER ::= { enterprises 10849 }
kefta                             OBJECT IDENTIFIER ::= { enterprises 10850 }
knowledgeIntelligenceAG           OBJECT IDENTIFIER ::= { enterprises 10851 }
kuulalaakeriOy                    OBJECT IDENTIFIER ::= { enterprises 10852 }
ltcSpZOo                          OBJECT IDENTIFIER ::= { enterprises 10853 }
lvivNationalPolytechnicalUniversity OBJECT IDENTIFIER ::= { enterprises 10854 }
masconCommunicationTechnologies   OBJECT IDENTIFIER ::= { enterprises 10855 }
menloParkTechnologies             OBJECT IDENTIFIER ::= { enterprises 10856 }
mindframeSoftwareAndServicesPvt   OBJECT IDENTIFIER ::= { enterprises 10857 }
myconNetworks                     OBJECT IDENTIFIER ::= { enterprises 10858 }
myinternet                        OBJECT IDENTIFIER ::= { enterprises 10859 }
naumannEDV                        OBJECT IDENTIFIER ::= { enterprises 10860 }
nielsBohrInstitute                OBJECT IDENTIFIER ::= { enterprises 10861 }
noahIndustries                    OBJECT IDENTIFIER ::= { enterprises 10862 }
odysseyTechnologiesLimited        OBJECT IDENTIFIER ::= { enterprises 10863 }
pacificUniversity                 OBJECT IDENTIFIER ::= { enterprises 10864 }
peteWilson                        OBJECT IDENTIFIER ::= { enterprises 10865 }
philipMLembo                      OBJECT IDENTIFIER ::= { enterprises 10866 }
playdeadNetworks                  OBJECT IDENTIFIER ::= { enterprises 10867 }
premitechAS                       OBJECT IDENTIFIER ::= { enterprises 10868 }
psc                               OBJECT IDENTIFIER ::= { enterprises 10869 }
safewwwRAndd                      OBJECT IDENTIFIER ::= { enterprises 10870 }
shanghaiTerabandPhtonicsCo        OBJECT IDENTIFIER ::= { enterprises 10871 }
skyflow                           OBJECT IDENTIFIER ::= { enterprises 10872 }
sorosFoundationKazakhstan         OBJECT IDENTIFIER ::= { enterprises 10873 }
spectrumAstro                     OBJECT IDENTIFIER ::= { enterprises 10874 }
sshCommunicationsSecurityCorp     OBJECT IDENTIFIER ::= { enterprises 10875 }
superMicroComputer                OBJECT IDENTIFIER ::= { enterprises 10876 }
systemServicesSpZOO               OBJECT IDENTIFIER ::= { enterprises 10877 }
techlinkDesenvolvimentosTecnologicos OBJECT IDENTIFIER ::= { enterprises 10878 }
tenebras                          OBJECT IDENTIFIER ::= { enterprises 10879 }
togabiTechnologies                OBJECT IDENTIFIER ::= { enterprises 10880 }
uffizioSoftwareConsultantsPvt     OBJECT IDENTIFIER ::= { enterprises 10881 }
universit2                        OBJECT IDENTIFIER ::= { enterprises 10882 }
universityOfTuebingen             OBJECT IDENTIFIER ::= { enterprises 10883 }
vinzant                           OBJECT IDENTIFIER ::= { enterprises 10884 }
virtualMonetTechnologies          OBJECT IDENTIFIER ::= { enterprises 10885 }
westlandHelicopters               OBJECT IDENTIFIER ::= { enterprises 10886 }
wizcom                            OBJECT IDENTIFIER ::= { enterprises 10887 }
xelus                             OBJECT IDENTIFIER ::= { enterprises 10888 }
alDigital                         OBJECT IDENTIFIER ::= { enterprises 10889 }
commworks                         OBJECT IDENTIFIER ::= { enterprises 10890 }
dave                              OBJECT IDENTIFIER ::= { enterprises 10891 }
doctorsnetuk                      OBJECT IDENTIFIER ::= { enterprises 10892 }
iomedexCorporation                OBJECT IDENTIFIER ::= { enterprises 10893 }
novraTechnologies                 OBJECT IDENTIFIER ::= { enterprises 10894 }
raonetSystems                     OBJECT IDENTIFIER ::= { enterprises 10895 }
theCareerAndEducationNetwork      OBJECT IDENTIFIER ::= { enterprises 10896 }
recombinantweb                    OBJECT IDENTIFIER ::= { enterprises 10897 }
oozood                            OBJECT IDENTIFIER ::= { enterprises 10898 }
consorsDiscountBrokerAG           OBJECT IDENTIFIER ::= { enterprises 10899 }
serco                             OBJECT IDENTIFIER ::= { enterprises 10900 }
spinnakerNetworks                 OBJECT IDENTIFIER ::= { enterprises 10901 }
threeIC                           OBJECT IDENTIFIER ::= { enterprises 10902 }
activate                          OBJECT IDENTIFIER ::= { enterprises 10903 }
alpineMayrederBau                 OBJECT IDENTIFIER ::= { enterprises 10904 }
arsenalDigitalSolutions           OBJECT IDENTIFIER ::= { enterprises 10905 }
aSKComputers                      OBJECT IDENTIFIER ::= { enterprises 10906 }
atebLimited                       OBJECT IDENTIFIER ::= { enterprises 10907 }
bigsurCommunications              OBJECT IDENTIFIER ::= { enterprises 10908 }
broadtelCommunications            OBJECT IDENTIFIER ::= { enterprises 10909 }
chateauSystems                    OBJECT IDENTIFIER ::= { enterprises 10910 }
appello                           OBJECT IDENTIFIER ::= { enterprises 10911 }
cincomSystems                     OBJECT IDENTIFIER ::= { enterprises 10912 }
clientSoftwareInternational       OBJECT IDENTIFIER ::= { enterprises 10913 }
coltTelecommunications            OBJECT IDENTIFIER ::= { enterprises 10914 }
conagraFoods                      OBJECT IDENTIFIER ::= { enterprises 10915 }
cynetaNetworks                    OBJECT IDENTIFIER ::= { enterprises 10916 }
datamaxCoporation                 OBJECT IDENTIFIER ::= { enterprises 10917 }
datamission                       OBJECT IDENTIFIER ::= { enterprises 10918 }
dbap                              OBJECT IDENTIFIER ::= { enterprises 10919 }
dirSolutionsBv                    OBJECT IDENTIFIER ::= { enterprises 10920 }
drumgrangeLimited                 OBJECT IDENTIFIER ::= { enterprises 10921 }
elsis                             OBJECT IDENTIFIER ::= { enterprises 10922 }
ericssonJuniperNetworksMobileIP   OBJECT IDENTIFIER ::= { enterprises 10923 }
estos                             OBJECT IDENTIFIER ::= { enterprises 10924 }
firmseek                          OBJECT IDENTIFIER ::= { enterprises 10925 }
foodBrokersLimited                OBJECT IDENTIFIER ::= { enterprises 10926 }
fullsix                           OBJECT IDENTIFIER ::= { enterprises 10927 }
fybubblancomConsulting            OBJECT IDENTIFIER ::= { enterprises 10928 }
gcdPrintlayout                    OBJECT IDENTIFIER ::= { enterprises 10929 }
georgAugustUniveristyGoettingen   OBJECT IDENTIFIER ::= { enterprises 10930 }
gigaSTREAMUMTSTechnologies        OBJECT IDENTIFIER ::= { enterprises 10931 }
gunadarmaUniversity               OBJECT IDENTIFIER ::= { enterprises 10932 }
haTechnicalSolutions              OBJECT IDENTIFIER ::= { enterprises 10933 }
hamsch                            OBJECT IDENTIFIER ::= { enterprises 10934 }
horizonDigitalEnterprise          OBJECT IDENTIFIER ::= { enterprises 10935 }
ijichiResearch                    OBJECT IDENTIFIER ::= { enterprises 10936 }
infalsys                          OBJECT IDENTIFIER ::= { enterprises 10937 }
internationalMessagingAssociatesCorporation OBJECT IDENTIFIER ::= { enterprises 10938 }
internetNews                      OBJECT IDENTIFIER ::= { enterprises 10939 }
jdThomlinson                      OBJECT IDENTIFIER ::= { enterprises 10940 }
kandalaya                         OBJECT IDENTIFIER ::= { enterprises 10941 }
lifelineNetworksBv                OBJECT IDENTIFIER ::= { enterprises 10942 }
linagora                          OBJECT IDENTIFIER ::= { enterprises 10943 }
maikisEDVDienstleistungen         OBJECT IDENTIFIER ::= { enterprises 10944 }
midwayGamesWest                   OBJECT IDENTIFIER ::= { enterprises 10945 }
mouselink                         OBJECT IDENTIFIER ::= { enterprises 10946 }
multiDruck                        OBJECT IDENTIFIER ::= { enterprises 10947 }
mynanet                           OBJECT IDENTIFIER ::= { enterprises 10948 }
netflixcom                        OBJECT IDENTIFIER ::= { enterprises 10949 }
netrakeCorporation                OBJECT IDENTIFIER ::= { enterprises 10950 }
netuseAG                          OBJECT IDENTIFIER ::= { enterprises 10951 }
netzero                           OBJECT IDENTIFIER ::= { enterprises 10952 }
nightlifese                       OBJECT IDENTIFIER ::= { enterprises 10953 }
nikolicicom                       OBJECT IDENTIFIER ::= { enterprises 10954 }
wescanLimited                     OBJECT IDENTIFIER ::= { enterprises 10955 }
noviforum                         OBJECT IDENTIFIER ::= { enterprises 10956 }
noze                              OBJECT IDENTIFIER ::= { enterprises 10957 }
olicorpTechnologies               OBJECT IDENTIFIER ::= { enterprises 10958 }
politechnikaWarszawska            OBJECT IDENTIFIER ::= { enterprises 10959 }
qualicontrol                      OBJECT IDENTIFIER ::= { enterprises 10960 }
ricciardiTechnologies             OBJECT IDENTIFIER ::= { enterprises 10961 }
rutgers                           OBJECT IDENTIFIER ::= { enterprises 10962 }
senaSystems                       OBJECT IDENTIFIER ::= { enterprises 10963 }
smtDataAS                         OBJECT IDENTIFIER ::= { enterprises 10964 }
solidstreaming                    OBJECT IDENTIFIER ::= { enterprises 10965 }
sollieCodeWorks                   OBJECT IDENTIFIER ::= { enterprises 10966 }
surftoolSystems                   OBJECT IDENTIFIER ::= { enterprises 10967 }
systematicSoftwareEngineeringAS   OBJECT IDENTIFIER ::= { enterprises 10968 }
thalesCommunications              OBJECT IDENTIFIER ::= { enterprises 10969 }
thresholdNetworks                 OBJECT IDENTIFIER ::= { enterprises 10970 }
vpnDynamics                       OBJECT IDENTIFIER ::= { enterprises 10971 }
witSoftware                       OBJECT IDENTIFIER ::= { enterprises 10972 }
xms                               OBJECT IDENTIFIER ::= { enterprises 10973 }
youngstownStateUniversity         OBJECT IDENTIFIER ::= { enterprises 10974 }
zionSoftware                      OBJECT IDENTIFIER ::= { enterprises 10975 }
zoomtowncom                       OBJECT IDENTIFIER ::= { enterprises 10976 }
gridIreland                       OBJECT IDENTIFIER ::= { enterprises 10977 }
kumamotoIndustrialResearchInstitute OBJECT IDENTIFIER ::= { enterprises 10978 }
capitelGroup                      OBJECT IDENTIFIER ::= { enterprises 10979 }
iqstorNetworks                    OBJECT IDENTIFIER ::= { enterprises 10980 }
shenzhenRouterNetworksLimited     OBJECT IDENTIFIER ::= { enterprises 10981 }
ubsWarburg                        OBJECT IDENTIFIER ::= { enterprises 10982 }
btg                               OBJECT IDENTIFIER ::= { enterprises 10983 }
bvbaWoodstone                     OBJECT IDENTIFIER ::= { enterprises 10984 }
jiveSoftware                      OBJECT IDENTIFIER ::= { enterprises 10985 }
beijingPolytechnicUniversity      OBJECT IDENTIFIER ::= { enterprises 10986 }
eircell2000                       OBJECT IDENTIFIER ::= { enterprises 10987 }
solomioCorporation                OBJECT IDENTIFIER ::= { enterprises 10988 }
alibre                            OBJECT IDENTIFIER ::= { enterprises 10989 }
astrumConsulting                  OBJECT IDENTIFIER ::= { enterprises 10990 }
axisIntegrated                    OBJECT IDENTIFIER ::= { enterprises 10991 }
babelProfessionalServicesSrl      OBJECT IDENTIFIER ::= { enterprises 10992 }
babeltechAS                       OBJECT IDENTIFIER ::= { enterprises 10993 }
biss                              OBJECT IDENTIFIER ::= { enterprises 10994 }
blueMug                           OBJECT IDENTIFIER ::= { enterprises 10995 }
ccss                              OBJECT IDENTIFIER ::= { enterprises 10996 }
connectionSoftware                OBJECT IDENTIFIER ::= { enterprises 10997 }
conversantSystems                 OBJECT IDENTIFIER ::= { enterprises 10998 }
cosAGAustria                      OBJECT IDENTIFIER ::= { enterprises 10999 }
creativeNetworkingSolutions       OBJECT IDENTIFIER ::= { enterprises 11000 }
dreyerConsulting                  OBJECT IDENTIFIER ::= { enterprises 11001 }
duMaurier                         OBJECT IDENTIFIER ::= { enterprises 11002 }
e-deltacom                        OBJECT IDENTIFIER ::= { enterprises 11003 }
earthtrax                         OBJECT IDENTIFIER ::= { enterprises 11004 }
eCertify                          OBJECT IDENTIFIER ::= { enterprises 11005 }
flashnetComputers                 OBJECT IDENTIFIER ::= { enterprises 11006 }
fmv                               OBJECT IDENTIFIER ::= { enterprises 11007 }
fujiwaraSoftOffice                OBJECT IDENTIFIER ::= { enterprises 11008 }
hadmutDanisch                     OBJECT IDENTIFIER ::= { enterprises 11009 }
harrisonFamilyOrganization        OBJECT IDENTIFIER ::= { enterprises 11010 }
hiwaayInformationServices         OBJECT IDENTIFIER ::= { enterprises 11011 }
imagineasia                       OBJECT IDENTIFIER ::= { enterprises 11012 }
lecInformationSystems             OBJECT IDENTIFIER ::= { enterprises 11013 }
libertyUniversity                 OBJECT IDENTIFIER ::= { enterprises 11014 }
lokomoSystemsAB                   OBJECT IDENTIFIER ::= { enterprises 11015 }
managestarcom                     OBJECT IDENTIFIER ::= { enterprises 11016 }
maraSystemsAB                     OBJECT IDENTIFIER ::= { enterprises 11017 }
massillonCableCommunications      OBJECT IDENTIFIER ::= { enterprises 11018 }
menta                             OBJECT IDENTIFIER ::= { enterprises 11019 }
mvpSystems                        OBJECT IDENTIFIER ::= { enterprises 11020 }
n2Broadband                       OBJECT IDENTIFIER ::= { enterprises 11021 }
omnisciSoftware                   OBJECT IDENTIFIER ::= { enterprises 11022 }
oucs                              OBJECT IDENTIFIER ::= { enterprises 11023 }
pAndsDataComCorporation           OBJECT IDENTIFIER ::= { enterprises 11024 }
pagoo                             OBJECT IDENTIFIER ::= { enterprises 11025 }
perfectwayCorporation             OBJECT IDENTIFIER ::= { enterprises 11026 }
physicsDepartment                 OBJECT IDENTIFIER ::= { enterprises 11027 }
reliableNetworks                  OBJECT IDENTIFIER ::= { enterprises 11028 }
reziprozitaetConsulting           OBJECT IDENTIFIER ::= { enterprises 11029 }
routefree                         OBJECT IDENTIFIER ::= { enterprises 11030 }
satecSA                           OBJECT IDENTIFIER ::= { enterprises 11031 }
semandexNetworks                  OBJECT IDENTIFIER ::= { enterprises 11032 }
sentitoNetworks                   OBJECT IDENTIFIER ::= { enterprises 11033 }
sentorMonitoringSystemsPty        OBJECT IDENTIFIER ::= { enterprises 11034 }
sheerGeniusSoftware               OBJECT IDENTIFIER ::= { enterprises 11035 }
softax                            OBJECT IDENTIFIER ::= { enterprises 11036 }
stratycLLC                        OBJECT IDENTIFIER ::= { enterprises 11037 }
tecoSOFTEspa                      OBJECT IDENTIFIER ::= { enterprises 11038 }
tivo                              OBJECT IDENTIFIER ::= { enterprises 11039 }
toolBankingSolutions              OBJECT IDENTIFIER ::= { enterprises 11040 }
ufsm                              OBJECT IDENTIFIER ::= { enterprises 11041 }
viaclix                           OBJECT IDENTIFIER ::= { enterprises 11042 }
vidaSoftwareSL                    OBJECT IDENTIFIER ::= { enterprises 11043 }
vodafone                          OBJECT IDENTIFIER ::= { enterprises 11044 }
windborneProductions              OBJECT IDENTIFIER ::= { enterprises 11045 }
zeroComputingSrl                  OBJECT IDENTIFIER ::= { enterprises 11046 }
akIndustrieinformatik             OBJECT IDENTIFIER ::= { enterprises 11047 }
billitonInternetservices          OBJECT IDENTIFIER ::= { enterprises 11048 }
cpCorporatePlanningAG             OBJECT IDENTIFIER ::= { enterprises 11049 }
idxSystemsCorporations            OBJECT IDENTIFIER ::= { enterprises 11050 }
pointSystems                      OBJECT IDENTIFIER ::= { enterprises 11051 }
achmeaHoldingNV                   OBJECT IDENTIFIER ::= { enterprises 11052 }
directInternet                    OBJECT IDENTIFIER ::= { enterprises 11053 }
romanSeidl                        OBJECT IDENTIFIER ::= { enterprises 11054 }
innoaceCO                         OBJECT IDENTIFIER ::= { enterprises 11055 }
allmycrapcom                      OBJECT IDENTIFIER ::= { enterprises 11056 }
eyefinity                         OBJECT IDENTIFIER ::= { enterprises 11057 }
hitachiCommunicationSystems       OBJECT IDENTIFIER ::= { enterprises 11058 }
impressSOFTWAREAG                 OBJECT IDENTIFIER ::= { enterprises 11059 }
intervoiceBrite                   OBJECT IDENTIFIER ::= { enterprises 11060 }
longitude                         OBJECT IDENTIFIER ::= { enterprises 11061 }
nurnbergScientific                OBJECT IDENTIFIER ::= { enterprises 11062 }
pingmagicLimited                  OBJECT IDENTIFIER ::= { enterprises 11063 }
rhbSecurities                     OBJECT IDENTIFIER ::= { enterprises 11064 }
telcoware                         OBJECT IDENTIFIER ::= { enterprises 11065 }
teniadTechnologies                OBJECT IDENTIFIER ::= { enterprises 11066 }
universityOfBelgrade              OBJECT IDENTIFIER ::= { enterprises 11067 }
webscreenTechnology               OBJECT IDENTIFIER ::= { enterprises 11068 }
yandex                            OBJECT IDENTIFIER ::= { enterprises 11069 }
ureachTechnologies                OBJECT IDENTIFIER ::= { enterprises 11070 }
motusTechnologies                 OBJECT IDENTIFIER ::= { enterprises 11071 }
iotecAB                           OBJECT IDENTIFIER ::= { enterprises 11072 }
thAngel                           OBJECT IDENTIFIER ::= { enterprises 11073 }
alter                             OBJECT IDENTIFIER ::= { enterprises 11074 }
antarixEApplicationsLimited       OBJECT IDENTIFIER ::= { enterprises 11075 }
banestoSA                         OBJECT IDENTIFIER ::= { enterprises 11076 }
cnetDoo                           OBJECT IDENTIFIER ::= { enterprises 11077 }
centralworksLLC                   OBJECT IDENTIFIER ::= { enterprises 11078 }
eit                               OBJECT IDENTIFIER ::= { enterprises 11079 }
firstHop                          OBJECT IDENTIFIER ::= { enterprises 11080 }
hydrogenLine                      OBJECT IDENTIFIER ::= { enterprises 11081 }
illinoisCentralCollege            OBJECT IDENTIFIER ::= { enterprises 11082 }
intersixTechnologiesSA            OBJECT IDENTIFIER ::= { enterprises 11083 }
itdevices                         OBJECT IDENTIFIER ::= { enterprises 11084 }
manojam                           OBJECT IDENTIFIER ::= { enterprises 11085 }
mindtreeConsultingPvt             OBJECT IDENTIFIER ::= { enterprises 11086 }
netForest                         OBJECT IDENTIFIER ::= { enterprises 11087 }
netusTechnologiesCo               OBJECT IDENTIFIER ::= { enterprises 11088 }
preferredSystems                  OBJECT IDENTIFIER ::= { enterprises 11089 }
properoLimited                    OBJECT IDENTIFIER ::= { enterprises 11090 }
razeTechnologies                  OBJECT IDENTIFIER ::= { enterprises 11091 }
stBonifaceGeneralHospital         OBJECT IDENTIFIER ::= { enterprises 11092 }
telamonSystems                    OBJECT IDENTIFIER ::= { enterprises 11093 }
xpediteSystems                    OBJECT IDENTIFIER ::= { enterprises 11094 }
loeaCommunications                OBJECT IDENTIFIER ::= { enterprises 11095 }
bluearcUK                         OBJECT IDENTIFIER ::= { enterprises 11096 }
hexalAG                           OBJECT IDENTIFIER ::= { enterprises 11097 }
comtelco                          OBJECT IDENTIFIER ::= { enterprises 11098 }
dickersonEnginering               OBJECT IDENTIFIER ::= { enterprises 11099 }
linuxNetworX                      OBJECT IDENTIFIER ::= { enterprises 11100 }
nriSecureTechnologies             OBJECT IDENTIFIER ::= { enterprises 11101 }
osaTechnologies                   OBJECT IDENTIFIER ::= { enterprises 11102 }
opusInternationalConsultants      OBJECT IDENTIFIER ::= { enterprises 11103 }
passbackITConsultancy             OBJECT IDENTIFIER ::= { enterprises 11104 }
pivotConsulting                   OBJECT IDENTIFIER ::= { enterprises 11105 }
scene7                            OBJECT IDENTIFIER ::= { enterprises 11106 }
ucentricSystems                   OBJECT IDENTIFIER ::= { enterprises 11107 }
wavemarket                        OBJECT IDENTIFIER ::= { enterprises 11108 }
xdvVereinF                        OBJECT IDENTIFIER ::= { enterprises 11109 }
arkivio                           OBJECT IDENTIFIER ::= { enterprises 11110 }
bellOntarioServiceAssurance       OBJECT IDENTIFIER ::= { enterprises 11111 }
stephenGouldPaperCo               OBJECT IDENTIFIER ::= { enterprises 11112 }
bjcHealthCare                     OBJECT IDENTIFIER ::= { enterprises 11113 }
citrusCommunications              OBJECT IDENTIFIER ::= { enterprises 11114 }
georgeFoxUniversity               OBJECT IDENTIFIER ::= { enterprises 11115 }
marcoHentschel                    OBJECT IDENTIFIER ::= { enterprises 11116 }
verenigingOpenDomeinZenon         OBJECT IDENTIFIER ::= { enterprises 11117 }
alpha1Communications              OBJECT IDENTIFIER ::= { enterprises 11118 }
threeIndiacom                     OBJECT IDENTIFIER ::= { enterprises 11119 }
advancedSoftwareResources         OBJECT IDENTIFIER ::= { enterprises 11120 }
c3                                OBJECT IDENTIFIER ::= { enterprises 11121 }
cencosudSA                        OBJECT IDENTIFIER ::= { enterprises 11122 }
colruyt                           OBJECT IDENTIFIER ::= { enterprises 11123 }
contenture                        OBJECT IDENTIFIER ::= { enterprises 11124 }
domaniSoftwareServices            OBJECT IDENTIFIER ::= { enterprises 11125 }
escpEAP                           OBJECT IDENTIFIER ::= { enterprises 11126 }
fstSrl                            OBJECT IDENTIFIER ::= { enterprises 11127 }
gadboisConsulting                 OBJECT IDENTIFIER ::= { enterprises 11128 }
google                            OBJECT IDENTIFIER ::= { enterprises 11129 }
h2                                OBJECT IDENTIFIER ::= { enterprises 11130 }
insidersInformationManagement     OBJECT IDENTIFIER ::= { enterprises 11131 }
integralSolutionsCorporation      OBJECT IDENTIFIER ::= { enterprises 11132 }
jemmacSoftwareLimited             OBJECT IDENTIFIER ::= { enterprises 11133 }
lentronics                        OBJECT IDENTIFIER ::= { enterprises 11134 }
marianEichhloz                    OBJECT IDENTIFIER ::= { enterprises 11135 }
meitetsuSystemDevCo               OBJECT IDENTIFIER ::= { enterprises 11136 }
metaparadigmPte                   OBJECT IDENTIFIER ::= { enterprises 11137 }
mformationTechnologies            OBJECT IDENTIFIER ::= { enterprises 11138 }
neowizCorporation                 OBJECT IDENTIFIER ::= { enterprises 11139 }
networkCenter                     OBJECT IDENTIFIER ::= { enterprises 11140 }
omneonVideoNetworks               OBJECT IDENTIFIER ::= { enterprises 11141 }
o                                 OBJECT IDENTIFIER ::= { enterprises 11142 }
pcsnc                             OBJECT IDENTIFIER ::= { enterprises 11143 }
radpharm                          OBJECT IDENTIFIER ::= { enterprises 11144 }
siemensFinancialServices          OBJECT IDENTIFIER ::= { enterprises 11145 }
siemensInformationsSystemsLimited OBJECT IDENTIFIER ::= { enterprises 11146 }
svtoHewlettPackard                OBJECT IDENTIFIER ::= { enterprises 11147 }
swanSystems                       OBJECT IDENTIFIER ::= { enterprises 11148 }
ti                                OBJECT IDENTIFIER ::= { enterprises 11149 }
unwiredsoft                       OBJECT IDENTIFIER ::= { enterprises 11150 }
urschelLaboratories               OBJECT IDENTIFIER ::= { enterprises 11151 }
vocalcom                          OBJECT IDENTIFIER ::= { enterprises 11152 }
webSquare                         OBJECT IDENTIFIER ::= { enterprises 11153 }
wirexCommunications               OBJECT IDENTIFIER ::= { enterprises 11154 }
wvsGroep                          OBJECT IDENTIFIER ::= { enterprises 11155 }
cdmedic                           OBJECT IDENTIFIER ::= { enterprises 11156 }
multitechSolutions                OBJECT IDENTIFIER ::= { enterprises 11157 }
panservice                        OBJECT IDENTIFIER ::= { enterprises 11158 }
pcDialogs                         OBJECT IDENTIFIER ::= { enterprises 11159 }
tdkCorporation                    OBJECT IDENTIFIER ::= { enterprises 11160 }
wistronCorporation                OBJECT IDENTIFIER ::= { enterprises 11161 }
advancedCampusServices            OBJECT IDENTIFIER ::= { enterprises 11162 }
halComputerSystems                OBJECT IDENTIFIER ::= { enterprises 11163 }
pbhPlanungsbueroHammer            OBJECT IDENTIFIER ::= { enterprises 11164 }
acerMobileNetworks                OBJECT IDENTIFIER ::= { enterprises 11165 }
allewa                            OBJECT IDENTIFIER ::= { enterprises 11166 }
azurtec                           OBJECT IDENTIFIER ::= { enterprises 11167 }
bancaDelGottardo                  OBJECT IDENTIFIER ::= { enterprises 11168 }
beaconBioscience                  OBJECT IDENTIFIER ::= { enterprises 11169 }
commsology                        OBJECT IDENTIFIER ::= { enterprises 11170 }
crol                              OBJECT IDENTIFIER ::= { enterprises 11171 }
dieInformatikWerkstatt            OBJECT IDENTIFIER ::= { enterprises 11172 }
directorySolutions                OBJECT IDENTIFIER ::= { enterprises 11173 }
dxAntennaCo                       OBJECT IDENTIFIER ::= { enterprises 11174 }
epicGroupPlc                      OBJECT IDENTIFIER ::= { enterprises 11175 }
extelligence                      OBJECT IDENTIFIER ::= { enterprises 11176 }
grapevineInteractive              OBJECT IDENTIFIER ::= { enterprises 11177 }
guardianControlsInternational     OBJECT IDENTIFIER ::= { enterprises 11178 }
hereuareCommunications            OBJECT IDENTIFIER ::= { enterprises 11179 }
invisibleHandNetworks             OBJECT IDENTIFIER ::= { enterprises 11180 }
janSchmidtDVBeratung              OBJECT IDENTIFIER ::= { enterprises 11181 }
kretzIndustries                   OBJECT IDENTIFIER ::= { enterprises 11182 }
mitacInternationalCorp            OBJECT IDENTIFIER ::= { enterprises 11183 }
narayInformationAndCommunicationEnterprise OBJECT IDENTIFIER ::= { enterprises 11184 }
possioAB                          OBJECT IDENTIFIER ::= { enterprises 11185 }
rattanInformation                 OBJECT IDENTIFIER ::= { enterprises 11186 }
snvNetherlandsDevelopmentOrganisation OBJECT IDENTIFIER ::= { enterprises 11187 }
universitatRoviraIVirgili         OBJECT IDENTIFIER ::= { enterprises 11188 }
universityOfAppliedSciencesSchmalkalden OBJECT IDENTIFIER ::= { enterprises 11189 }
vioxServices                      OBJECT IDENTIFIER ::= { enterprises 11190 }
xiam                              OBJECT IDENTIFIER ::= { enterprises 11191 }
xiphorgFoundation                 OBJECT IDENTIFIER ::= { enterprises 11192 }
salica                            OBJECT IDENTIFIER ::= { enterprises 11193 }
wirelessMaingate                  OBJECT IDENTIFIER ::= { enterprises 11194 }
vectorSpZOo                       OBJECT IDENTIFIER ::= { enterprises 11195 }
marcantInternetServices           OBJECT IDENTIFIER ::= { enterprises 11196 }
aLJazeeraSatelliteChannel         OBJECT IDENTIFIER ::= { enterprises 11197 }
atridSystemes                     OBJECT IDENTIFIER ::= { enterprises 11198 }
auspice                           OBJECT IDENTIFIER ::= { enterprises 11199 }
bellsouth                         OBJECT IDENTIFIER ::= { enterprises 11200 }
benefitSystems                    OBJECT IDENTIFIER ::= { enterprises 11201 }
blueSkyStudios                    OBJECT IDENTIFIER ::= { enterprises 11202 }
cybermation                       OBJECT IDENTIFIER ::= { enterprises 11203 }
enterceptSecurityTechnologies     OBJECT IDENTIFIER ::= { enterprises 11204 }
environmentalSystemsResearchInstitute OBJECT IDENTIFIER ::= { enterprises 11205 }
eplsEnterpriseComputingPte        OBJECT IDENTIFIER ::= { enterprises 11206 }
falkESolutionsAG                  OBJECT IDENTIFIER ::= { enterprises 11207 }
globalMediaSystems                OBJECT IDENTIFIER ::= { enterprises 11208 }
goldWireTechnology                OBJECT IDENTIFIER ::= { enterprises 11209 }
iainStevenson                     OBJECT IDENTIFIER ::= { enterprises 11210 }
idetic                            OBJECT IDENTIFIER ::= { enterprises 11211 }
idm                               OBJECT IDENTIFIER ::= { enterprises 11212 }
informationServicesExtended       OBJECT IDENTIFIER ::= { enterprises 11213 }
meridisCorporation                OBJECT IDENTIFIER ::= { enterprises 11214 }
navitaire                         OBJECT IDENTIFIER ::= { enterprises 11215 }
neowareSystems                    OBJECT IDENTIFIER ::= { enterprises 11216 }
oceanetTechnology                 OBJECT IDENTIFIER ::= { enterprises 11217 }
oculanCorp                        OBJECT IDENTIFIER ::= { enterprises 11218 }
opvista                           OBJECT IDENTIFIER ::= { enterprises 11219 }
pirelliCaviESistemiSpA            OBJECT IDENTIFIER ::= { enterprises 11220 }
procon                            OBJECT IDENTIFIER ::= { enterprises 11221 }
rochesterGeneralHospital          OBJECT IDENTIFIER ::= { enterprises 11222 }
rwtTelefonyPolskieSA              OBJECT IDENTIFIER ::= { enterprises 11223 }
saebex                            OBJECT IDENTIFIER ::= { enterprises 11224 }
scmb                              OBJECT IDENTIFIER ::= { enterprises 11225 }
skandinaviskaMagasin1AB           OBJECT IDENTIFIER ::= { enterprises 11226 }
startcorp                         OBJECT IDENTIFIER ::= { enterprises 11227 }
systembaseCo                      OBJECT IDENTIFIER ::= { enterprises 11228 }
systemware                        OBJECT IDENTIFIER ::= { enterprises 11229 }
voiceAccessTechnologies           OBJECT IDENTIFIER ::= { enterprises 11230 }
wincomSystems                     OBJECT IDENTIFIER ::= { enterprises 11231 }
apocalypseComputingServices       OBJECT IDENTIFIER ::= { enterprises 11232 }
haraldGliebe                      OBJECT IDENTIFIER ::= { enterprises 11233 }
hotcircles                        OBJECT IDENTIFIER ::= { enterprises 11234 }
whichmallcom                      OBJECT IDENTIFIER ::= { enterprises 11235 }
mosakinInternationalCorporation   OBJECT IDENTIFIER ::= { enterprises 11236 }
itekSpf                           OBJECT IDENTIFIER ::= { enterprises 11237 }
apsSysteme                        OBJECT IDENTIFIER ::= { enterprises 11238 }
bennett                           OBJECT IDENTIFIER ::= { enterprises 11239 }
caixaD                            OBJECT IDENTIFIER ::= { enterprises 11240 }
carmelSecondarySchool             OBJECT IDENTIFIER ::= { enterprises 11241 }
customElectronics                 OBJECT IDENTIFIER ::= { enterprises 11242 }
dcwg                              OBJECT IDENTIFIER ::= { enterprises 11243 }
netControl                        OBJECT IDENTIFIER ::= { enterprises 11244 }
e2open                            OBJECT IDENTIFIER ::= { enterprises 11245 }
ghz                               OBJECT IDENTIFIER ::= { enterprises 11246 }
glaxosmithkline                   OBJECT IDENTIFIER ::= { enterprises 11247 }
greenwichTechnologyPartners       OBJECT IDENTIFIER ::= { enterprises 11248 }
iDNSnetInternational              OBJECT IDENTIFIER ::= { enterprises 11249 }
indianaPurdueUniversityFtWayne    OBJECT IDENTIFIER ::= { enterprises 11250 }
intrado                           OBJECT IDENTIFIER ::= { enterprises 11251 }
itouchLabs                        OBJECT IDENTIFIER ::= { enterprises 11252 }
jpStephensonCo                    OBJECT IDENTIFIER ::= { enterprises 11253 }
jydskConsulting                   OBJECT IDENTIFIER ::= { enterprises 11254 }
locationetSystemsLTD              OBJECT IDENTIFIER ::= { enterprises 11255 }
netasq                            OBJECT IDENTIFIER ::= { enterprises 11256 }
netES                             OBJECT IDENTIFIER ::= { enterprises 11257 }
noguiAB                           OBJECT IDENTIFIER ::= { enterprises 11258 }
sepulvedaSystems                  OBJECT IDENTIFIER ::= { enterprises 11259 }
singleSourceOy                    OBJECT IDENTIFIER ::= { enterprises 11260 }
tschaecheServices                 OBJECT IDENTIFIER ::= { enterprises 11261 }
wireCardAG                        OBJECT IDENTIFIER ::= { enterprises 11262 }
wrnetworks                        OBJECT IDENTIFIER ::= { enterprises 11263 }
mobileartsAB                      OBJECT IDENTIFIER ::= { enterprises 11264 }
setSoftware                       OBJECT IDENTIFIER ::= { enterprises 11265 }
jiangsuFujitsuTelecommunicationsTechnologyCO OBJECT IDENTIFIER ::= { enterprises 11266 }
disscPresidenciaDelGobierno       OBJECT IDENTIFIER ::= { enterprises 11267 }
aastra                            OBJECT IDENTIFIER ::= { enterprises 11268 }
aculabPLC                         OBJECT IDENTIFIER ::= { enterprises 11269 }
adelphiaBusinessSolutions         OBJECT IDENTIFIER ::= { enterprises 11270 }
ariaTechnologyPte                 OBJECT IDENTIFIER ::= { enterprises 11271 }
birdstepTechnology                OBJECT IDENTIFIER ::= { enterprises 11272 }
bjbSoftware                       OBJECT IDENTIFIER ::= { enterprises 11273 }
centricTelecom                    OBJECT IDENTIFIER ::= { enterprises 11274 }
changingworlds                    OBJECT IDENTIFIER ::= { enterprises 11275 }
commil                            OBJECT IDENTIFIER ::= { enterprises 11276 }
convergenceIntegratedMediaGmbh    OBJECT IDENTIFIER ::= { enterprises 11277 }
csEngineeringBv                   OBJECT IDENTIFIER ::= { enterprises 11278 }
datalabTechnologiaSA              OBJECT IDENTIFIER ::= { enterprises 11279 }
digimob                           OBJECT IDENTIFIER ::= { enterprises 11280 }
digitalBus                        OBJECT IDENTIFIER ::= { enterprises 11281 }
dksin                             OBJECT IDENTIFIER ::= { enterprises 11282 }
dobsonicsLaboratories             OBJECT IDENTIFIER ::= { enterprises 11283 }
eswEXTELSYSTEMSWEDEL              OBJECT IDENTIFIER ::= { enterprises 11284 }
flipdogcom                        OBJECT IDENTIFIER ::= { enterprises 11285 }
h1                                OBJECT IDENTIFIER ::= { enterprises 11286 }
highAvailabilitycom               OBJECT IDENTIFIER ::= { enterprises 11287 }
icreateSoftware                   OBJECT IDENTIFIER ::= { enterprises 11288 }
imagineLAN                        OBJECT IDENTIFIER ::= { enterprises 11289 }
informationServicesPlc            OBJECT IDENTIFIER ::= { enterprises 11290 }
ionaTechnologies                  OBJECT IDENTIFIER ::= { enterprises 11291 }
laFactor                          OBJECT IDENTIFIER ::= { enterprises 11292 }
locanet                           OBJECT IDENTIFIER ::= { enterprises 11293 }
mobinorAS                         OBJECT IDENTIFIER ::= { enterprises 11294 }
cybercity                         OBJECT IDENTIFIER ::= { enterprises 11295 }
neonSoftware                      OBJECT IDENTIFIER ::= { enterprises 11296 }
netnet                            OBJECT IDENTIFIER ::= { enterprises 11297 }
nlwebcom                          OBJECT IDENTIFIER ::= { enterprises 11298 }
onTimeSystems                     OBJECT IDENTIFIER ::= { enterprises 11299 }
passagewaysTravel                 OBJECT IDENTIFIER ::= { enterprises 11300 }
pearsonEducation                  OBJECT IDENTIFIER ::= { enterprises 11301 }
perimeterTechnology               OBJECT IDENTIFIER ::= { enterprises 11302 }
photonixnetCorporation            OBJECT IDENTIFIER ::= { enterprises 11303 }
printeronCorporation              OBJECT IDENTIFIER ::= { enterprises 11304 }
researchInstituteForParticleAndNuclearPhysics OBJECT IDENTIFIER ::= { enterprises 11305 }
robartsResearchInstitute          OBJECT IDENTIFIER ::= { enterprises 11306 }
solarwindsnet                     OBJECT IDENTIFIER ::= { enterprises 11307 }
swapcom                           OBJECT IDENTIFIER ::= { enterprises 11308 }
tallgrassCommunications           OBJECT IDENTIFIER ::= { enterprises 11309 }
techniqueConsultantsPty           OBJECT IDENTIFIER ::= { enterprises 11310 }
tubitakUEKAE                      OBJECT IDENTIFIER ::= { enterprises 11311 }
universit3                        OBJECT IDENTIFIER ::= { enterprises 11312 }
universityOfCalgary               OBJECT IDENTIFIER ::= { enterprises 11313 }
universityOfKansas                OBJECT IDENTIFIER ::= { enterprises 11314 }
usaconnect                        OBJECT IDENTIFIER ::= { enterprises 11315 }
wareSolutions                     OBJECT IDENTIFIER ::= { enterprises 11316 }
wielandElectric                   OBJECT IDENTIFIER ::= { enterprises 11317 }
xeroxResearch                     OBJECT IDENTIFIER ::= { enterprises 11318 }
alcatel                           OBJECT IDENTIFIER ::= { enterprises 11319 }
communalCC                        OBJECT IDENTIFIER ::= { enterprises 11320 }
eciIP2                            OBJECT IDENTIFIER ::= { enterprises 11321 }
integratedSupportSystems          OBJECT IDENTIFIER ::= { enterprises 11322 }
manpower                          OBJECT IDENTIFIER ::= { enterprises 11323 }
netsolsde                         OBJECT IDENTIFIER ::= { enterprises 11324 }
opendesign                        OBJECT IDENTIFIER ::= { enterprises 11325 }
blueScooter                       OBJECT IDENTIFIER ::= { enterprises 11326 }
xi                                OBJECT IDENTIFIER ::= { enterprises 11327 }
rana                              OBJECT IDENTIFIER ::= { enterprises 11328 }
llnlNIF                           OBJECT IDENTIFIER ::= { enterprises 11329 }
inpronetworkCorporation           OBJECT IDENTIFIER ::= { enterprises 11330 }
betasoft                          OBJECT IDENTIFIER ::= { enterprises 11331 }
broadstormTelecommunications      OBJECT IDENTIFIER ::= { enterprises 11332 }
mediaDataSystemsPte               OBJECT IDENTIFIER ::= { enterprises 11333 }
olesPolymediaAG                   OBJECT IDENTIFIER ::= { enterprises 11334 }
quris                             OBJECT IDENTIFIER ::= { enterprises 11335 }
rSquaredTechnologies              OBJECT IDENTIFIER ::= { enterprises 11336 }
softwareWorkhouseOfHiteLee        OBJECT IDENTIFIER ::= { enterprises 11337 }
successInformationSystemCo        OBJECT IDENTIFIER ::= { enterprises 11338 }
danamCommunications               OBJECT IDENTIFIER ::= { enterprises 11339 }
dregisDresdnerGlobalITServicesGesellschaftMbH OBJECT IDENTIFIER ::= { enterprises 11340 }
nowalls                           OBJECT IDENTIFIER ::= { enterprises 11341 }
teliaMobileFinland                OBJECT IDENTIFIER ::= { enterprises 11342 }
terra                             OBJECT IDENTIFIER ::= { enterprises 11343 }
theFreeRADIUSServerProject        OBJECT IDENTIFIER ::= { enterprises 11344 }
provinzialVersicherung            OBJECT IDENTIFIER ::= { enterprises 11346 }
academConsultingServices          OBJECT IDENTIFIER ::= { enterprises 11347 }
airbus                            OBJECT IDENTIFIER ::= { enterprises 11348 }
atReteAg                          OBJECT IDENTIFIER ::= { enterprises 11349 }
bondcarcom                        OBJECT IDENTIFIER ::= { enterprises 11350 }
bouwens                           OBJECT IDENTIFIER ::= { enterprises 11351 }
cognigenCorporation               OBJECT IDENTIFIER ::= { enterprises 11352 }
dasBueroAmDraht                   OBJECT IDENTIFIER ::= { enterprises 11353 }
dataDesignSystems                 OBJECT IDENTIFIER ::= { enterprises 11354 }
datavault                         OBJECT IDENTIFIER ::= { enterprises 11355 }
dtvTechnicalKnowledgeCenterOfDenmark OBJECT IDENTIFIER ::= { enterprises 11356 }
edealSchroederMaihoeferGbR        OBJECT IDENTIFIER ::= { enterprises 11357 }
elcommtechCorp                    OBJECT IDENTIFIER ::= { enterprises 11358 }
eml                               OBJECT IDENTIFIER ::= { enterprises 11359 }
excenon                           OBJECT IDENTIFIER ::= { enterprises 11360 }
fasterCZ                          OBJECT IDENTIFIER ::= { enterprises 11361 }
fcsPartners                       OBJECT IDENTIFIER ::= { enterprises 11362 }
federationOfNorwegianAgriculturalCooperatives OBJECT IDENTIFIER ::= { enterprises 11363 }
gaeasoftCorp                      OBJECT IDENTIFIER ::= { enterprises 11364 }
orangeSlovakia                    OBJECT IDENTIFIER ::= { enterprises 11365 }
goannaGraphics                    OBJECT IDENTIFIER ::= { enterprises 11366 }
helix                             OBJECT IDENTIFIER ::= { enterprises 11367 }
iavista                           OBJECT IDENTIFIER ::= { enterprises 11368 }
iomega                            OBJECT IDENTIFIER ::= { enterprises 11369 }
ittCO                             OBJECT IDENTIFIER ::= { enterprises 11370 }
jungMyungTelecomCo                OBJECT IDENTIFIER ::= { enterprises 11371 }
meretOpticalCommunications        OBJECT IDENTIFIER ::= { enterprises 11372 }
netvisionSpZOo                    OBJECT IDENTIFIER ::= { enterprises 11373 }
okoBankGroup                      OBJECT IDENTIFIER ::= { enterprises 11374 }
pacificGeoscienceCenter           OBJECT IDENTIFIER ::= { enterprises 11375 }
pedestalSoftware                  OBJECT IDENTIFIER ::= { enterprises 11376 }
productTechnologyPartners         OBJECT IDENTIFIER ::= { enterprises 11377 }
quartzElectronics                 OBJECT IDENTIFIER ::= { enterprises 11378 }
radiantRt                         OBJECT IDENTIFIER ::= { enterprises 11379 }
retek                             OBJECT IDENTIFIER ::= { enterprises 11380 }
rogersSharedServices              OBJECT IDENTIFIER ::= { enterprises 11381 }
rrEnterprises                     OBJECT IDENTIFIER ::= { enterprises 11382 }
saudinet                          OBJECT IDENTIFIER ::= { enterprises 11383 }
sevenlayerServices                OBJECT IDENTIFIER ::= { enterprises 11384 }
spanlinkCommunications            OBJECT IDENTIFIER ::= { enterprises 11385 }
studer                            OBJECT IDENTIFIER ::= { enterprises 11386 }
t4ConsultingGroup                 OBJECT IDENTIFIER ::= { enterprises 11387 }
tarantolaLabs                     OBJECT IDENTIFIER ::= { enterprises 11388 }
tecfa                             OBJECT IDENTIFIER ::= { enterprises 11389 }
texasDepartmentOfHousingAndCommunityAffairs OBJECT IDENTIFIER ::= { enterprises 11390 }
theTexasGigaPOP                   OBJECT IDENTIFIER ::= { enterprises 11391 }
tools4everBv                      OBJECT IDENTIFIER ::= { enterprises 11392 }
tymlabsManagement                 OBJECT IDENTIFIER ::= { enterprises 11393 }
udTechnology                      OBJECT IDENTIFIER ::= { enterprises 11394 }
vancouverPublicLibrary            OBJECT IDENTIFIER ::= { enterprises 11395 }
webexChina                        OBJECT IDENTIFIER ::= { enterprises 11396 }
xpedioAB                          OBJECT IDENTIFIER ::= { enterprises 11397 }
pyxEngineeringAG                  OBJECT IDENTIFIER ::= { enterprises 11398 }
washingtonStateUniversityVancouver OBJECT IDENTIFIER ::= { enterprises 11399 }
deptOfInformationAndCommunicationsTechnology OBJECT IDENTIFIER ::= { enterprises 11400 }
concatel                          OBJECT IDENTIFIER ::= { enterprises 11401 }
mroSoftware                       OBJECT IDENTIFIER ::= { enterprises 11402 }
openreach                         OBJECT IDENTIFIER ::= { enterprises 11403 }
seanetCorporation                 OBJECT IDENTIFIER ::= { enterprises 11404 }
shanghaionline                    OBJECT IDENTIFIER ::= { enterprises 11405 }
sandyGroup                        OBJECT IDENTIFIER ::= { enterprises 11406 }
obsceneskillscom                  OBJECT IDENTIFIER ::= { enterprises 11407 }
wuhanFiberHomeNetworksCo          OBJECT IDENTIFIER ::= { enterprises 11408 }
adequateSystems                   OBJECT IDENTIFIER ::= { enterprises 11409 }
advancedCommunicationDevicesCorp  OBJECT IDENTIFIER ::= { enterprises 11410 }
aolAustralia                      OBJECT IDENTIFIER ::= { enterprises 11411 }
bktelCommunication                OBJECT IDENTIFIER ::= { enterprises 11412 }
capeClearSoftware                 OBJECT IDENTIFIER ::= { enterprises 11413 }
carnationTechnology               OBJECT IDENTIFIER ::= { enterprises 11414 }
clcsoft                           OBJECT IDENTIFIER ::= { enterprises 11415 }
coalsere                          OBJECT IDENTIFIER ::= { enterprises 11416 }
cynops                            OBJECT IDENTIFIER ::= { enterprises 11417 }
dfnCERT                           OBJECT IDENTIFIER ::= { enterprises 11418 }
fotelCorp                         OBJECT IDENTIFIER ::= { enterprises 11419 }
ghsDataManagement                 OBJECT IDENTIFIER ::= { enterprises 11420 }
industrialNetworkingSolution      OBJECT IDENTIFIER ::= { enterprises 11421 }
larmouthTAndPDS                   OBJECT IDENTIFIER ::= { enterprises 11422 }
lucidVision                       OBJECT IDENTIFIER ::= { enterprises 11423 }
mitsubishiGASCHEMICALCOMPANY      OBJECT IDENTIFIER ::= { enterprises 11424 }
mobilewebsurf                     OBJECT IDENTIFIER ::= { enterprises 11425 }
netfusionsSrl                     OBJECT IDENTIFIER ::= { enterprises 11426 }
particlePhysicsGroup              OBJECT IDENTIFIER ::= { enterprises 11427 }
redesDeComputadoras               OBJECT IDENTIFIER ::= { enterprises 11428 }
schumacher                        OBJECT IDENTIFIER ::= { enterprises 11429 }
simtekCorporation                 OBJECT IDENTIFIER ::= { enterprises 11430 }
southernPolytechnicStateUniversity OBJECT IDENTIFIER ::= { enterprises 11431 }
towerGroupNetwork                 OBJECT IDENTIFIER ::= { enterprises 11432 }
universityOfWestBohemia           OBJECT IDENTIFIER ::= { enterprises 11433 }
utahScientific                    OBJECT IDENTIFIER ::= { enterprises 11434 }
webexCommunications               OBJECT IDENTIFIER ::= { enterprises 11435 }
xmlGlobalTechnologies             OBJECT IDENTIFIER ::= { enterprises 11436 }
xymbol                            OBJECT IDENTIFIER ::= { enterprises 11437 }
canadianCenterForRemoteSensing    OBJECT IDENTIFIER ::= { enterprises 11438 }
cclrc                             OBJECT IDENTIFIER ::= { enterprises 11439 }
sapros                            OBJECT IDENTIFIER ::= { enterprises 11440 }
goshenCollege                     OBJECT IDENTIFIER ::= { enterprises 11441 }
insertads                         OBJECT IDENTIFIER ::= { enterprises 11442 }
morderDevices                     OBJECT IDENTIFIER ::= { enterprises 11443 }
frederickEngineering              OBJECT IDENTIFIER ::= { enterprises 11444 }
anoregBR                          OBJECT IDENTIFIER ::= { enterprises 11445 }
adduceNetworks                    OBJECT IDENTIFIER ::= { enterprises 11446 }
xilogic                           OBJECT IDENTIFIER ::= { enterprises 11447 }
itologyCo                         OBJECT IDENTIFIER ::= { enterprises 11448 }
tethernet                         OBJECT IDENTIFIER ::= { enterprises 11449 }
xitecde                           OBJECT IDENTIFIER ::= { enterprises 11450 }
sinbonELECTRONICCO                OBJECT IDENTIFIER ::= { enterprises 11451 }
allegientSystems                  OBJECT IDENTIFIER ::= { enterprises 11452 }
altadis                           OBJECT IDENTIFIER ::= { enterprises 11453 }
avenciSA                          OBJECT IDENTIFIER ::= { enterprises 11454 }
aviationManagementTechnologies    OBJECT IDENTIFIER ::= { enterprises 11455 }
calvaediSA                        OBJECT IDENTIFIER ::= { enterprises 11456 }
cimcor                            OBJECT IDENTIFIER ::= { enterprises 11457 }
computingServicesDepartment       OBJECT IDENTIFIER ::= { enterprises 11458 }
dataTrackTechnologyPLC            OBJECT IDENTIFIER ::= { enterprises 11459 }
datafront                         OBJECT IDENTIFIER ::= { enterprises 11460 }
deloitteAndTouche                 OBJECT IDENTIFIER ::= { enterprises 11461 }
dronedap                          OBJECT IDENTIFIER ::= { enterprises 11462 }
ecFounder                         OBJECT IDENTIFIER ::= { enterprises 11463 }
electronicArts                    OBJECT IDENTIFIER ::= { enterprises 11464 }
envoyTechnologies                 OBJECT IDENTIFIER ::= { enterprises 11465 }
ePollinationEnterprise            OBJECT IDENTIFIER ::= { enterprises 11466 }
intermediasp                      OBJECT IDENTIFIER ::= { enterprises 11467 }
jacksonCountySchoolDistrict6      OBJECT IDENTIFIER ::= { enterprises 11468 }
kokong                            OBJECT IDENTIFIER ::= { enterprises 11469 }
lxNetworking                      OBJECT IDENTIFIER ::= { enterprises 11470 }
mineitSoftware                    OBJECT IDENTIFIER ::= { enterprises 11471 }
moetiCorp                         OBJECT IDENTIFIER ::= { enterprises 11472 }
nordicMessagingTechnologiesAB     OBJECT IDENTIFIER ::= { enterprises 11473 }
nttDATACOPORATION                 OBJECT IDENTIFIER ::= { enterprises 11474 }
proActive                         OBJECT IDENTIFIER ::= { enterprises 11475 }
questControls                     OBJECT IDENTIFIER ::= { enterprises 11476 }
rasviaSystems                     OBJECT IDENTIFIER ::= { enterprises 11477 }
scorpionControls                  OBJECT IDENTIFIER ::= { enterprises 11478 }
selso                             OBJECT IDENTIFIER ::= { enterprises 11479 }
sunnyindCorp                      OBJECT IDENTIFIER ::= { enterprises 11480 }
teimaAudiotex                     OBJECT IDENTIFIER ::= { enterprises 11481 }
universalTrafficManagementSocietyOfJapan OBJECT IDENTIFIER ::= { enterprises 11482 }
universityOfIllinoisAtUrbanaChampaign OBJECT IDENTIFIER ::= { enterprises 11483 }
viastoreSystems                   OBJECT IDENTIFIER ::= { enterprises 11484 }
vidaNetworkTechnologies           OBJECT IDENTIFIER ::= { enterprises 11485 }
vizzaviNL                         OBJECT IDENTIFIER ::= { enterprises 11486 }
voxsurf                           OBJECT IDENTIFIER ::= { enterprises 11487 }
abComputers                       OBJECT IDENTIFIER ::= { enterprises 11488 }
alacritus                         OBJECT IDENTIFIER ::= { enterprises 11489 }
betweenmarkets                    OBJECT IDENTIFIER ::= { enterprises 11490 }
jyvaskylaUniversity               OBJECT IDENTIFIER ::= { enterprises 11491 }
microResearchLaboratory           OBJECT IDENTIFIER ::= { enterprises 11492 }
obourgOrignyInformatique          OBJECT IDENTIFIER ::= { enterprises 11493 }
nebulonPty                        OBJECT IDENTIFIER ::= { enterprises 11494 }
cubicch                           OBJECT IDENTIFIER ::= { enterprises 11495 }
foocz                             OBJECT IDENTIFIER ::= { enterprises 11496 }
gamerznetEnterprises              OBJECT IDENTIFIER ::= { enterprises 11497 }
hccnetBV                          OBJECT IDENTIFIER ::= { enterprises 11498 }
hollmannConsultingServices        OBJECT IDENTIFIER ::= { enterprises 11499 }
infrantTechnology                 OBJECT IDENTIFIER ::= { enterprises 11500 }
ingmarnet                         OBJECT IDENTIFIER ::= { enterprises 11501 }
ituTASN1Project                   OBJECT IDENTIFIER ::= { enterprises 11502 }
metraware                         OBJECT IDENTIFIER ::= { enterprises 11503 }
ndsl                              OBJECT IDENTIFIER ::= { enterprises 11504 }
network1SecuritySolutions         OBJECT IDENTIFIER ::= { enterprises 11505 }
probusiness                       OBJECT IDENTIFIER ::= { enterprises 11507 }
schoolOfBankingAndManagementInCracow OBJECT IDENTIFIER ::= { enterprises 11508 }
schweizerElectronicAG             OBJECT IDENTIFIER ::= { enterprises 11509 }
serviceIntelligence               OBJECT IDENTIFIER ::= { enterprises 11510 }
southernIllinoisUniversitySchoolOfMedicine OBJECT IDENTIFIER ::= { enterprises 11511 }
stJoseph                          OBJECT IDENTIFIER ::= { enterprises 11512 }
streleInformatik                  OBJECT IDENTIFIER ::= { enterprises 11513 }
studentAdvantage                  OBJECT IDENTIFIER ::= { enterprises 11514 }
sub1SA                            OBJECT IDENTIFIER ::= { enterprises 11515 }
theAcademyOfSciencesOfTheCzechRepublic OBJECT IDENTIFIER ::= { enterprises 11516 }
trivadisAG                        OBJECT IDENTIFIER ::= { enterprises 11517 }
tSoft                             OBJECT IDENTIFIER ::= { enterprises 11518 }
vet                               OBJECT IDENTIFIER ::= { enterprises 11519 }
visilinx                          OBJECT IDENTIFIER ::= { enterprises 11520 }
broadcastMusic                    OBJECT IDENTIFIER ::= { enterprises 11521 }
linxtek                           OBJECT IDENTIFIER ::= { enterprises 11522 }
fujitsuLaboratoriesOfAmerica      OBJECT IDENTIFIER ::= { enterprises 11523 }
ch5FinlandOy                      OBJECT IDENTIFIER ::= { enterprises 11524 }
brain-OnAG                        OBJECT IDENTIFIER ::= { enterprises 11525 }
giroLTD                           OBJECT IDENTIFIER ::= { enterprises 11526 }
bromaxCommunications              OBJECT IDENTIFIER ::= { enterprises 11527 }
dvbernAG                          OBJECT IDENTIFIER ::= { enterprises 11528 }
kogaELECTRONICSCO                 OBJECT IDENTIFIER ::= { enterprises 11529 }
threeGNetWorks                    OBJECT IDENTIFIER ::= { enterprises 11530 }
ahaSystems                        OBJECT IDENTIFIER ::= { enterprises 11531 }
bondUniversity                    OBJECT IDENTIFIER ::= { enterprises 11532 }
chibaIndustries                   OBJECT IDENTIFIER ::= { enterprises 11533 }
coaxmedia                         OBJECT IDENTIFIER ::= { enterprises 11534 }
cogitis                           OBJECT IDENTIFIER ::= { enterprises 11535 }
cyberArk                          OBJECT IDENTIFIER ::= { enterprises 11536 }
direcci                           OBJECT IDENTIFIER ::= { enterprises 11537 }
elata                             OBJECT IDENTIFIER ::= { enterprises 11538 }
essentKabelcom                    OBJECT IDENTIFIER ::= { enterprises 11539 }
etit                              OBJECT IDENTIFIER ::= { enterprises 11540 }
fuguAngstProductions              OBJECT IDENTIFIER ::= { enterprises 11541 }
guangzhouGaoKeCommunicationEquipmentCo OBJECT IDENTIFIER ::= { enterprises 11542 }
internetNorthwest                 OBJECT IDENTIFIER ::= { enterprises 11543 }
kunsthochschuleFuerMedien         OBJECT IDENTIFIER ::= { enterprises 11544 }
kurtevIntergalactic               OBJECT IDENTIFIER ::= { enterprises 11545 }
metraware2                        OBJECT IDENTIFIER ::= { enterprises 11546 }
mpowerCommunicationsCorporation   OBJECT IDENTIFIER ::= { enterprises 11547 }
nabla2Srl                         OBJECT IDENTIFIER ::= { enterprises 11548 }
netousTECHNOLOGIES                OBJECT IDENTIFIER ::= { enterprises 11549 }
netpiaSYSTEMSCo                   OBJECT IDENTIFIER ::= { enterprises 11550 }
orcaOrcinus                       OBJECT IDENTIFIER ::= { enterprises 11551 }
page87                            OBJECT IDENTIFIER ::= { enterprises 11552 }
planetTechnologiesNV              OBJECT IDENTIFIER ::= { enterprises 11553 }
pomcor                            OBJECT IDENTIFIER ::= { enterprises 11554 }
riderUniversity                   OBJECT IDENTIFIER ::= { enterprises 11555 }
robertBurrellDonkin               OBJECT IDENTIFIER ::= { enterprises 11556 }
sAndci                            OBJECT IDENTIFIER ::= { enterprises 11557 }
sofice                            OBJECT IDENTIFIER ::= { enterprises 11558 }
softgameInternationalPty          OBJECT IDENTIFIER ::= { enterprises 11559 }
tantiaTechnologies                OBJECT IDENTIFIER ::= { enterprises 11560 }
topconPositioningSystems          OBJECT IDENTIFIER ::= { enterprises 11561 }
ve2ug                             OBJECT IDENTIFIER ::= { enterprises 11562 }
ahnlab                            OBJECT IDENTIFIER ::= { enterprises 11563 }
citeitwrite                       OBJECT IDENTIFIER ::= { enterprises 11564 }
institutoNacionalDeEstat          OBJECT IDENTIFIER ::= { enterprises 11565 }
prologueSoftware                  OBJECT IDENTIFIER ::= { enterprises 11566 }
deltaloydDeutschland              OBJECT IDENTIFIER ::= { enterprises 11567 }
bmbwk                             OBJECT IDENTIFIER ::= { enterprises 11568 }
handydeVertriebs                  OBJECT IDENTIFIER ::= { enterprises 11569 }
magesTouch                        OBJECT IDENTIFIER ::= { enterprises 11570 }
ntiStudio                         OBJECT IDENTIFIER ::= { enterprises 11571 }
rasviaSystems2                    OBJECT IDENTIFIER ::= { enterprises 11572 }
rockusat                          OBJECT IDENTIFIER ::= { enterprises 11573 }
sevenWinds                        OBJECT IDENTIFIER ::= { enterprises 11574 }
solutionDesignLaboratory          OBJECT IDENTIFIER ::= { enterprises 11575 }
sunnycal                          OBJECT IDENTIFIER ::= { enterprises 11576 }
globalSystemServices              OBJECT IDENTIFIER ::= { enterprises 11577 }
airzip                            OBJECT IDENTIFIER ::= { enterprises 11578 }
amadeusDataProcessing             OBJECT IDENTIFIER ::= { enterprises 11579 }
amdocs                            OBJECT IDENTIFIER ::= { enterprises 11580 }
bylinuxnet                        OBJECT IDENTIFIER ::= { enterprises 11581 }
cAndiTechnologies                 OBJECT IDENTIFIER ::= { enterprises 11582 }
cayenta                           OBJECT IDENTIFIER ::= { enterprises 11583 }
classAG                           OBJECT IDENTIFIER ::= { enterprises 11584 }
coloradobiznet                    OBJECT IDENTIFIER ::= { enterprises 11585 }
dlrEV                             OBJECT IDENTIFIER ::= { enterprises 11586 }
epictetAG                         OBJECT IDENTIFIER ::= { enterprises 11587 }
eraAs                             OBJECT IDENTIFIER ::= { enterprises 11588 }
exsiorDataAndInformationTech      OBJECT IDENTIFIER ::= { enterprises 11589 }
fortech                           OBJECT IDENTIFIER ::= { enterprises 11590 }
freeSoftwareFoundation            OBJECT IDENTIFIER ::= { enterprises 11591 }
hangzhousunyardINFORMATIONENGINEERINGCO OBJECT IDENTIFIER ::= { enterprises 11592 }
imise                             OBJECT IDENTIFIER ::= { enterprises 11593 }
ldcomNetworks                     OBJECT IDENTIFIER ::= { enterprises 11594 }
lightmazeAG                       OBJECT IDENTIFIER ::= { enterprises 11595 }
mediakabel                        OBJECT IDENTIFIER ::= { enterprises 11596 }
mfbMultaSpolSRo                   OBJECT IDENTIFIER ::= { enterprises 11597 }
mgicMortgageGuarantyInsuranceCorp OBJECT IDENTIFIER ::= { enterprises 11598 }
mille21                           OBJECT IDENTIFIER ::= { enterprises 11599 }
neogration                        OBJECT IDENTIFIER ::= { enterprises 11600 }
netaxsInternetServices            OBJECT IDENTIFIER ::= { enterprises 11601 }
newYorkStateOfficeOfTheStateComptroller OBJECT IDENTIFIER ::= { enterprises 11602 }
nexxientCommunications            OBJECT IDENTIFIER ::= { enterprises 11603 }
nordugrid                         OBJECT IDENTIFIER ::= { enterprises 11604 }
opticalWirelessLink               OBJECT IDENTIFIER ::= { enterprises 11605 }
pacificBroadbankNetworks          OBJECT IDENTIFIER ::= { enterprises 11606 }
plumtreeSoftware                  OBJECT IDENTIFIER ::= { enterprises 11607 }
pracomPty                         OBJECT IDENTIFIER ::= { enterprises 11608 }
pusanweb                          OBJECT IDENTIFIER ::= { enterprises 11609 }
sandvine                          OBJECT IDENTIFIER ::= { enterprises 11610 }
secretariaDaFazendaDoEstadoDeSp   OBJECT IDENTIFIER ::= { enterprises 11611 }
sttSrl                            OBJECT IDENTIFIER ::= { enterprises 11612 }
vortex                            OBJECT IDENTIFIER ::= { enterprises 11613 }
vrwg                              OBJECT IDENTIFIER ::= { enterprises 11614 }
webaronetTechnology               OBJECT IDENTIFIER ::= { enterprises 11615 }
webperformGroup                   OBJECT IDENTIFIER ::= { enterprises 11616 }
cablevisionSystemsHoldings        OBJECT IDENTIFIER ::= { enterprises 11617 }
soltechCO                         OBJECT IDENTIFIER ::= { enterprises 11618 }
ptcSolutions                      OBJECT IDENTIFIER ::= { enterprises 11619 }
paceAntiPiracy                    OBJECT IDENTIFIER ::= { enterprises 11620 }
agrotecnicaArpaScrl               OBJECT IDENTIFIER ::= { enterprises 11621 }
threePARData                      OBJECT IDENTIFIER ::= { enterprises 11622 }
aegisSoftware                     OBJECT IDENTIFIER ::= { enterprises 11623 }
bitLabPTYLTD                      OBJECT IDENTIFIER ::= { enterprises 11624 }
blackBearSoftware                 OBJECT IDENTIFIER ::= { enterprises 11625 }
combol                            OBJECT IDENTIFIER ::= { enterprises 11626 }
davidPitts                        OBJECT IDENTIFIER ::= { enterprises 11627 }
ediportTelecommunication          OBJECT IDENTIFIER ::= { enterprises 11628 }
educationalServiceUnitnum2        OBJECT IDENTIFIER ::= { enterprises 11629 }
eircomnet                         OBJECT IDENTIFIER ::= { enterprises 11630 }
enablingtrustLLC                  OBJECT IDENTIFIER ::= { enterprises 11631 }
eSecTecnologiaEmSegurancaDeDadosLTDA OBJECT IDENTIFIER ::= { enterprises 11632 }
europopAG                         OBJECT IDENTIFIER ::= { enterprises 11633 }
exempla                           OBJECT IDENTIFIER ::= { enterprises 11634 }
fioranoSoftware                   OBJECT IDENTIFIER ::= { enterprises 11635 }
focalPointSoftware                OBJECT IDENTIFIER ::= { enterprises 11636 }
generatio                         OBJECT IDENTIFIER ::= { enterprises 11637 }
grapesNetworkServices             OBJECT IDENTIFIER ::= { enterprises 11638 }
intersysUruguay                   OBJECT IDENTIFIER ::= { enterprises 11639 }
miritek                           OBJECT IDENTIFIER ::= { enterprises 11640 }
netova                            OBJECT IDENTIFIER ::= { enterprises 11641 }
nextraEnsure                      OBJECT IDENTIFIER ::= { enterprises 11642 }
oneStopConsulting                 OBJECT IDENTIFIER ::= { enterprises 11643 }
orbismConsulting                  OBJECT IDENTIFIER ::= { enterprises 11644 }
pentalogInet                      OBJECT IDENTIFIER ::= { enterprises 11645 }
pentamediaCo                      OBJECT IDENTIFIER ::= { enterprises 11646 }
planetasia                        OBJECT IDENTIFIER ::= { enterprises 11647 }
remotesiteTechnologies            OBJECT IDENTIFIER ::= { enterprises 11648 }
rossStores                        OBJECT IDENTIFIER ::= { enterprises 11649 }
schnedermannSoftwareConsulting    OBJECT IDENTIFIER ::= { enterprises 11650 }
sidespace                         OBJECT IDENTIFIER ::= { enterprises 11651 }
sonomaStateUniversity             OBJECT IDENTIFIER ::= { enterprises 11652 }
stackComputerSolutions            OBJECT IDENTIFIER ::= { enterprises 11653 }
strottNetworkSolutions            OBJECT IDENTIFIER ::= { enterprises 11654 }
syoSrl                            OBJECT IDENTIFIER ::= { enterprises 11655 }
synapseSystemsAB                  OBJECT IDENTIFIER ::= { enterprises 11656 }
taiwanTelecommunicationNetworkServicesCo OBJECT IDENTIFIER ::= { enterprises 11657 }
universiteBlaisePASCAL            OBJECT IDENTIFIER ::= { enterprises 11658 }
virtualSecurityResearch           OBJECT IDENTIFIER ::= { enterprises 11659 }
vmsLimited                        OBJECT IDENTIFIER ::= { enterprises 11660 }
wahooInternationalEnterpriseCo    OBJECT IDENTIFIER ::= { enterprises 11661 }
marcelRuff                        OBJECT IDENTIFIER ::= { enterprises 11662 }
xAlta                             OBJECT IDENTIFIER ::= { enterprises 11663 }
base2                             OBJECT IDENTIFIER ::= { enterprises 11664 }
dacom                             OBJECT IDENTIFIER ::= { enterprises 11665 }
instituteOfCommunicationsEngineeringUniversityOfHanover OBJECT IDENTIFIER ::= { enterprises 11666 }
newYorkStateEducationDepartment   OBJECT IDENTIFIER ::= { enterprises 11667 }
wrlucas                           OBJECT IDENTIFIER ::= { enterprises 11668 }
milhouseTechnologiesUSA           OBJECT IDENTIFIER ::= { enterprises 11669 }
chinaSanjiangSpaceGroup           OBJECT IDENTIFIER ::= { enterprises 11770 }
broadStreet                       OBJECT IDENTIFIER ::= { enterprises 11771 }
adrockSoftware                    OBJECT IDENTIFIER ::= { enterprises 11772 }
agmodel                           OBJECT IDENTIFIER ::= { enterprises 11773 }
asykSA                            OBJECT IDENTIFIER ::= { enterprises 11774 }
atchik                            OBJECT IDENTIFIER ::= { enterprises 11775 }
avibitDataProcessing              OBJECT IDENTIFIER ::= { enterprises 11776 }
aymanLLC                          OBJECT IDENTIFIER ::= { enterprises 11777 }
bluebridgeTechnologiesAG          OBJECT IDENTIFIER ::= { enterprises 11778 }
casedevActiveOy                   OBJECT IDENTIFIER ::= { enterprises 11779 }
cbim                              OBJECT IDENTIFIER ::= { enterprises 11780 }
celtro                            OBJECT IDENTIFIER ::= { enterprises 11781 }
charlesIndustries                 OBJECT IDENTIFIER ::= { enterprises 11782 }
choriJOHOSYSTEMCoLTD              OBJECT IDENTIFIER ::= { enterprises 11783 }
credantTechnologies               OBJECT IDENTIFIER ::= { enterprises 11784 }
criticalIntegration               OBJECT IDENTIFIER ::= { enterprises 11785 }
daisySoftware                     OBJECT IDENTIFIER ::= { enterprises 11786 }
datagateDoo                       OBJECT IDENTIFIER ::= { enterprises 11787 }
fluxxcomECommerce                 OBJECT IDENTIFIER ::= { enterprises 11788 }
forescoutTechnologies             OBJECT IDENTIFIER ::= { enterprises 11789 }
gatewayCommunityCollege           OBJECT IDENTIFIER ::= { enterprises 11790 }
gieseckeAndDevrient               OBJECT IDENTIFIER ::= { enterprises 11791 }
grantCountyPUD                    OBJECT IDENTIFIER ::= { enterprises 11792 }
ibmSlovakia                       OBJECT IDENTIFIER ::= { enterprises 11793 }
incentiveTechnologies             OBJECT IDENTIFIER ::= { enterprises 11794 }
infoglobe                         OBJECT IDENTIFIER ::= { enterprises 11795 }
innovidata                        OBJECT IDENTIFIER ::= { enterprises 11796 }
kaboomEnterprises                 OBJECT IDENTIFIER ::= { enterprises 11797 }
lateralSandsPty                   OBJECT IDENTIFIER ::= { enterprises 11798 }
latisNetworks                     OBJECT IDENTIFIER ::= { enterprises 11799 }
logosoft                          OBJECT IDENTIFIER ::= { enterprises 11800 }
mpsv                              OBJECT IDENTIFIER ::= { enterprises 11801 }
northwestAirlines                 OBJECT IDENTIFIER ::= { enterprises 11802 }
ohloneCommunityCollege            OBJECT IDENTIFIER ::= { enterprises 11803 }
pcs                               OBJECT IDENTIFIER ::= { enterprises 11804 }
plexus                            OBJECT IDENTIFIER ::= { enterprises 11805 }
antonvenetaABNAMROBank            OBJECT IDENTIFIER ::= { enterprises 11806 }
samuelballecom                    OBJECT IDENTIFIER ::= { enterprises 11807 }
sifryConsulting                   OBJECT IDENTIFIER ::= { enterprises 11808 }
skobeltsynInstituteOfNuclesrPhysics OBJECT IDENTIFIER ::= { enterprises 11809 }
solesysSA                         OBJECT IDENTIFIER ::= { enterprises 11810 }
spaces                            OBJECT IDENTIFIER ::= { enterprises 11811 }
tdcInternetAS                     OBJECT IDENTIFIER ::= { enterprises 11812 }
tmt                               OBJECT IDENTIFIER ::= { enterprises 11813 }
universityOfNantes                OBJECT IDENTIFIER ::= { enterprises 11814 }
yellowOnline                      OBJECT IDENTIFIER ::= { enterprises 11815 }
yuantongTechnology                OBJECT IDENTIFIER ::= { enterprises 11816 }
zentrumInformatikdienste          OBJECT IDENTIFIER ::= { enterprises 11817 }
zStarMicroelectronicsCorporation  OBJECT IDENTIFIER ::= { enterprises 11818 }
zxFactory                         OBJECT IDENTIFIER ::= { enterprises 11819 }
fonterraCoOperativeGroup          OBJECT IDENTIFIER ::= { enterprises 11820 }
jetInfosystems                    OBJECT IDENTIFIER ::= { enterprises 11821 }
spsuSelinuxLDAPTeam               OBJECT IDENTIFIER ::= { enterprises 11822 }
wsmicrosystems                    OBJECT IDENTIFIER ::= { enterprises 11823 }
computerAndTechnologiesInternational OBJECT IDENTIFIER ::= { enterprises 11824 }
dajiWorkshop                      OBJECT IDENTIFIER ::= { enterprises 11825 }
sistemasTecnicosDeEnse            OBJECT IDENTIFIER ::= { enterprises 11826 }
acumenADVANCEDTECHNOLOGIES        OBJECT IDENTIFIER ::= { enterprises 11827 }
coastMountainsSchoolDistrict      OBJECT IDENTIFIER ::= { enterprises 11828 }
corvilNetworks                    OBJECT IDENTIFIER ::= { enterprises 11829 }
f                                 OBJECT IDENTIFIER ::= { enterprises 11830 }
interactiveTransactionServices    OBJECT IDENTIFIER ::= { enterprises 11831 }
joergPreuss                       OBJECT IDENTIFIER ::= { enterprises 11832 }
ncircleNetworkSecurity            OBJECT IDENTIFIER ::= { enterprises 11833 }
plivaDd                           OBJECT IDENTIFIER ::= { enterprises 11834 }
streamserve                       OBJECT IDENTIFIER ::= { enterprises 11835 }
swissNationalBank                 OBJECT IDENTIFIER ::= { enterprises 11836 }
telenorMobileCommunications       OBJECT IDENTIFIER ::= { enterprises 11837 }
vistaar                           OBJECT IDENTIFIER ::= { enterprises 11838 }
webwayone                         OBJECT IDENTIFIER ::= { enterprises 11839 }
yrCONSEIL                         OBJECT IDENTIFIER ::= { enterprises 11840 }
aaltonenAndVuorela                OBJECT IDENTIFIER ::= { enterprises 11841 }
anchora                           OBJECT IDENTIFIER ::= { enterprises 11842 }
argusSystemsGroup                 OBJECT IDENTIFIER ::= { enterprises 11843 }
beijingSuperChannelNetworkLimited OBJECT IDENTIFIER ::= { enterprises 11844 }
blueairNetworks                   OBJECT IDENTIFIER ::= { enterprises 11845 }
citap                             OBJECT IDENTIFIER ::= { enterprises 11846 }
himnebaughConsulting              OBJECT IDENTIFIER ::= { enterprises 11847 }
inlineCorporation                 OBJECT IDENTIFIER ::= { enterprises 11848 }
janusTechnologies                 OBJECT IDENTIFIER ::= { enterprises 11849 }
nativeNamesCorporation            OBJECT IDENTIFIER ::= { enterprises 11850 }
neteconomist                      OBJECT IDENTIFIER ::= { enterprises 11851 }
newProductivityInitiative         OBJECT IDENTIFIER ::= { enterprises 11852 }
publicServiceCompanyOfNewMexico   OBJECT IDENTIFIER ::= { enterprises 11853 }
quovadx                           OBJECT IDENTIFIER ::= { enterprises 11854 }
retirementByDesign                OBJECT IDENTIFIER ::= { enterprises 11855 }
tntLogisticsNorthAmerica          OBJECT IDENTIFIER ::= { enterprises 11856 }
transmodeSystemsAB                OBJECT IDENTIFIER ::= { enterprises 11857 }
uangel                            OBJECT IDENTIFIER ::= { enterprises 11858 }
worldchain                        OBJECT IDENTIFIER ::= { enterprises 11859 }
wossnameorguk                     OBJECT IDENTIFIER ::= { enterprises 11860 }
codenet                           OBJECT IDENTIFIER ::= { enterprises 11861 }
columbiaUniversityInTheCityOfNewYork OBJECT IDENTIFIER ::= { enterprises 11862 }
tpLinkTechnologyCo                OBJECT IDENTIFIER ::= { enterprises 11863 }
b                                 OBJECT IDENTIFIER ::= { enterprises 11864 }
exploITResearch                   OBJECT IDENTIFIER ::= { enterprises 11865 }
gdtti                             OBJECT IDENTIFIER ::= { enterprises 11866 }
loopTreinamentoEmInform           OBJECT IDENTIFIER ::= { enterprises 11867 }
placenet                          OBJECT IDENTIFIER ::= { enterprises 11868 }
romanZielinskiMetodOchSystemutveckling OBJECT IDENTIFIER ::= { enterprises 11869 }
sandhillsCommunityCollege         OBJECT IDENTIFIER ::= { enterprises 11870 }
spacenetAG                        OBJECT IDENTIFIER ::= { enterprises 11871 }
systemyMikroprocesorowe           OBJECT IDENTIFIER ::= { enterprises 11872 }
yolkeCorporation                  OBJECT IDENTIFIER ::= { enterprises 11873 }
scopusTecnologiaSA                OBJECT IDENTIFIER ::= { enterprises 11874 }
biometMerckBV                     OBJECT IDENTIFIER ::= { enterprises 11875 }
siteseers                         OBJECT IDENTIFIER ::= { enterprises 11876 }
threeUPSystems                    OBJECT IDENTIFIER ::= { enterprises 11877 }
achillesGuard                     OBJECT IDENTIFIER ::= { enterprises 11878 }
castelEtFromaget                  OBJECT IDENTIFIER ::= { enterprises 11879 }
customBusinessLink                OBJECT IDENTIFIER ::= { enterprises 11880 }
fiberspansCorporation             OBJECT IDENTIFIER ::= { enterprises 11881 }
geschkeInternetConsulting         OBJECT IDENTIFIER ::= { enterprises 11882 }
igniteCommunications              OBJECT IDENTIFIER ::= { enterprises 11883 }
indeedVisualConcepts              OBJECT IDENTIFIER ::= { enterprises 11884 }
mmcTechnology                     OBJECT IDENTIFIER ::= { enterprises 11885 }
nextcard                          OBJECT IDENTIFIER ::= { enterprises 11886 }
secretseal                        OBJECT IDENTIFIER ::= { enterprises 11887 }
teamlogExternal                   OBJECT IDENTIFIER ::= { enterprises 11888 }
theAnswerGroup                    OBJECT IDENTIFIER ::= { enterprises 11889 }
theNogNetwork                     OBJECT IDENTIFIER ::= { enterprises 11890 }
unifiedCommunicationsPte          OBJECT IDENTIFIER ::= { enterprises 11891 }
vodafoneGlobalPlatformAndInternetServices OBJECT IDENTIFIER ::= { enterprises 11892 }
thePepBoysManny                   OBJECT IDENTIFIER ::= { enterprises 11893 }
integritySolutions                OBJECT IDENTIFIER ::= { enterprises 11894 }
globalnet                         OBJECT IDENTIFIER ::= { enterprises 11895 }
threeGLab                         OBJECT IDENTIFIER ::= { enterprises 11896 }
acantho                           OBJECT IDENTIFIER ::= { enterprises 11897 }
agereSystems                      OBJECT IDENTIFIER ::= { enterprises 11898 }
bitfoneCorporation                OBJECT IDENTIFIER ::= { enterprises 11899 }
bluesoft                          OBJECT IDENTIFIER ::= { enterprises 11900 }
bonndata                          OBJECT IDENTIFIER ::= { enterprises 11901 }
cartelCommunicationSystems        OBJECT IDENTIFIER ::= { enterprises 11902 }
caseWesternReserveUniversity      OBJECT IDENTIFIER ::= { enterprises 11903 }
cirquedigital                     OBJECT IDENTIFIER ::= { enterprises 11904 }
icom                              OBJECT IDENTIFIER ::= { enterprises 11905 }
ifDRAUDIMAS                       OBJECT IDENTIFIER ::= { enterprises 11906 }
imaginaryrealities                OBJECT IDENTIFIER ::= { enterprises 11907 }
institutoCubanoDeRadioYTelevision OBJECT IDENTIFIER ::= { enterprises 11908 }
logOnAmerica                      OBJECT IDENTIFIER ::= { enterprises 11909 }
michaelRoettigConsulting          OBJECT IDENTIFIER ::= { enterprises 11910 }
unassigned4                       OBJECT IDENTIFIER ::= { enterprises 11911 }
netmotionWireless                 OBJECT IDENTIFIER ::= { enterprises 11912 }
netsyscom                         OBJECT IDENTIFIER ::= { enterprises 11913 }
officeOfNationalInformationInfrastructureDevelopment OBJECT IDENTIFIER ::= { enterprises 11914 }
oldringAndAssociates              OBJECT IDENTIFIER ::= { enterprises 11915 }
pablix                            OBJECT IDENTIFIER ::= { enterprises 11916 }
par3Communications                OBJECT IDENTIFIER ::= { enterprises 11917 }
praja                             OBJECT IDENTIFIER ::= { enterprises 11918 }
qcom                              OBJECT IDENTIFIER ::= { enterprises 11919 }
quantumbeam                       OBJECT IDENTIFIER ::= { enterprises 11920 }
ruprechtAndPartnerOEG             OBJECT IDENTIFIER ::= { enterprises 11921 }
sd                                OBJECT IDENTIFIER ::= { enterprises 11922 }
spectrumControl                   OBJECT IDENTIFIER ::= { enterprises 11923 }
techsystemTechnologies            OBJECT IDENTIFIER ::= { enterprises 11924 }
theIQGroup                        OBJECT IDENTIFIER ::= { enterprises 11925 }
theUnitedWorldColleges            OBJECT IDENTIFIER ::= { enterprises 11926 }
tytrastSystems                    OBJECT IDENTIFIER ::= { enterprises 11927 }
velozGlobalSolutions              OBJECT IDENTIFIER ::= { enterprises 11928 }
veridicom                         OBJECT IDENTIFIER ::= { enterprises 11929 }
vseobecn                          OBJECT IDENTIFIER ::= { enterprises 11930 }
statenIslandUniversityHospital    OBJECT IDENTIFIER ::= { enterprises 11931 }
theWolfGroup                      OBJECT IDENTIFIER ::= { enterprises 11932 }
universityOfAlberta               OBJECT IDENTIFIER ::= { enterprises 11933 }
stadtsparkasseK                   OBJECT IDENTIFIER ::= { enterprises 11934 }
josuyaTechnologyCorporation       OBJECT IDENTIFIER ::= { enterprises 11935 }
amadeusNMCHolding                 OBJECT IDENTIFIER ::= { enterprises 11936 }
arcsight                          OBJECT IDENTIFIER ::= { enterprises 11937 }
cominet                           OBJECT IDENTIFIER ::= { enterprises 11938 }
electronicDirect                  OBJECT IDENTIFIER ::= { enterprises 11939 }
medicalCodingAndComplianceSolutions OBJECT IDENTIFIER ::= { enterprises 11940 }
mssu                              OBJECT IDENTIFIER ::= { enterprises 11941 }
muhenSoftware                     OBJECT IDENTIFIER ::= { enterprises 11942 }
netPartnetsSpZOo                  OBJECT IDENTIFIER ::= { enterprises 11943 }
paulmichlNetWork                  OBJECT IDENTIFIER ::= { enterprises 11944 }
qStationnet                       OBJECT IDENTIFIER ::= { enterprises 11945 }
quantaNetworkSystems              OBJECT IDENTIFIER ::= { enterprises 11946 }
stowarzyszenieFREEZENETASK        OBJECT IDENTIFIER ::= { enterprises 11947 }
syracuseUniversity                OBJECT IDENTIFIER ::= { enterprises 11948 }
ukrsotsbank                       OBJECT IDENTIFIER ::= { enterprises 11949 }
vivocom                           OBJECT IDENTIFIER ::= { enterprises 11950 }
vtechnologiesS                    OBJECT IDENTIFIER ::= { enterprises 11951 }
zetaBroadband                     OBJECT IDENTIFIER ::= { enterprises 11952 }
zumtobelAG                        OBJECT IDENTIFIER ::= { enterprises 11953 }
elegantSolutionsConsulting        OBJECT IDENTIFIER ::= { enterprises 11954 }
beijingNetPowerTECHNOLOGIES       OBJECT IDENTIFIER ::= { enterprises 11955 }
mobigenCo                         OBJECT IDENTIFIER ::= { enterprises 11956 }
itc                               OBJECT IDENTIFIER ::= { enterprises 11957 }
premonitia                        OBJECT IDENTIFIER ::= { enterprises 11958 }
coyoteRock                        OBJECT IDENTIFIER ::= { enterprises 11959 }
downlodeMedia                     OBJECT IDENTIFIER ::= { enterprises 11960 }
larcUSP                           OBJECT IDENTIFIER ::= { enterprises 11961 }
nevala                            OBJECT IDENTIFIER ::= { enterprises 11962 }
propel                            OBJECT IDENTIFIER ::= { enterprises 11963 }
technicalChamberOfGreece          OBJECT IDENTIFIER ::= { enterprises 11964 }
thomasMonitorSystems              OBJECT IDENTIFIER ::= { enterprises 11965 }
alstomPowerSwedenAB               OBJECT IDENTIFIER ::= { enterprises 11966 }
mlpAG                             OBJECT IDENTIFIER ::= { enterprises 11967 }
symlabs                           OBJECT IDENTIFIER ::= { enterprises 11968 }
systechRetailSystems              OBJECT IDENTIFIER ::= { enterprises 11969 }
watch4netSolutions                OBJECT IDENTIFIER ::= { enterprises 11970 }
peterService                      OBJECT IDENTIFIER ::= { enterprises 11971 }
tais                              OBJECT IDENTIFIER ::= { enterprises 11972 }
northCentralCollge                OBJECT IDENTIFIER ::= { enterprises 11973 }
uffizioInternetServices           OBJECT IDENTIFIER ::= { enterprises 11974 }
alphaSYSTEMS                      OBJECT IDENTIFIER ::= { enterprises 11975 }
atAndtLabsIntelligentNetworkAnalysis OBJECT IDENTIFIER ::= { enterprises 11976 }
backwoodsCommunications           OBJECT IDENTIFIER ::= { enterprises 11977 }
boxcarMedia                       OBJECT IDENTIFIER ::= { enterprises 11978 }
brainstormBusinessResources       OBJECT IDENTIFIER ::= { enterprises 11979 }
bravenetWebServices               OBJECT IDENTIFIER ::= { enterprises 11980 }
cac                               OBJECT IDENTIFIER ::= { enterprises 11981 }
chiznet                           OBJECT IDENTIFIER ::= { enterprises 11982 }
collectivebidSystems              OBJECT IDENTIFIER ::= { enterprises 11983 }
contentManagementAG               OBJECT IDENTIFIER ::= { enterprises 11984 }
conysisSA                         OBJECT IDENTIFIER ::= { enterprises 11985 }
creekpathSystems                  OBJECT IDENTIFIER ::= { enterprises 11986 }
dakosDataAndCommunicationCo       OBJECT IDENTIFIER ::= { enterprises 11987 }
dicarta                           OBJECT IDENTIFIER ::= { enterprises 11988 }
dmeCorporation                    OBJECT IDENTIFIER ::= { enterprises 11989 }
gadgeteerorg                      OBJECT IDENTIFIER ::= { enterprises 11990 }
greenpeace                        OBJECT IDENTIFIER ::= { enterprises 11991 }
helixensePte                      OBJECT IDENTIFIER ::= { enterprises 11992 }
hilbertComputing                  OBJECT IDENTIFIER ::= { enterprises 11993 }
hubertKrause                      OBJECT IDENTIFIER ::= { enterprises 11994 }
hybridSolutions                   OBJECT IDENTIFIER ::= { enterprises 11995 }
ibsn                              OBJECT IDENTIFIER ::= { enterprises 11996 }
iknowtheanswercom                 OBJECT IDENTIFIER ::= { enterprises 11997 }
jscDesarrollosYAplicaciones       OBJECT IDENTIFIER ::= { enterprises 11998 }
kfkiSystems                       OBJECT IDENTIFIER ::= { enterprises 11999 }
kiConsultingAndSolutionsAB        OBJECT IDENTIFIER ::= { enterprises 12000 }
lakefieldTelecom                  OBJECT IDENTIFIER ::= { enterprises 12001 }
lemurNetworks                     OBJECT IDENTIFIER ::= { enterprises 12002 }
luna8                             OBJECT IDENTIFIER ::= { enterprises 12003 }
mckAdvanceTechnologies            OBJECT IDENTIFIER ::= { enterprises 12004 }
mediags                           OBJECT IDENTIFIER ::= { enterprises 12005 }
nchSpaNetworkComputerHouse        OBJECT IDENTIFIER ::= { enterprises 12006 }
nams                              OBJECT IDENTIFIER ::= { enterprises 12007 }
pacher                            OBJECT IDENTIFIER ::= { enterprises 12008 }
regenstriefInstituteForHealthCare OBJECT IDENTIFIER ::= { enterprises 12009 }
schnackelchen                     OBJECT IDENTIFIER ::= { enterprises 12010 }
seagull                           OBJECT IDENTIFIER ::= { enterprises 12011 }
seoulNationalUniversityOfTechnology OBJECT IDENTIFIER ::= { enterprises 12012 }
softworksGroup                    OBJECT IDENTIFIER ::= { enterprises 12013 }
studioOfArtsAndSciences           OBJECT IDENTIFIER ::= { enterprises 12014 }
tgaTechnologies                   OBJECT IDENTIFIER ::= { enterprises 12015 }
universiteDeCergyPontoise         OBJECT IDENTIFIER ::= { enterprises 12016 }
veratnet                          OBJECT IDENTIFIER ::= { enterprises 12017 }
vivanet                           OBJECT IDENTIFIER ::= { enterprises 12018 }
waterfordorg                      OBJECT IDENTIFIER ::= { enterprises 12019 }
webwareTechnologiesPvt            OBJECT IDENTIFIER ::= { enterprises 12020 }
wesleyWorldWideSolutions          OBJECT IDENTIFIER ::= { enterprises 12021 }
brecisCommunications              OBJECT IDENTIFIER ::= { enterprises 12022 }
unassigned5                       OBJECT IDENTIFIER ::= { enterprises 12023 }
miraesysCo                        OBJECT IDENTIFIER ::= { enterprises 12024 }
cEISA                             OBJECT IDENTIFIER ::= { enterprises 12025 }
proactiveJavaConsultancyLLP       OBJECT IDENTIFIER ::= { enterprises 12026 }
accelanet                         OBJECT IDENTIFIER ::= { enterprises 12027 }
airwaveWireless                   OBJECT IDENTIFIER ::= { enterprises 12028 }
altawave                          OBJECT IDENTIFIER ::= { enterprises 12029 }
anamWirelessInternetSolutions     OBJECT IDENTIFIER ::= { enterprises 12030 }
bitstreamLogic                    OBJECT IDENTIFIER ::= { enterprises 12031 }
boozAllenHamilton                 OBJECT IDENTIFIER ::= { enterprises 12032 }
checkmateManagement               OBJECT IDENTIFIER ::= { enterprises 12033 }
czechCertificationAuthoritySro    OBJECT IDENTIFIER ::= { enterprises 12034 }
ebjConsulting                     OBJECT IDENTIFIER ::= { enterprises 12035 }
tcoleNormaleSup                   OBJECT IDENTIFIER ::= { enterprises 12036 }
euronetWorldwide                  OBJECT IDENTIFIER ::= { enterprises 12037 }
everyhostcom                      OBJECT IDENTIFIER ::= { enterprises 12038 }
exaleadSA                         OBJECT IDENTIFIER ::= { enterprises 12039 }
gullHouse                         OBJECT IDENTIFIER ::= { enterprises 12040 }
htlBraunau                        OBJECT IDENTIFIER ::= { enterprises 12041 }
infosysCorporation                OBJECT IDENTIFIER ::= { enterprises 12042 }
jasmap                            OBJECT IDENTIFIER ::= { enterprises 12043 }
lakesoftConsultingAndISP          OBJECT IDENTIFIER ::= { enterprises 12044 }
medfusion                         OBJECT IDENTIFIER ::= { enterprises 12045 }
metroInformationConceptsAs        OBJECT IDENTIFIER ::= { enterprises 12046 }
meylanConsulting                  OBJECT IDENTIFIER ::= { enterprises 12047 }
millenniumMicrowaveCorporation    OBJECT IDENTIFIER ::= { enterprises 12048 }
netplanetearth                    OBJECT IDENTIFIER ::= { enterprises 12049 }
ohmanITConsult                    OBJECT IDENTIFIER ::= { enterprises 12050 }
onyxSoftware                      OBJECT IDENTIFIER ::= { enterprises 12051 }
rcnTelecom                        OBJECT IDENTIFIER ::= { enterprises 12052 }
skjaerlundSoftware                OBJECT IDENTIFIER ::= { enterprises 12053 }
specialAppliedIntelligenceCorporation OBJECT IDENTIFIER ::= { enterprises 12054 }
sudac                             OBJECT IDENTIFIER ::= { enterprises 12055 }
tadiranCommunications             OBJECT IDENTIFIER ::= { enterprises 12056 }
teData                            OBJECT IDENTIFIER ::= { enterprises 12057 }
theYAKCorporation                 OBJECT IDENTIFIER ::= { enterprises 12058 }
digitalApplianceCorp              OBJECT IDENTIFIER ::= { enterprises 12059 }
trueposition                      OBJECT IDENTIFIER ::= { enterprises 12060 }
universityOfWesternOntario        OBJECT IDENTIFIER ::= { enterprises 12061 }
userInterfaceTechnologies         OBJECT IDENTIFIER ::= { enterprises 12062 }
vericell                          OBJECT IDENTIFIER ::= { enterprises 12063 }
zurichScudderInvestments          OBJECT IDENTIFIER ::= { enterprises 12064 }
apaton                            OBJECT IDENTIFIER ::= { enterprises 12065 }
daedalusNetworks                  OBJECT IDENTIFIER ::= { enterprises 12066 }
pajoNetworks                      OBJECT IDENTIFIER ::= { enterprises 12067 }
wroc                              OBJECT IDENTIFIER ::= { enterprises 12068 }
corpexInternet                    OBJECT IDENTIFIER ::= { enterprises 12069 }
warco                             OBJECT IDENTIFIER ::= { enterprises 12070 }
acrowaveSystemsCo                 OBJECT IDENTIFIER ::= { enterprises 12072 }
aerNovo                           OBJECT IDENTIFIER ::= { enterprises 12073 }
alisonAssociates                  OBJECT IDENTIFIER ::= { enterprises 12074 }
beckhausConsulting                OBJECT IDENTIFIER ::= { enterprises 12075 }
bonware                           OBJECT IDENTIFIER ::= { enterprises 12076 }
broadmindResearchCorporation      OBJECT IDENTIFIER ::= { enterprises 12077 }
circle24Technologies              OBJECT IDENTIFIER ::= { enterprises 12078 }
dotmaudot                         OBJECT IDENTIFIER ::= { enterprises 12079 }
ePeopleserve                      OBJECT IDENTIFIER ::= { enterprises 12080 }
esticAndPartnersBv                OBJECT IDENTIFIER ::= { enterprises 12081 }
europeanComputerTelecomsAG        OBJECT IDENTIFIER ::= { enterprises 12082 }
getronicsSolutionsItaliaSpA       OBJECT IDENTIFIER ::= { enterprises 12083 }
highdeal                          OBJECT IDENTIFIER ::= { enterprises 12084 }
krConsulting                      OBJECT IDENTIFIER ::= { enterprises 12085 }
mkapium                           OBJECT IDENTIFIER ::= { enterprises 12086 }
netdirectoryorg                   OBJECT IDENTIFIER ::= { enterprises 12087 }
newdreamnetCo                     OBJECT IDENTIFIER ::= { enterprises 12088 }
o3sisInfomationTechnologyAG       OBJECT IDENTIFIER ::= { enterprises 12089 }
prophetSystems                    OBJECT IDENTIFIER ::= { enterprises 12090 }
realFS                            OBJECT IDENTIFIER ::= { enterprises 12091 }
rotechHealthcare                  OBJECT IDENTIFIER ::= { enterprises 12092 }
severoceskaEnergetika             OBJECT IDENTIFIER ::= { enterprises 12093 }
sup                               OBJECT IDENTIFIER ::= { enterprises 12094 }
telenorSatelliteBroadcasting      OBJECT IDENTIFIER ::= { enterprises 12095 }
telicCommunications               OBJECT IDENTIFIER ::= { enterprises 12096 }
uzaUniversitairZiekenhuisAntwerpen OBJECT IDENTIFIER ::= { enterprises 12097 }
voodooXSolutions                  OBJECT IDENTIFIER ::= { enterprises 12098 }
woollenServices                   OBJECT IDENTIFIER ::= { enterprises 12099 }
xecurenexus                       OBJECT IDENTIFIER ::= { enterprises 12100 }
ycomSA                            OBJECT IDENTIFIER ::= { enterprises 12101 }
airportAuthorityHongKong          OBJECT IDENTIFIER ::= { enterprises 12102 }
tierSoftware                      OBJECT IDENTIFIER ::= { enterprises 12103 }
asis                              OBJECT IDENTIFIER ::= { enterprises 12104 }
bisc                              OBJECT IDENTIFIER ::= { enterprises 12105 }
bipopCARIRESpa                    OBJECT IDENTIFIER ::= { enterprises 12106 }
cawNetworks                       OBJECT IDENTIFIER ::= { enterprises 12107 }
concordant                        OBJECT IDENTIFIER ::= { enterprises 12108 }
itServiceOmikron                  OBJECT IDENTIFIER ::= { enterprises 12109 }
lifewayChristianResources         OBJECT IDENTIFIER ::= { enterprises 12110 }
markSchnurConsulting              OBJECT IDENTIFIER ::= { enterprises 12111 }
norsys                            OBJECT IDENTIFIER ::= { enterprises 12112 }
zox                               OBJECT IDENTIFIER ::= { enterprises 12113 }
norisNetworkAG                    OBJECT IDENTIFIER ::= { enterprises 12114 }
philipsMP4Net                     OBJECT IDENTIFIER ::= { enterprises 12115 }
advancedReality                   OBJECT IDENTIFIER ::= { enterprises 12116 }
atmelNantes                       OBJECT IDENTIFIER ::= { enterprises 12117 }
centrata                          OBJECT IDENTIFIER ::= { enterprises 12118 }
cityOfMesquiteTexas               OBJECT IDENTIFIER ::= { enterprises 12119 }
defenseSupplyCenterRichmond       OBJECT IDENTIFIER ::= { enterprises 12120 }
fastnetCommunications             OBJECT IDENTIFIER ::= { enterprises 12121 }
hennyPennyCorp                    OBJECT IDENTIFIER ::= { enterprises 12122 }
iprocessSolutions                 OBJECT IDENTIFIER ::= { enterprises 12123 }
isilonStstems                     OBJECT IDENTIFIER ::= { enterprises 12124 }
mediavirtuel                      OBJECT IDENTIFIER ::= { enterprises 12125 }
miraforAssociatesOy               OBJECT IDENTIFIER ::= { enterprises 12126 }
rambold                           OBJECT IDENTIFIER ::= { enterprises 12127 }
rodoguConsulting                  OBJECT IDENTIFIER ::= { enterprises 12128 }
safeweb                           OBJECT IDENTIFIER ::= { enterprises 12129 }
sciquest                          OBJECT IDENTIFIER ::= { enterprises 12130 }
siegfriedHoldingAG                OBJECT IDENTIFIER ::= { enterprises 12131 }
simutronicsCorporation            OBJECT IDENTIFIER ::= { enterprises 12132 }
talkingBlocks                     OBJECT IDENTIFIER ::= { enterprises 12133 }
tradetrans                        OBJECT IDENTIFIER ::= { enterprises 12134 }
uniqueBroadbankSystems            OBJECT IDENTIFIER ::= { enterprises 12135 }
universidadNacionalDeSanLuis      OBJECT IDENTIFIER ::= { enterprises 12136 }
universiteDeParisSorbonneParisIV  OBJECT IDENTIFIER ::= { enterprises 12137 }
laborat                           OBJECT IDENTIFIER ::= { enterprises 12138 }
iowaOutdoors                      OBJECT IDENTIFIER ::= { enterprises 12139 }
alcoma                            OBJECT IDENTIFIER ::= { enterprises 12140 }
aloes                             OBJECT IDENTIFIER ::= { enterprises 12141 }
bobCorbettNetworks                OBJECT IDENTIFIER ::= { enterprises 12142 }
chronoLogic                       OBJECT IDENTIFIER ::= { enterprises 12143 }
consumerContact                   OBJECT IDENTIFIER ::= { enterprises 12144 }
coreIntegratedTecnologies         OBJECT IDENTIFIER ::= { enterprises 12145 }
dialogsftService                  OBJECT IDENTIFIER ::= { enterprises 12146 }
dieWeltregierung                  OBJECT IDENTIFIER ::= { enterprises 12147 }
eltekEnergyAS                     OBJECT IDENTIFIER ::= { enterprises 12148 }
enalurSA                          OBJECT IDENTIFIER ::= { enterprises 12149 }
finmaticaSpA                      OBJECT IDENTIFIER ::= { enterprises 12150 }
fyrplusAB                         OBJECT IDENTIFIER ::= { enterprises 12151 }
guruLabs                          OBJECT IDENTIFIER ::= { enterprises 12152 }
hpcinteractive                    OBJECT IDENTIFIER ::= { enterprises 12153 }
ikeaITAB                          OBJECT IDENTIFIER ::= { enterprises 12154 }
innovay                           OBJECT IDENTIFIER ::= { enterprises 12155 }
jointSTOCKCOMPANY                 OBJECT IDENTIFIER ::= { enterprises 12156 }
kcMicroSpecialists                OBJECT IDENTIFIER ::= { enterprises 12157 }
mikrosKosmos                      OBJECT IDENTIFIER ::= { enterprises 12158 }
mTECNV                            OBJECT IDENTIFIER ::= { enterprises 12159 }
netcommpletePtyLyd                OBJECT IDENTIFIER ::= { enterprises 12160 }
newWorldTelephone                 OBJECT IDENTIFIER ::= { enterprises 12161 }
orsusSolutions                    OBJECT IDENTIFIER ::= { enterprises 12162 }
quebebercom                       OBJECT IDENTIFIER ::= { enterprises 12163 }
ringlingSchoolOfArtAndDesign      OBJECT IDENTIFIER ::= { enterprises 12164 }
santinEASSOCIATISRL               OBJECT IDENTIFIER ::= { enterprises 12165 }
scanPlus                          OBJECT IDENTIFIER ::= { enterprises 12166 }
sequiturSystems                   OBJECT IDENTIFIER ::= { enterprises 12167 }
server2000InternetTechnologyGmbh  OBJECT IDENTIFIER ::= { enterprises 12168 }
shenzhenMODERNCOMPUTERMANUFACTERCo OBJECT IDENTIFIER ::= { enterprises 12169 }
szcomBroadBandNetworkTechnology   OBJECT IDENTIFIER ::= { enterprises 12170 }
tonyBibbs                         OBJECT IDENTIFIER ::= { enterprises 12171 }
transparentSystems                OBJECT IDENTIFIER ::= { enterprises 12172 }
unicc                             OBJECT IDENTIFIER ::= { enterprises 12173 }
consolidatedFreightways           OBJECT IDENTIFIER ::= { enterprises 12174 }
frontierInternet                  OBJECT IDENTIFIER ::= { enterprises 12175 }
sumitomoMetalSystemSolutionsCo    OBJECT IDENTIFIER ::= { enterprises 12176 }
henkelKGaA                        OBJECT IDENTIFIER ::= { enterprises 12177 }
threeVanet                        OBJECT IDENTIFIER ::= { enterprises 12178 }
alacris                           OBJECT IDENTIFIER ::= { enterprises 12179 }
aliTechnologies                   OBJECT IDENTIFIER ::= { enterprises 12180 }
alleghenyEnergyGlobalMarkets      OBJECT IDENTIFIER ::= { enterprises 12181 }
astrium                           OBJECT IDENTIFIER ::= { enterprises 12182 }
baldwinHackettAndMeeks            OBJECT IDENTIFIER ::= { enterprises 12183 }
bamsco                            OBJECT IDENTIFIER ::= { enterprises 12184 }
benNederlandBV                    OBJECT IDENTIFIER ::= { enterprises 12185 }
compagnonAG                       OBJECT IDENTIFIER ::= { enterprises 12186 }
directSolutions                   OBJECT IDENTIFIER ::= { enterprises 12187 }
gbaseCommunications               OBJECT IDENTIFIER ::= { enterprises 12188 }
holoplexTechnologies              OBJECT IDENTIFIER ::= { enterprises 12189 }
inMediasRes                       OBJECT IDENTIFIER ::= { enterprises 12190 }
insSureServicesLimited            OBJECT IDENTIFIER ::= { enterprises 12191 }
ironHillTechnology                OBJECT IDENTIFIER ::= { enterprises 12192 }
leapstoneSystems                  OBJECT IDENTIFIER ::= { enterprises 12193 }
mssCommunicationsDesign           OBJECT IDENTIFIER ::= { enterprises 12194 }
noicomSpA                         OBJECT IDENTIFIER ::= { enterprises 12195 }
one4net                           OBJECT IDENTIFIER ::= { enterprises 12196 }
provisionsoft                     OBJECT IDENTIFIER ::= { enterprises 12197 }
rinet                             OBJECT IDENTIFIER ::= { enterprises 12198 }
sageSRL                           OBJECT IDENTIFIER ::= { enterprises 12199 }
senecaGroepBV                     OBJECT IDENTIFIER ::= { enterprises 12200 }
universityHealthNetwork           OBJECT IDENTIFIER ::= { enterprises 12201 }
up3i                              OBJECT IDENTIFIER ::= { enterprises 12202 }
vttInformationTechnology          OBJECT IDENTIFIER ::= { enterprises 12203 }
devonit                           OBJECT IDENTIFIER ::= { enterprises 12204 }
allianzIrelandPLC                 OBJECT IDENTIFIER ::= { enterprises 12205 }
msinbg                            OBJECT IDENTIFIER ::= { enterprises 12206 }
acmeSolutions                     OBJECT IDENTIFIER ::= { enterprises 12207 }
actinaAG                          OBJECT IDENTIFIER ::= { enterprises 12208 }
astorPROMOCJAPoland               OBJECT IDENTIFIER ::= { enterprises 12209 }
bauerVerlagsgruppe                OBJECT IDENTIFIER ::= { enterprises 12210 }
biogem                            OBJECT IDENTIFIER ::= { enterprises 12211 }
bluehavenServices                 OBJECT IDENTIFIER ::= { enterprises 12212 }
camis                             OBJECT IDENTIFIER ::= { enterprises 12213 }
covenantRetirementCommunities     OBJECT IDENTIFIER ::= { enterprises 12214 }
cuets                             OBJECT IDENTIFIER ::= { enterprises 12215 }
dgtLAB                            OBJECT IDENTIFIER ::= { enterprises 12216 }
ecolePolytechniqueDeMontreal      OBJECT IDENTIFIER ::= { enterprises 12217 }
gl                                OBJECT IDENTIFIER ::= { enterprises 12218 }
hamiltonAndSullivan               OBJECT IDENTIFIER ::= { enterprises 12219 }
instituteOfEnvironmentAndDevelopment OBJECT IDENTIFIER ::= { enterprises 12220 }
itwm                              OBJECT IDENTIFIER ::= { enterprises 12221 }
kawatetsuSystems                  OBJECT IDENTIFIER ::= { enterprises 12222 }
kineticsFluidSystems              OBJECT IDENTIFIER ::= { enterprises 12223 }
knightnet                         OBJECT IDENTIFIER ::= { enterprises 12224 }
koreaEmbeddedLinuxLaboratory      OBJECT IDENTIFIER ::= { enterprises 12225 }
maxPlanckInstitutFuerFestkoerperforschung OBJECT IDENTIFIER ::= { enterprises 12226 }
naumen                            OBJECT IDENTIFIER ::= { enterprises 12227 }
niedermayerSystems                OBJECT IDENTIFIER ::= { enterprises 12228 }
nirvanaResearch                   OBJECT IDENTIFIER ::= { enterprises 12229 }
odahodade                         OBJECT IDENTIFIER ::= { enterprises 12230 }
openadviceITServices              OBJECT IDENTIFIER ::= { enterprises 12231 }
orderN                            OBJECT IDENTIFIER ::= { enterprises 12232 }
ozCommunications                  OBJECT IDENTIFIER ::= { enterprises 12233 }
proguydk                          OBJECT IDENTIFIER ::= { enterprises 12234 }
roanokeCollege                    OBJECT IDENTIFIER ::= { enterprises 12235 }
senaTechnologies                  OBJECT IDENTIFIER ::= { enterprises 12236 }
silogix2                          OBJECT IDENTIFIER ::= { enterprises 12237 }
spumoni                           OBJECT IDENTIFIER ::= { enterprises 12238 }
symsoftAB                         OBJECT IDENTIFIER ::= { enterprises 12239 }
systemSolutions                   OBJECT IDENTIFIER ::= { enterprises 12240 }
szkolaGlownaHandlowa              OBJECT IDENTIFIER ::= { enterprises 12241 }
teamnet                           OBJECT IDENTIFIER ::= { enterprises 12242 }
vislinkPLC                        OBJECT IDENTIFIER ::= { enterprises 12243 }
celesticaCorporation              OBJECT IDENTIFIER ::= { enterprises 12244 }
elvin                             OBJECT IDENTIFIER ::= { enterprises 12245 }
scottishQualificationsAuthority   OBJECT IDENTIFIER ::= { enterprises 12246 }
idp                               OBJECT IDENTIFIER ::= { enterprises 12247 }
availixSA                         OBJECT IDENTIFIER ::= { enterprises 12248 }
escolaUniversitariaPolit          OBJECT IDENTIFIER ::= { enterprises 12249 }
alosysSpA                         OBJECT IDENTIFIER ::= { enterprises 12250 }
avalonNet                         OBJECT IDENTIFIER ::= { enterprises 12251 }
bakuConstructionOffice            OBJECT IDENTIFIER ::= { enterprises 12252 }
cnSolutions                       OBJECT IDENTIFIER ::= { enterprises 12253 }
compubahn                         OBJECT IDENTIFIER ::= { enterprises 12254 }
connecticutTelephone              OBJECT IDENTIFIER ::= { enterprises 12255 }
covere                            OBJECT IDENTIFIER ::= { enterprises 12256 }
escosoftTechnologies              OBJECT IDENTIFIER ::= { enterprises 12257 }
europeanTechnologyConsultants     OBJECT IDENTIFIER ::= { enterprises 12258 }
forumDesImages                    OBJECT IDENTIFIER ::= { enterprises 12259 }
globalTelecom                     OBJECT IDENTIFIER ::= { enterprises 12260 }
globalcenter                      OBJECT IDENTIFIER ::= { enterprises 12261 }
gnosysSARL                        OBJECT IDENTIFIER ::= { enterprises 12262 }
hdfcbank                          OBJECT IDENTIFIER ::= { enterprises 12263 }
imagineIT                         OBJECT IDENTIFIER ::= { enterprises 12264 }
indraweb                          OBJECT IDENTIFIER ::= { enterprises 12265 }
ircd                              OBJECT IDENTIFIER ::= { enterprises 12266 }
johnsHopkinsAppliedPhysicsLaboratory OBJECT IDENTIFIER ::= { enterprises 12267 }
libertyCommunicationServices      OBJECT IDENTIFIER ::= { enterprises 12268 }
maybaum                           OBJECT IDENTIFIER ::= { enterprises 12269 }
novar                             OBJECT IDENTIFIER ::= { enterprises 12270 }
pruthviSoft                       OBJECT IDENTIFIER ::= { enterprises 12271 }
sacredBytes                       OBJECT IDENTIFIER ::= { enterprises 12272 }
stateOfMinnesota                  OBJECT IDENTIFIER ::= { enterprises 12273 }
universiteJosephFourierGrenoble1  OBJECT IDENTIFIER ::= { enterprises 12274 }
universityOfSouthampton           OBJECT IDENTIFIER ::= { enterprises 12275 }
uroam                             OBJECT IDENTIFIER ::= { enterprises 12276 }
varysysTechnologies               OBJECT IDENTIFIER ::= { enterprises 12277 }
vtxTechnologie                    OBJECT IDENTIFIER ::= { enterprises 12278 }
warpLink                          OBJECT IDENTIFIER ::= { enterprises 12279 }
westernInstituteOfTechnologyAtTaranaki OBJECT IDENTIFIER ::= { enterprises 12280 }
yumemi                            OBJECT IDENTIFIER ::= { enterprises 12281 }
crewCo                            OBJECT IDENTIFIER ::= { enterprises 12282 }
planetInternetCommerce            OBJECT IDENTIFIER ::= { enterprises 12283 }
imaxNETWORKS                      OBJECT IDENTIFIER ::= { enterprises 12284 }
acclamationSystems                OBJECT IDENTIFIER ::= { enterprises 12285 }
issaqua                           OBJECT IDENTIFIER ::= { enterprises 12286 }
globecommSystems                  OBJECT IDENTIFIER ::= { enterprises 12287 }
andernResearchLabs                OBJECT IDENTIFIER ::= { enterprises 12288 }
beeweebSrl                        OBJECT IDENTIFIER ::= { enterprises 12289 }
celesticaInternational            OBJECT IDENTIFIER ::= { enterprises 12290 }
cellularSpecialties               OBJECT IDENTIFIER ::= { enterprises 12291 }
cindercat                         OBJECT IDENTIFIER ::= { enterprises 12292 }
digitalInsight                    OBJECT IDENTIFIER ::= { enterprises 12293 }
emblazeSystems                    OBJECT IDENTIFIER ::= { enterprises 12294 }
ercist                            OBJECT IDENTIFIER ::= { enterprises 12295 }
iddexCorp                         OBJECT IDENTIFIER ::= { enterprises 12296 }
independentStorageCorporation     OBJECT IDENTIFIER ::= { enterprises 12297 }
kingeAndCoLimited                 OBJECT IDENTIFIER ::= { enterprises 12298 }
ktg                               OBJECT IDENTIFIER ::= { enterprises 12299 }
mennonitenet                      OBJECT IDENTIFIER ::= { enterprises 12300 }
mountainVisionsPL                 OBJECT IDENTIFIER ::= { enterprises 12301 }
netikosSpa                        OBJECT IDENTIFIER ::= { enterprises 12302 }
newBridges                        OBJECT IDENTIFIER ::= { enterprises 12303 }
nextAdvisors                      OBJECT IDENTIFIER ::= { enterprises 12304 }
petrasync                         OBJECT IDENTIFIER ::= { enterprises 12305 }
preworkx                          OBJECT IDENTIFIER ::= { enterprises 12306 }
redWagonSolutions                 OBJECT IDENTIFIER ::= { enterprises 12307 }
seclab                            OBJECT IDENTIFIER ::= { enterprises 12308 }
selfIndulgenceorg                 OBJECT IDENTIFIER ::= { enterprises 12309 }
simpleAccess                      OBJECT IDENTIFIER ::= { enterprises 12310 }
strategicServiceAlliance          OBJECT IDENTIFIER ::= { enterprises 12311 }
taikaTechnologies                 OBJECT IDENTIFIER ::= { enterprises 12312 }
tattersalls                       OBJECT IDENTIFIER ::= { enterprises 12313 }
universidadeFederalDeCampinaGrande OBJECT IDENTIFIER ::= { enterprises 12314 }
worldwithoutwirecom               OBJECT IDENTIFIER ::= { enterprises 12315 }
chuoElectroplaters                OBJECT IDENTIFIER ::= { enterprises 12316 }
glTrade                           OBJECT IDENTIFIER ::= { enterprises 12317 }
loomisChaffeeSchool               OBJECT IDENTIFIER ::= { enterprises 12318 }
heiwakogyo                        OBJECT IDENTIFIER ::= { enterprises 12319 }
aspenSystems                      OBJECT IDENTIFIER ::= { enterprises 12320 }
bureEquity                        OBJECT IDENTIFIER ::= { enterprises 12321 }
deltaInformationAndCommunication  OBJECT IDENTIFIER ::= { enterprises 12322 }
departmentOfComputerScience       OBJECT IDENTIFIER ::= { enterprises 12323 }
deutscheLebensRettungsGesellschaftEV OBJECT IDENTIFIER ::= { enterprises 12324 }
fraunhoferFOKUS                   OBJECT IDENTIFIER ::= { enterprises 12325 }
hermesPrecisaAustralia            OBJECT IDENTIFIER ::= { enterprises 12326 }
kjsandersProfessionalConsultingEngineers OBJECT IDENTIFIER ::= { enterprises 12327 }
lawsitPty                         OBJECT IDENTIFIER ::= { enterprises 12328 }
panasonicOWL                      OBJECT IDENTIFIER ::= { enterprises 12329 }
plan42Gmbh                        OBJECT IDENTIFIER ::= { enterprises 12330 }
prestoPty                         OBJECT IDENTIFIER ::= { enterprises 12331 }
primusTelecommunicationsGroup     OBJECT IDENTIFIER ::= { enterprises 12332 }
teTMTiimi                         OBJECT IDENTIFIER ::= { enterprises 12333 }
universalCommunicationPlatformGmbh OBJECT IDENTIFIER ::= { enterprises 12334 }
universityOfYork                  OBJECT IDENTIFIER ::= { enterprises 12335 }
buyways                           OBJECT IDENTIFIER ::= { enterprises 12336 }
broadBandNetworkCenterOfTsinghuaUniversity OBJECT IDENTIFIER ::= { enterprises 12337 }
netcoreNetworkTechnology          OBJECT IDENTIFIER ::= { enterprises 12338 }
empoweredNetworks                 OBJECT IDENTIFIER ::= { enterprises 12339 }
netFacilitiesGroup                OBJECT IDENTIFIER ::= { enterprises 12340 }
novomodo                          OBJECT IDENTIFIER ::= { enterprises 12341 }
pivia                             OBJECT IDENTIFIER ::= { enterprises 12342 }
skAccessDevices                   OBJECT IDENTIFIER ::= { enterprises 12343 }
teros                             OBJECT IDENTIFIER ::= { enterprises 12344 }
vwbGroup                          OBJECT IDENTIFIER ::= { enterprises 12345 }
hagero                            OBJECT IDENTIFIER ::= { enterprises 12346 }
amalgamatedSystems                OBJECT IDENTIFIER ::= { enterprises 12347 }
americanRadioRelayLeague          OBJECT IDENTIFIER ::= { enterprises 12348 }
atConsultancy                     OBJECT IDENTIFIER ::= { enterprises 12349 }
atmelHellas                       OBJECT IDENTIFIER ::= { enterprises 12350 }
barkingCow                        OBJECT IDENTIFIER ::= { enterprises 12351 }
centralDataServices               OBJECT IDENTIFIER ::= { enterprises 12352 }
claridenBank                      OBJECT IDENTIFIER ::= { enterprises 12353 }
colbournAssociates                OBJECT IDENTIFIER ::= { enterprises 12354 }
ctiPETSystems                     OBJECT IDENTIFIER ::= { enterprises 12355 }
fortinet                          OBJECT IDENTIFIER ::= { enterprises 12356 }
genericMedia                      OBJECT IDENTIFIER ::= { enterprises 12357 }
imagemedical                      OBJECT IDENTIFIER ::= { enterprises 12358 }
indigoTango                       OBJECT IDENTIFIER ::= { enterprises 12359 }
institutoEspa                     OBJECT IDENTIFIER ::= { enterprises 12360 }
kgexcomCo                         OBJECT IDENTIFIER ::= { enterprises 12361 }
lombardOdierAndCie                OBJECT IDENTIFIER ::= { enterprises 12362 }
netLabsSystemhaus                 OBJECT IDENTIFIER ::= { enterprises 12363 }
newbreakLLC                       OBJECT IDENTIFIER ::= { enterprises 12364 }
nttCOMWARECORPORATION             OBJECT IDENTIFIER ::= { enterprises 12365 }
pharmaciaCorporation              OBJECT IDENTIFIER ::= { enterprises 12366 }
quickCorp                         OBJECT IDENTIFIER ::= { enterprises 12367 }
raesemannEnterprises              OBJECT IDENTIFIER ::= { enterprises 12368 }
r                                 OBJECT IDENTIFIER ::= { enterprises 12369 }
sardCommunications                OBJECT IDENTIFIER ::= { enterprises 12370 }
scrutiny                          OBJECT IDENTIFIER ::= { enterprises 12371 }
teracloudCorporation              OBJECT IDENTIFIER ::= { enterprises 12372 }
tetrapodCommunications            OBJECT IDENTIFIER ::= { enterprises 12373 }
texasStateCreditCompany           OBJECT IDENTIFIER ::= { enterprises 12374 }
universalAccess                   OBJECT IDENTIFIER ::= { enterprises 12375 }
universityOfTechnologyDresden     OBJECT IDENTIFIER ::= { enterprises 12376 }
vivendiTelecomHungary             OBJECT IDENTIFIER ::= { enterprises 12377 }
wellthot                          OBJECT IDENTIFIER ::= { enterprises 12378 }
wingraTechnologies                OBJECT IDENTIFIER ::= { enterprises 12379 }
wiwoSupport                       OBJECT IDENTIFIER ::= { enterprises 12380 }
worldcomAsiaPacific               OBJECT IDENTIFIER ::= { enterprises 12381 }
unihubGLOBALNETWORK               OBJECT IDENTIFIER ::= { enterprises 12382 }
chrysalisITS                      OBJECT IDENTIFIER ::= { enterprises 12383 }
commissariatAL                    OBJECT IDENTIFIER ::= { enterprises 12384 }
commonVoices                      OBJECT IDENTIFIER ::= { enterprises 12385 }
inteqCorporation                  OBJECT IDENTIFIER ::= { enterprises 12386 }
ipdirections                      OBJECT IDENTIFIER ::= { enterprises 12387 }
justthenetLLC                     OBJECT IDENTIFIER ::= { enterprises 12388 }
macsdesignStudio                  OBJECT IDENTIFIER ::= { enterprises 12389 }
microcellTelecommunications       OBJECT IDENTIFIER ::= { enterprises 12390 }
universiteitUtrecht               OBJECT IDENTIFIER ::= { enterprises 12391 }
welcat                            OBJECT IDENTIFIER ::= { enterprises 12392 }
activeHotels                      OBJECT IDENTIFIER ::= { enterprises 12393 }
alvarion                          OBJECT IDENTIFIER ::= { enterprises 12394 }
centroDeInformaticaDaUniversidadeDeCoimbra OBJECT IDENTIFIER ::= { enterprises 12395 }
cintechSolutions                  OBJECT IDENTIFIER ::= { enterprises 12396 }
gesellschaftFuerRaumbildsystemeMbH OBJECT IDENTIFIER ::= { enterprises 12397 }
eOOspedaliGalliera                OBJECT IDENTIFIER ::= { enterprises 12398 }
fixExpressCorp                    OBJECT IDENTIFIER ::= { enterprises 12399 }
gatea                             OBJECT IDENTIFIER ::= { enterprises 12400 }
germinusSolutions                 OBJECT IDENTIFIER ::= { enterprises 12401 }
idlspm                            OBJECT IDENTIFIER ::= { enterprises 12402 }
imediaSemiconductorCorp           OBJECT IDENTIFIER ::= { enterprises 12403 }
indianguidecom                    OBJECT IDENTIFIER ::= { enterprises 12404 }
matrics                           OBJECT IDENTIFIER ::= { enterprises 12405 }
medinetIDGSA                      OBJECT IDENTIFIER ::= { enterprises 12406 }
niceshippingTechnologyCorporation OBJECT IDENTIFIER ::= { enterprises 12407 }
noordelijkeHogeschoolLeeuwarden   OBJECT IDENTIFIER ::= { enterprises 12408 }
objectivity                       OBJECT IDENTIFIER ::= { enterprises 12409 }
ops                               OBJECT IDENTIFIER ::= { enterprises 12410 }
plasmedia                         OBJECT IDENTIFIER ::= { enterprises 12411 }
portbridgeInternet                OBJECT IDENTIFIER ::= { enterprises 12412 }
radioFrequencySystems             OBJECT IDENTIFIER ::= { enterprises 12413 }
scryptoSystems                    OBJECT IDENTIFIER ::= { enterprises 12414 }
sinnerschraderAG                  OBJECT IDENTIFIER ::= { enterprises 12415 }
summitPlaceAles                   OBJECT IDENTIFIER ::= { enterprises 12416 }
tataInfotechLimited               OBJECT IDENTIFIER ::= { enterprises 12417 }
thales                            OBJECT IDENTIFIER ::= { enterprises 12418 }
yamahaCORPORATION                 OBJECT IDENTIFIER ::= { enterprises 12419 }
yokogawaBlueStarIndia             OBJECT IDENTIFIER ::= { enterprises 12420 }
jwayGROUP                         OBJECT IDENTIFIER ::= { enterprises 12421 }
theCoOperators                    OBJECT IDENTIFIER ::= { enterprises 12422 }
concordTelephoneCompany           OBJECT IDENTIFIER ::= { enterprises 12423 }
congregationOfTheSacredHearts     OBJECT IDENTIFIER ::= { enterprises 12424 }
conlingual                        OBJECT IDENTIFIER ::= { enterprises 12425 }
eControlSystems                   OBJECT IDENTIFIER ::= { enterprises 12426 }
equinoxEngineering                OBJECT IDENTIFIER ::= { enterprises 12427 }
genieInformationCo                OBJECT IDENTIFIER ::= { enterprises 12428 }
interact                          OBJECT IDENTIFIER ::= { enterprises 12429 }
iSilver                           OBJECT IDENTIFIER ::= { enterprises 12430 }
ixusTechnologiedienstleistungen   OBJECT IDENTIFIER ::= { enterprises 12431 }
jippiGroupOyj                     OBJECT IDENTIFIER ::= { enterprises 12432 }
johnSheahanAndCo                  OBJECT IDENTIFIER ::= { enterprises 12433 }
knoxCollege                       OBJECT IDENTIFIER ::= { enterprises 12434 }
m2SystemsCorporation              OBJECT IDENTIFIER ::= { enterprises 12435 }
navosha                           OBJECT IDENTIFIER ::= { enterprises 12436 }
nextLevelDesign                   OBJECT IDENTIFIER ::= { enterprises 12437 }
paradigmonePty                    OBJECT IDENTIFIER ::= { enterprises 12438 }
ritzlmayrConsulting               OBJECT IDENTIFIER ::= { enterprises 12439 }
securenet                         OBJECT IDENTIFIER ::= { enterprises 12440 }
selectedHOSTING                   OBJECT IDENTIFIER ::= { enterprises 12441 }
techgemini                        OBJECT IDENTIFIER ::= { enterprises 12442 }
wwwtrafficshapercom               OBJECT IDENTIFIER ::= { enterprises 12443 }
mangolution                       OBJECT IDENTIFIER ::= { enterprises 12444 }
teradyne                          OBJECT IDENTIFIER ::= { enterprises 12445 }
unphu                             OBJECT IDENTIFIER ::= { enterprises 12446 }
ycConsultant                      OBJECT IDENTIFIER ::= { enterprises 12447 }
thVISIONBILLINGCOMPANY            OBJECT IDENTIFIER ::= { enterprises 12448 }
audiofonChatAndPlay               OBJECT IDENTIFIER ::= { enterprises 12449 }
australianDepartmentOfEmploymentAndWorkplaceRelations OBJECT IDENTIFIER ::= { enterprises 12450 }
communicationConcept              OBJECT IDENTIFIER ::= { enterprises 12451 }
intraconnect                      OBJECT IDENTIFIER ::= { enterprises 12452 }
alaskaPowerAndTelephone           OBJECT IDENTIFIER ::= { enterprises 12453 }
ariaSolutions                     OBJECT IDENTIFIER ::= { enterprises 12454 }
caco                              OBJECT IDENTIFIER ::= { enterprises 12455 }
certisurSA                        OBJECT IDENTIFIER ::= { enterprises 12456 }
chunghwaTelecomLaboratories       OBJECT IDENTIFIER ::= { enterprises 12457 }
dickinsonConsulting               OBJECT IDENTIFIER ::= { enterprises 12458 }
globalNameRegistryLimited         OBJECT IDENTIFIER ::= { enterprises 12459 }
isgConsultoriaEInformatica        OBJECT IDENTIFIER ::= { enterprises 12460 }
jamm                              OBJECT IDENTIFIER ::= { enterprises 12461 }
linuxfabrik                       OBJECT IDENTIFIER ::= { enterprises 12462 }
mendosus                          OBJECT IDENTIFIER ::= { enterprises 12463 }
microdowellSpA                    OBJECT IDENTIFIER ::= { enterprises 12464 }
mykitchentablenet                 OBJECT IDENTIFIER ::= { enterprises 12465 }
netfectiveTechnology              OBJECT IDENTIFIER ::= { enterprises 12466 }
onesecure                         OBJECT IDENTIFIER ::= { enterprises 12467 }
pixion                            OBJECT IDENTIFIER ::= { enterprises 12468 }
qacQualityAssuranceConsult        OBJECT IDENTIFIER ::= { enterprises 12469 }
rechberger                        OBJECT IDENTIFIER ::= { enterprises 12470 }
rocketSoftware                    OBJECT IDENTIFIER ::= { enterprises 12471 }
scapevisionAG                     OBJECT IDENTIFIER ::= { enterprises 12472 }
unilang                           OBJECT IDENTIFIER ::= { enterprises 12473 }
wac                               OBJECT IDENTIFIER ::= { enterprises 12474 }
webmotion                         OBJECT IDENTIFIER ::= { enterprises 12475 }
carmodyConsulting                 OBJECT IDENTIFIER ::= { enterprises 12476 }
christianMichelsenResearchAS      OBJECT IDENTIFIER ::= { enterprises 12477 }
marylandDepartmentOfTransportation OBJECT IDENTIFIER ::= { enterprises 12478 }
opendnsCorp                       OBJECT IDENTIFIER ::= { enterprises 12479 }
alliedWorldwide                   OBJECT IDENTIFIER ::= { enterprises 12480 }
altrick                           OBJECT IDENTIFIER ::= { enterprises 12481 }
departmentoT                      OBJECT IDENTIFIER ::= { enterprises 12482 }
ebel                              OBJECT IDENTIFIER ::= { enterprises 12483 }
binarySolutions                   OBJECT IDENTIFIER ::= { enterprises 12484 }
wumag                             OBJECT IDENTIFIER ::= { enterprises 12485 }
accessGrid                        OBJECT IDENTIFIER ::= { enterprises 12486 }
adamCommunicationSystemsInternational OBJECT IDENTIFIER ::= { enterprises 12487 }
ankorSystems                      OBJECT IDENTIFIER ::= { enterprises 12488 }
arizonaMailOrderCo                OBJECT IDENTIFIER ::= { enterprises 12489 }
becksteinSystems                  OBJECT IDENTIFIER ::= { enterprises 12490 }
bonddesk                          OBJECT IDENTIFIER ::= { enterprises 12491 }
cameronNet                        OBJECT IDENTIFIER ::= { enterprises 12492 }
elistEXpressLLC                   OBJECT IDENTIFIER ::= { enterprises 12493 }
enigmatec                         OBJECT IDENTIFIER ::= { enterprises 12494 }
eskataSystems                     OBJECT IDENTIFIER ::= { enterprises 12495 }
gosbc                             OBJECT IDENTIFIER ::= { enterprises 12496 }
holbornColleg                     OBJECT IDENTIFIER ::= { enterprises 12497 }
infofiend                         OBJECT IDENTIFIER ::= { enterprises 12498 }
ipb                               OBJECT IDENTIFIER ::= { enterprises 12499 }
isroSatelliteCentre               OBJECT IDENTIFIER ::= { enterprises 12500 }
keysoftenterllect                 OBJECT IDENTIFIER ::= { enterprises 12501 }
metzemix                          OBJECT IDENTIFIER ::= { enterprises 12502 }
myuglyfaceCOMPUTING               OBJECT IDENTIFIER ::= { enterprises 12503 }
onlight                           OBJECT IDENTIFIER ::= { enterprises 12504 }
photonicBridges                   OBJECT IDENTIFIER ::= { enterprises 12505 }
pinpointNetworks                  OBJECT IDENTIFIER ::= { enterprises 12506 }
profisSA                          OBJECT IDENTIFIER ::= { enterprises 12507 }
scardineAndLopes                  OBJECT IDENTIFIER ::= { enterprises 12508 }
secureone                         OBJECT IDENTIFIER ::= { enterprises 12509 }
slackworks                        OBJECT IDENTIFIER ::= { enterprises 12510 }
telesudesteCelular                OBJECT IDENTIFIER ::= { enterprises 12511 }
universityOfUtahCollegeOfMinesAndEarthSciences OBJECT IDENTIFIER ::= { enterprises 12512 }
xitemediaISVOF                    OBJECT IDENTIFIER ::= { enterprises 12513 }
abbottLaboratories                OBJECT IDENTIFIER ::= { enterprises 12514 }
orgaKartensysteme                 OBJECT IDENTIFIER ::= { enterprises 12515 }
arlHomeCommunicationsSdnBhd       OBJECT IDENTIFIER ::= { enterprises 12516 }
manNutzfahrzeugeAG                OBJECT IDENTIFIER ::= { enterprises 12517 }
universityOfMainz                 OBJECT IDENTIFIER ::= { enterprises 12518 }
activa3                           OBJECT IDENTIFIER ::= { enterprises 12519 }
asyres                            OBJECT IDENTIFIER ::= { enterprises 12520 }
avacue                            OBJECT IDENTIFIER ::= { enterprises 12521 }
californiaStateUniversity3        OBJECT IDENTIFIER ::= { enterprises 12522 }
creditUnionCentralOfManitoba      OBJECT IDENTIFIER ::= { enterprises 12523 }
dib                               OBJECT IDENTIFIER ::= { enterprises 12524 }
echostarSolutions                 OBJECT IDENTIFIER ::= { enterprises 12525 }
groupeEyrolles                    OBJECT IDENTIFIER ::= { enterprises 12526 }
hopfElektronik                    OBJECT IDENTIFIER ::= { enterprises 12527 }
icognitoTechnologies              OBJECT IDENTIFIER ::= { enterprises 12528 }
idgCommunications                 OBJECT IDENTIFIER ::= { enterprises 12529 }
informatikdienste                 OBJECT IDENTIFIER ::= { enterprises 12530 }
jamesKFeganConsulting             OBJECT IDENTIFIER ::= { enterprises 12531 }
neoteris                          OBJECT IDENTIFIER ::= { enterprises 12532 }
noxCO                             OBJECT IDENTIFIER ::= { enterprises 12533 }
nzphoneSA                         OBJECT IDENTIFIER ::= { enterprises 12534 }
schmidtAndCo                      OBJECT IDENTIFIER ::= { enterprises 12535 }
simsamConsultingLimited           OBJECT IDENTIFIER ::= { enterprises 12536 }
spiderEyeStudios                  OBJECT IDENTIFIER ::= { enterprises 12537 }
telkom                            OBJECT IDENTIFIER ::= { enterprises 12538 }
thePalantirCorporation            OBJECT IDENTIFIER ::= { enterprises 12539 }
tSystemsInternational             OBJECT IDENTIFIER ::= { enterprises 12540 }
universidadDeCarabobo             OBJECT IDENTIFIER ::= { enterprises 12541 }
unizetoSpZOo                      OBJECT IDENTIFIER ::= { enterprises 12542 }
virgilBV                          OBJECT IDENTIFIER ::= { enterprises 12543 }
aegonNederlandNV                  OBJECT IDENTIFIER ::= { enterprises 12544 }
isIndustrialServicesAG            OBJECT IDENTIFIER ::= { enterprises 12545 }
verysmartpeople                   OBJECT IDENTIFIER ::= { enterprises 12546 }
principle                         OBJECT IDENTIFIER ::= { enterprises 12547 }
hshNordbankAG                     OBJECT IDENTIFIER ::= { enterprises 12548 }
airNavigationServices             OBJECT IDENTIFIER ::= { enterprises 12549 }
associationForMultidisciplineEducationInTheHealthSciences OBJECT IDENTIFIER ::= { enterprises 12550 }
ceT                               OBJECT IDENTIFIER ::= { enterprises 12551 }
corporationOfBalcultha            OBJECT IDENTIFIER ::= { enterprises 12552 }
dispuutMeteoor                    OBJECT IDENTIFIER ::= { enterprises 12553 }
ecclesiasnet                      OBJECT IDENTIFIER ::= { enterprises 12554 }
eduroTechnologies                 OBJECT IDENTIFIER ::= { enterprises 12555 }
emsolLLC                          OBJECT IDENTIFIER ::= { enterprises 12556 }
gurumeditationsorg                OBJECT IDENTIFIER ::= { enterprises 12557 }
icoserveInformationTechnologies2  OBJECT IDENTIFIER ::= { enterprises 12558 }
inria                             OBJECT IDENTIFIER ::= { enterprises 12559 }
interepochTechnology              OBJECT IDENTIFIER ::= { enterprises 12560 }
khonraadSystemsEngineeringBV      OBJECT IDENTIFIER ::= { enterprises 12561 }
marcomDepartmentShanghaiMitacResearchCo OBJECT IDENTIFIER ::= { enterprises 12562 }
megatel                           OBJECT IDENTIFIER ::= { enterprises 12563 }
natverket                         OBJECT IDENTIFIER ::= { enterprises 12564 }
navahoNetworks                    OBJECT IDENTIFIER ::= { enterprises 12565 }
nikoilInvestmentBankingGroup      OBJECT IDENTIFIER ::= { enterprises 12566 }
one5Corporation                   OBJECT IDENTIFIER ::= { enterprises 12567 }
rangerComputers                   OBJECT IDENTIFIER ::= { enterprises 12568 }
rigelCorporation                  OBJECT IDENTIFIER ::= { enterprises 12569 }
siceSrl                           OBJECT IDENTIFIER ::= { enterprises 12570 }
symneticsHoldings                 OBJECT IDENTIFIER ::= { enterprises 12571 }
tcdEnterprise                     OBJECT IDENTIFIER ::= { enterprises 12572 }
telonorBusinessSolutions          OBJECT IDENTIFIER ::= { enterprises 12573 }
tmhTheMarilynHouseSrl             OBJECT IDENTIFIER ::= { enterprises 12574 }
uic                               OBJECT IDENTIFIER ::= { enterprises 12575 }
unidirect                         OBJECT IDENTIFIER ::= { enterprises 12576 }
uniqueInteractive                 OBJECT IDENTIFIER ::= { enterprises 12577 }
violaSystems                      OBJECT IDENTIFIER ::= { enterprises 12578 }
zigzagInternetServiceProvider     OBJECT IDENTIFIER ::= { enterprises 12579 }
zirionNETWORKS                    OBJECT IDENTIFIER ::= { enterprises 12580 }
naruhodoSolutions                 OBJECT IDENTIFIER ::= { enterprises 12581 }
primericaFinancialServices        OBJECT IDENTIFIER ::= { enterprises 12582 }
universityOfCalifornia2           OBJECT IDENTIFIER ::= { enterprises 12583 }
butler                            OBJECT IDENTIFIER ::= { enterprises 12584 }
alstomHoldings                    OBJECT IDENTIFIER ::= { enterprises 12585 }
apiatechInformationTechnologies   OBJECT IDENTIFIER ::= { enterprises 12586 }
three0am                          OBJECT IDENTIFIER ::= { enterprises 12587 }
blueiceResearchAB                 OBJECT IDENTIFIER ::= { enterprises 12588 }
celestialSoftwareLLC              OBJECT IDENTIFIER ::= { enterprises 12589 }
changiInternationalAirportServicesPte OBJECT IDENTIFIER ::= { enterprises 12590 }
corusGroupPlc                     OBJECT IDENTIFIER ::= { enterprises 12591 }
dycec                             OBJECT IDENTIFIER ::= { enterprises 12592 }
eklSolutionsLLC                   OBJECT IDENTIFIER ::= { enterprises 12593 }
elmaIngenierieInformatique        OBJECT IDENTIFIER ::= { enterprises 12594 }
emsEnterpriseMessagingSolutions   OBJECT IDENTIFIER ::= { enterprises 12595 }
jouveSA                           OBJECT IDENTIFIER ::= { enterprises 12596 }
lightwaveCommunications           OBJECT IDENTIFIER ::= { enterprises 12597 }
netVista                          OBJECT IDENTIFIER ::= { enterprises 12598 }
ordynElectronicSystemsPrivateLimited OBJECT IDENTIFIER ::= { enterprises 12599 }
peramonTechnology                 OBJECT IDENTIFIER ::= { enterprises 12600 }
reedCollege                       OBJECT IDENTIFIER ::= { enterprises 12601 }
roonetworks                       OBJECT IDENTIFIER ::= { enterprises 12602 }
shadowsupport                     OBJECT IDENTIFIER ::= { enterprises 12603 }
spatialWireless                   OBJECT IDENTIFIER ::= { enterprises 12604 }
shom                              OBJECT IDENTIFIER ::= { enterprises 12605 }
mbbGelma                          OBJECT IDENTIFIER ::= { enterprises 12606 }
advanceFiberOptics                OBJECT IDENTIFIER ::= { enterprises 12607 }
ahapala                           OBJECT IDENTIFIER ::= { enterprises 12608 }
ascellaTechnologies               OBJECT IDENTIFIER ::= { enterprises 12609 }
aspenBusinessLogicComputing       OBJECT IDENTIFIER ::= { enterprises 12610 }
atlantiqueSoftware                OBJECT IDENTIFIER ::= { enterprises 12611 }
barcoBCI                          OBJECT IDENTIFIER ::= { enterprises 12612 }
broadjump                         OBJECT IDENTIFIER ::= { enterprises 12613 }
cirba                             OBJECT IDENTIFIER ::= { enterprises 12614 }
craigFDonlan                      OBJECT IDENTIFIER ::= { enterprises 12615 }
datacorp                          OBJECT IDENTIFIER ::= { enterprises 12616 }
espedairSystems                   OBJECT IDENTIFIER ::= { enterprises 12617 }
ezhiTechnologies                  OBJECT IDENTIFIER ::= { enterprises 12618 }
ufrgs                             OBJECT IDENTIFIER ::= { enterprises 12619 }
futureSystemConsultingCorp        OBJECT IDENTIFIER ::= { enterprises 12620 }
geMedicalSystemInformationTechnologiesSW OBJECT IDENTIFIER ::= { enterprises 12621 }
instant802Networks                OBJECT IDENTIFIER ::= { enterprises 12622 }
irciSA                            OBJECT IDENTIFIER ::= { enterprises 12623 }
kennesawStateUniversity           OBJECT IDENTIFIER ::= { enterprises 12624 }
labbook                           OBJECT IDENTIFIER ::= { enterprises 12625 }
ministryOfEducation               OBJECT IDENTIFIER ::= { enterprises 12626 }
morganStanleySVSA                 OBJECT IDENTIFIER ::= { enterprises 12627 }
movielink                         OBJECT IDENTIFIER ::= { enterprises 12628 }
mse                               OBJECT IDENTIFIER ::= { enterprises 12629 }
mSolutions                        OBJECT IDENTIFIER ::= { enterprises 12630 }
netsAG                            OBJECT IDENTIFIER ::= { enterprises 12631 }
objektManagement                  OBJECT IDENTIFIER ::= { enterprises 12632 }
oceanbayInternetServices          OBJECT IDENTIFIER ::= { enterprises 12633 }
picmg                             OBJECT IDENTIFIER ::= { enterprises 12634 }
redsonic                          OBJECT IDENTIFIER ::= { enterprises 12635 }
scrippsCollege                    OBJECT IDENTIFIER ::= { enterprises 12636 }
shazamEntertainments              OBJECT IDENTIFIER ::= { enterprises 12637 }
siennax                           OBJECT IDENTIFIER ::= { enterprises 12638 }
supercable                        OBJECT IDENTIFIER ::= { enterprises 12639 }
theHoustonHarrisCountyImmunizationRegistry OBJECT IDENTIFIER ::= { enterprises 12640 }
tribunalREGIONALDOTRABALHODa10    OBJECT IDENTIFIER ::= { enterprises 12641 }
universityOfSouthernMississippi   OBJECT IDENTIFIER ::= { enterprises 12642 }
utiSystemsSA                      OBJECT IDENTIFIER ::= { enterprises 12643 }
visaa                             OBJECT IDENTIFIER ::= { enterprises 12644 }
vodafoneInformationTechnologyAndTechnologyManagement OBJECT IDENTIFIER ::= { enterprises 12645 }
widebandCorporation               OBJECT IDENTIFIER ::= { enterprises 12646 }
luleaUniversityOfTechnology       OBJECT IDENTIFIER ::= { enterprises 12647 }
systekInformationTechnology       OBJECT IDENTIFIER ::= { enterprises 12648 }
utforsAB                          OBJECT IDENTIFIER ::= { enterprises 12649 }
administrativeManagementGroup     OBJECT IDENTIFIER ::= { enterprises 12650 }
alaskaDepartmentOfLabor           OBJECT IDENTIFIER ::= { enterprises 12651 }
aminor                            OBJECT IDENTIFIER ::= { enterprises 12652 }
armitel                           OBJECT IDENTIFIER ::= { enterprises 12653 }
athSystem                         OBJECT IDENTIFIER ::= { enterprises 12654 }
authentidateInternationalAG       OBJECT IDENTIFIER ::= { enterprises 12655 }
avestPlc                          OBJECT IDENTIFIER ::= { enterprises 12656 }
birm                              OBJECT IDENTIFIER ::= { enterprises 12657 }
blueStarSustainableTechnologies   OBJECT IDENTIFIER ::= { enterprises 12658 }
brazierAndWelch                   OBJECT IDENTIFIER ::= { enterprises 12659 }
cacheware                         OBJECT IDENTIFIER ::= { enterprises 12660 }
carolineChisholmCatholicCollege   OBJECT IDENTIFIER ::= { enterprises 12661 }
chm                               OBJECT IDENTIFIER ::= { enterprises 12662 }
docfi                             OBJECT IDENTIFIER ::= { enterprises 12663 }
dotcall                           OBJECT IDENTIFIER ::= { enterprises 12664 }
enfotec                           OBJECT IDENTIFIER ::= { enterprises 12665 }
etagon                            OBJECT IDENTIFIER ::= { enterprises 12666 }
etere                             OBJECT IDENTIFIER ::= { enterprises 12667 }
garudaNetworks                    OBJECT IDENTIFIER ::= { enterprises 12668 }
hanenkampcom                      OBJECT IDENTIFIER ::= { enterprises 12669 }
indigoDevelopmentCorp             OBJECT IDENTIFIER ::= { enterprises 12670 }
institutFuerSystemManagement      OBJECT IDENTIFIER ::= { enterprises 12671 }
ismobileAB                        OBJECT IDENTIFIER ::= { enterprises 12672 }
itelcoCommunications              OBJECT IDENTIFIER ::= { enterprises 12673 }
kaonInteractive                   OBJECT IDENTIFIER ::= { enterprises 12674 }
linuxUnlimited                    OBJECT IDENTIFIER ::= { enterprises 12675 }
logical                           OBJECT IDENTIFIER ::= { enterprises 12676 }
mackeeg                           OBJECT IDENTIFIER ::= { enterprises 12677 }
nankaiUniversityChuangyuanInformationTechnologiesCo OBJECT IDENTIFIER ::= { enterprises 12678 }
nextfuture                        OBJECT IDENTIFIER ::= { enterprises 12679 }
objectiveDynamics                 OBJECT IDENTIFIER ::= { enterprises 12680 }
parkerAbexNWL                     OBJECT IDENTIFIER ::= { enterprises 12681 }
pcInfoSolutions                   OBJECT IDENTIFIER ::= { enterprises 12682 }
precache                          OBJECT IDENTIFIER ::= { enterprises 12683 }
quantumSolutions                  OBJECT IDENTIFIER ::= { enterprises 12684 }
scsEngineers                      OBJECT IDENTIFIER ::= { enterprises 12685 }
sds                               OBJECT IDENTIFIER ::= { enterprises 12686 }
siliconlogic                      OBJECT IDENTIFIER ::= { enterprises 12687 }
sohucom                           OBJECT IDENTIFIER ::= { enterprises 12688 }
superonlineINTERNATIONALONLINEINFORMATIONANDCOMMUNICATIONSERVICE OBJECT IDENTIFIER ::= { enterprises 12689 }
technologyLeaders                 OBJECT IDENTIFIER ::= { enterprises 12690 }
terilogyCo                        OBJECT IDENTIFIER ::= { enterprises 12691 }
think4youITServices               OBJECT IDENTIFIER ::= { enterprises 12692 }
tikomTirolKommunikation           OBJECT IDENTIFIER ::= { enterprises 12693 }
universittDEMARNELAVALL           OBJECT IDENTIFIER ::= { enterprises 12694 }
vsVisionSystems                   OBJECT IDENTIFIER ::= { enterprises 12695 }
xavierCollege                     OBJECT IDENTIFIER ::= { enterprises 12696 }
younghomecom                      OBJECT IDENTIFIER ::= { enterprises 12697 }
afranetCo                         OBJECT IDENTIFIER ::= { enterprises 12698 }
moyCorporation                    OBJECT IDENTIFIER ::= { enterprises 12699 }
uncHealthCare                     OBJECT IDENTIFIER ::= { enterprises 12700 }
tuxnology                         OBJECT IDENTIFIER ::= { enterprises 12701 }
solutions                         OBJECT IDENTIFIER ::= { enterprises 12702 }
acelet                            OBJECT IDENTIFIER ::= { enterprises 12703 }
alltelCorporation                 OBJECT IDENTIFIER ::= { enterprises 12704 }
baxGlobal                         OBJECT IDENTIFIER ::= { enterprises 12705 }
byterage                          OBJECT IDENTIFIER ::= { enterprises 12706 }
connectSystems                    OBJECT IDENTIFIER ::= { enterprises 12707 }
cyberlancetCorporation            OBJECT IDENTIFIER ::= { enterprises 12708 }
davies                            OBJECT IDENTIFIER ::= { enterprises 12709 }
dedicatedHostingServices          OBJECT IDENTIFIER ::= { enterprises 12710 }
experianLimited                   OBJECT IDENTIFIER ::= { enterprises 12711 }
fourCornersTelecommunicationsCorp OBJECT IDENTIFIER ::= { enterprises 12712 }
highspeedSurfing                  OBJECT IDENTIFIER ::= { enterprises 12713 }
ikosaeder                         OBJECT IDENTIFIER ::= { enterprises 12714 }
indianInstituteOfTechnology       OBJECT IDENTIFIER ::= { enterprises 12715 }
infologigruppenNorrAB             OBJECT IDENTIFIER ::= { enterprises 12716 }
intersan                          OBJECT IDENTIFIER ::= { enterprises 12717 }
mathematischesInstitut            OBJECT IDENTIFIER ::= { enterprises 12718 }
openSoftwareServices              OBJECT IDENTIFIER ::= { enterprises 12719 }
reliantResources                  OBJECT IDENTIFIER ::= { enterprises 12720 }
renditionNetworks                 OBJECT IDENTIFIER ::= { enterprises 12721 }
riteAidCorporation                OBJECT IDENTIFIER ::= { enterprises 12722 }
seisint                           OBJECT IDENTIFIER ::= { enterprises 12723 }
sensinovaAB                       OBJECT IDENTIFIER ::= { enterprises 12724 }
socialServicesAgency              OBJECT IDENTIFIER ::= { enterprises 12725 }
sudoesteServi                     OBJECT IDENTIFIER ::= { enterprises 12726 }
superviseNetwork                  OBJECT IDENTIFIER ::= { enterprises 12727 }
syswill                           OBJECT IDENTIFIER ::= { enterprises 12728 }
targit                            OBJECT IDENTIFIER ::= { enterprises 12729 }
tecsysDevelopment                 OBJECT IDENTIFIER ::= { enterprises 12730 }
utiSystemsSA2                     OBJECT IDENTIFIER ::= { enterprises 12731 }
voipGroup                         OBJECT IDENTIFIER ::= { enterprises 12732 }
wildpackets                       OBJECT IDENTIFIER ::= { enterprises 12733 }
northropGrummanInformationTechnology OBJECT IDENTIFIER ::= { enterprises 12734 }
vfspih                            OBJECT IDENTIFIER ::= { enterprises 12735 }
eloAndMahoutAndCo                 OBJECT IDENTIFIER ::= { enterprises 12736 }
algenibSoftware                   OBJECT IDENTIFIER ::= { enterprises 12737 }
bmwOfNorthAmerica                 OBJECT IDENTIFIER ::= { enterprises 12738 }
dgstarCo                          OBJECT IDENTIFIER ::= { enterprises 12739 }
equallogic                        OBJECT IDENTIFIER ::= { enterprises 12740 }
ergointegrationAS                 OBJECT IDENTIFIER ::= { enterprises 12741 }
homeconcept                       OBJECT IDENTIFIER ::= { enterprises 12742 }
integratedServiceLab              OBJECT IDENTIFIER ::= { enterprises 12743 }
nakisa                            OBJECT IDENTIFIER ::= { enterprises 12744 }
nordiskSpr                        OBJECT IDENTIFIER ::= { enterprises 12745 }
spinozaTechnology                 OBJECT IDENTIFIER ::= { enterprises 12746 }
teamsoft                          OBJECT IDENTIFIER ::= { enterprises 12747 }
telenorBusinessSolutionsAS        OBJECT IDENTIFIER ::= { enterprises 12748 }
utaTelekomAG                      OBJECT IDENTIFIER ::= { enterprises 12749 }
xi2                               OBJECT IDENTIFIER ::= { enterprises 12750 }
eChiceros                         OBJECT IDENTIFIER ::= { enterprises 12751 }
actaTechnology                    OBJECT IDENTIFIER ::= { enterprises 12752 }
biomedicalInformaticsLaboratory   OBJECT IDENTIFIER ::= { enterprises 12753 }
bturtle                           OBJECT IDENTIFIER ::= { enterprises 12754 }
cup2000Spa                        OBJECT IDENTIFIER ::= { enterprises 12755 }
deltaNetworks                     OBJECT IDENTIFIER ::= { enterprises 12756 }
ecubenetcom                       OBJECT IDENTIFIER ::= { enterprises 12757 }
expetTechnologies                 OBJECT IDENTIFIER ::= { enterprises 12758 }
garbanIntercapital                OBJECT IDENTIFIER ::= { enterprises 12759 }
h00org                            OBJECT IDENTIFIER ::= { enterprises 12760 }
hipbone                           OBJECT IDENTIFIER ::= { enterprises 12761 }
impacctTechnologyCorp             OBJECT IDENTIFIER ::= { enterprises 12762 }
iskSystems                        OBJECT IDENTIFIER ::= { enterprises 12763 }
mediaocean                        OBJECT IDENTIFIER ::= { enterprises 12764 }
minteraCorp                       OBJECT IDENTIFIER ::= { enterprises 12765 }
mobixellNetworks                  OBJECT IDENTIFIER ::= { enterprises 12766 }
nationalComputerHelpdesk          OBJECT IDENTIFIER ::= { enterprises 12767 }
navisite                          OBJECT IDENTIFIER ::= { enterprises 12768 }
netvigatorcom                     OBJECT IDENTIFIER ::= { enterprises 12769 }
nyttabAbSurfNet                   OBJECT IDENTIFIER ::= { enterprises 12770 }
palfrader                         OBJECT IDENTIFIER ::= { enterprises 12771 }
pzuZycieSA                        OBJECT IDENTIFIER ::= { enterprises 12772 }
resourceCenter                    OBJECT IDENTIFIER ::= { enterprises 12773 }
sengent                           OBJECT IDENTIFIER ::= { enterprises 12774 }
shironSatelliteCommunications     OBJECT IDENTIFIER ::= { enterprises 12775 }
theBoxIT                          OBJECT IDENTIFIER ::= { enterprises 12776 }
tngTheNetGeneration               OBJECT IDENTIFIER ::= { enterprises 12777 }
trantech                          OBJECT IDENTIFIER ::= { enterprises 12778 }
universityOfVermont               OBJECT IDENTIFIER ::= { enterprises 12779 }
volktekCorporation                OBJECT IDENTIFIER ::= { enterprises 12780 }
progenyLinuxSystems               OBJECT IDENTIFIER ::= { enterprises 12781 }
rostOberndoerferConsultingGbR     OBJECT IDENTIFIER ::= { enterprises 12782 }
universityOfMaineSystem           OBJECT IDENTIFIER ::= { enterprises 12783 }
teamwareGroupAB                   OBJECT IDENTIFIER ::= { enterprises 12784 }
amacis                            OBJECT IDENTIFIER ::= { enterprises 12785 }
automatos                         OBJECT IDENTIFIER ::= { enterprises 12786 }
axxessanywhere                    OBJECT IDENTIFIER ::= { enterprises 12787 }
bladelogic                        OBJECT IDENTIFIER ::= { enterprises 12788 }
centreForIntegratedComputerSystemsResearch OBJECT IDENTIFIER ::= { enterprises 12789 }
ceskyTELECOMAsImaginetOz          OBJECT IDENTIFIER ::= { enterprises 12790 }
dataAndControlSystems             OBJECT IDENTIFIER ::= { enterprises 12791 }
embarcaderoTechnologies           OBJECT IDENTIFIER ::= { enterprises 12792 }
eurem                             OBJECT IDENTIFIER ::= { enterprises 12793 }
frank                             OBJECT IDENTIFIER ::= { enterprises 12794 }
hccHobbynet                       OBJECT IDENTIFIER ::= { enterprises 12795 }
iOSoftware                        OBJECT IDENTIFIER ::= { enterprises 12796 }
interactivePayerNetwork           OBJECT IDENTIFIER ::= { enterprises 12797 }
internetKayttajatIkuisestiIKIRy   OBJECT IDENTIFIER ::= { enterprises 12798 }
ipv6ResearchAndDevelopment        OBJECT IDENTIFIER ::= { enterprises 12799 }
iqdoq                             OBJECT IDENTIFIER ::= { enterprises 12800 }
linuxmagic                        OBJECT IDENTIFIER ::= { enterprises 12801 }
mathcomSolutions                  OBJECT IDENTIFIER ::= { enterprises 12802 }
multitaskConsultoria              OBJECT IDENTIFIER ::= { enterprises 12803 }
nationalLibraryOfAustralia        OBJECT IDENTIFIER ::= { enterprises 12804 }
notnetWebhosting                  OBJECT IDENTIFIER ::= { enterprises 12805 }
peterStamfest                     OBJECT IDENTIFIER ::= { enterprises 12806 }
rabbitSemiconductor               OBJECT IDENTIFIER ::= { enterprises 12807 }
s2ioTechnologiesCorp              OBJECT IDENTIFIER ::= { enterprises 12808 }
sanDiegoHighSchool                OBJECT IDENTIFIER ::= { enterprises 12809 }
saratovStateUniversity            OBJECT IDENTIFIER ::= { enterprises 12810 }
satservice                        OBJECT IDENTIFIER ::= { enterprises 12811 }
securepipe                        OBJECT IDENTIFIER ::= { enterprises 12812 }
speedwiseTechnologies             OBJECT IDENTIFIER ::= { enterprises 12813 }
staatlicheStudienakademieLeipzig  OBJECT IDENTIFIER ::= { enterprises 12814 }
terraspring                       OBJECT IDENTIFIER ::= { enterprises 12815 }
universit4                        OBJECT IDENTIFIER ::= { enterprises 12816 }
zWorld                            OBJECT IDENTIFIER ::= { enterprises 12817 }
theKeyCentreForHumanFactorsAndAppliedCognitivePsychology OBJECT IDENTIFIER ::= { enterprises 12818 }
banqueGeneraleDuLuxembourg        OBJECT IDENTIFIER ::= { enterprises 12819 }
electrumInformationTechnologyCo   OBJECT IDENTIFIER ::= { enterprises 12820 }
ePieEntertainmentAndTechnologyCorporation OBJECT IDENTIFIER ::= { enterprises 12821 }
icu                               OBJECT IDENTIFIER ::= { enterprises 12822 }
advanceMultimediaInternetTechnology OBJECT IDENTIFIER ::= { enterprises 12823 }
andtek                            OBJECT IDENTIFIER ::= { enterprises 12824 }
atcInformationServices            OBJECT IDENTIFIER ::= { enterprises 12825 }
axlPerformanceSolutions           OBJECT IDENTIFIER ::= { enterprises 12826 }
barcoviewLLC                      OBJECT IDENTIFIER ::= { enterprises 12827 }
blueHeronBiotechnology            OBJECT IDENTIFIER ::= { enterprises 12828 }
bradyMotorSports                  OBJECT IDENTIFIER ::= { enterprises 12829 }
centralFloridaMain                OBJECT IDENTIFIER ::= { enterprises 12830 }
codemark                          OBJECT IDENTIFIER ::= { enterprises 12831 }
councilOFEUROPE                   OBJECT IDENTIFIER ::= { enterprises 12832 }
covansys                          OBJECT IDENTIFIER ::= { enterprises 12833 }
cpe                               OBJECT IDENTIFIER ::= { enterprises 12834 }
digitrustCertificadoraNotarialSA  OBJECT IDENTIFIER ::= { enterprises 12835 }
eAdvies                           OBJECT IDENTIFIER ::= { enterprises 12836 }
polytech                          OBJECT IDENTIFIER ::= { enterprises 12837 }
exisSrl                           OBJECT IDENTIFIER ::= { enterprises 12838 }
germanGutierrez                   OBJECT IDENTIFIER ::= { enterprises 12839 }
griffinPlazaPartners              OBJECT IDENTIFIER ::= { enterprises 12840 }
interactiveTKO                    OBJECT IDENTIFIER ::= { enterprises 12841 }
mediso                            OBJECT IDENTIFIER ::= { enterprises 12842 }
miptelecom                        OBJECT IDENTIFIER ::= { enterprises 12843 }
northernMichiganUniversity        OBJECT IDENTIFIER ::= { enterprises 12844 }
oakLawnSchoolDistrict229          OBJECT IDENTIFIER ::= { enterprises 12845 }
objectcode                        OBJECT IDENTIFIER ::= { enterprises 12846 }
orinconCorporation                OBJECT IDENTIFIER ::= { enterprises 12847 }
saddlebackCollege                 OBJECT IDENTIFIER ::= { enterprises 12848 }
skyrixSoftwareAG                  OBJECT IDENTIFIER ::= { enterprises 12849 }
smartTechConsulting               OBJECT IDENTIFIER ::= { enterprises 12850 }
syncopeCommunicationSystems       OBJECT IDENTIFIER ::= { enterprises 12851 }
syspak                            OBJECT IDENTIFIER ::= { enterprises 12852 }
technicalToysLimited              OBJECT IDENTIFIER ::= { enterprises 12853 }
tellion                           OBJECT IDENTIFIER ::= { enterprises 12854 }
vastwebTechnology                 OBJECT IDENTIFIER ::= { enterprises 12855 }
vergeNetworks                     OBJECT IDENTIFIER ::= { enterprises 12856 }
williamsCollege                   OBJECT IDENTIFIER ::= { enterprises 12857 }
enetrex                           OBJECT IDENTIFIER ::= { enterprises 12858 }
highwayru                         OBJECT IDENTIFIER ::= { enterprises 12859 }
zaryba                            OBJECT IDENTIFIER ::= { enterprises 12860 }
bayerischeBeamtenVersicherungen   OBJECT IDENTIFIER ::= { enterprises 12861 }
neefLAPPCOM                       OBJECT IDENTIFIER ::= { enterprises 12862 }
airlinkTechnology                 OBJECT IDENTIFIER ::= { enterprises 12863 }
incogen                           OBJECT IDENTIFIER ::= { enterprises 12864 }
aminGroup                         OBJECT IDENTIFIER ::= { enterprises 12865 }
cardengine                        OBJECT IDENTIFIER ::= { enterprises 12866 }
cedarPointCommunications2         OBJECT IDENTIFIER ::= { enterprises 12867 }
cetTechnologiesPte                OBJECT IDENTIFIER ::= { enterprises 12868 }
codentNetworks                    OBJECT IDENTIFIER ::= { enterprises 12869 }
danlabElectronicsAS               OBJECT IDENTIFIER ::= { enterprises 12870 }
dieNetzwerker                     OBJECT IDENTIFIER ::= { enterprises 12871 }
dteEnergy                         OBJECT IDENTIFIER ::= { enterprises 12872 }
eccSa                             OBJECT IDENTIFIER ::= { enterprises 12873 }
efmNetworks                       OBJECT IDENTIFIER ::= { enterprises 12874 }
expershare                        OBJECT IDENTIFIER ::= { enterprises 12875 }
fokkerSpace                       OBJECT IDENTIFIER ::= { enterprises 12876 }
fortis                            OBJECT IDENTIFIER ::= { enterprises 12877 }
griffinNetworkConsulting          OBJECT IDENTIFIER ::= { enterprises 12878 }
idntIntegratedDigitalNetworkTechnologies OBJECT IDENTIFIER ::= { enterprises 12879 }
kiwiInteraktiveMedienGmbh         OBJECT IDENTIFIER ::= { enterprises 12880 }
knowgeeks                         OBJECT IDENTIFIER ::= { enterprises 12881 }
lgcWireless                       OBJECT IDENTIFIER ::= { enterprises 12882 }
martinssonInformationssystem      OBJECT IDENTIFIER ::= { enterprises 12883 }
moodyBibleInstitute               OBJECT IDENTIFIER ::= { enterprises 12884 }
myarticCommunities                OBJECT IDENTIFIER ::= { enterprises 12885 }
nationalTechnicalSystems          OBJECT IDENTIFIER ::= { enterprises 12886 }
netplexAB                         OBJECT IDENTIFIER ::= { enterprises 12887 }
prokomBilgisayarVeDanismanlikHizmetleriSanVeTic OBJECT IDENTIFIER ::= { enterprises 12888 }
ptc                               OBJECT IDENTIFIER ::= { enterprises 12889 }
shorty                            OBJECT IDENTIFIER ::= { enterprises 12890 }
syndicatInterhospitalierLimousin  OBJECT IDENTIFIER ::= { enterprises 12891 }
universityOfPatras                OBJECT IDENTIFIER ::= { enterprises 12892 }
visiowaveSA                       OBJECT IDENTIFIER ::= { enterprises 12893 }
wmode                             OBJECT IDENTIFIER ::= { enterprises 12894 }
xsetup                            OBJECT IDENTIFIER ::= { enterprises 12895 }
xtriaHealthcare                   OBJECT IDENTIFIER ::= { enterprises 12896 }
zilog                             OBJECT IDENTIFIER ::= { enterprises 12897 }
sinterConsulting                  OBJECT IDENTIFIER ::= { enterprises 12898 }
visogentTechnologies              OBJECT IDENTIFIER ::= { enterprises 12899 }
itec                              OBJECT IDENTIFIER ::= { enterprises 12900 }
instituteOfSoftware               OBJECT IDENTIFIER ::= { enterprises 12901 }
advancedNetworkTechnologyLaboratoriesPte OBJECT IDENTIFIER ::= { enterprises 12902 }
bayshoreNetworks                  OBJECT IDENTIFIER ::= { enterprises 12903 }
evault                            OBJECT IDENTIFIER ::= { enterprises 12904 }
indianInstituteOfTechnologyGuwahati OBJECT IDENTIFIER ::= { enterprises 12905 }
japc                              OBJECT IDENTIFIER ::= { enterprises 12906 }
kansaiBroadbandPlanningCorp       OBJECT IDENTIFIER ::= { enterprises 12907 }
litechSystemsDesign               OBJECT IDENTIFIER ::= { enterprises 12908 }
machineVisionProducts             OBJECT IDENTIFIER ::= { enterprises 12909 }
nextElement                       OBJECT IDENTIFIER ::= { enterprises 12910 }
oceNV                             OBJECT IDENTIFIER ::= { enterprises 12911 }
peerpro                           OBJECT IDENTIFIER ::= { enterprises 12912 }
proceraNetworks                   OBJECT IDENTIFIER ::= { enterprises 12913 }
productionRobotsEngineering       OBJECT IDENTIFIER ::= { enterprises 12914 }
radioFreeEuropeRadioLiberty       OBJECT IDENTIFIER ::= { enterprises 12915 }
rocklandCommunityCollege          OBJECT IDENTIFIER ::= { enterprises 12916 }
saberELazer                       OBJECT IDENTIFIER ::= { enterprises 12917 }
tdiTransistorDevices              OBJECT IDENTIFIER ::= { enterprises 12918 }
xaviTechnologiesCorporation       OBJECT IDENTIFIER ::= { enterprises 12919 }
xteamSoftwareCo                   OBJECT IDENTIFIER ::= { enterprises 12920 }
yeamanAssociates                  OBJECT IDENTIFIER ::= { enterprises 12921 }
yourVoiceSpA                      OBJECT IDENTIFIER ::= { enterprises 12922 }
kigyoZanmaiCorp                   OBJECT IDENTIFIER ::= { enterprises 12923 }
klonJaworAssociation              OBJECT IDENTIFIER ::= { enterprises 12924 }
threePARData2                     OBJECT IDENTIFIER ::= { enterprises 12925 }
anheuserBusch                     OBJECT IDENTIFIER ::= { enterprises 12926 }
axiom                             OBJECT IDENTIFIER ::= { enterprises 12927 }
clarusSystems                     OBJECT IDENTIFIER ::= { enterprises 12928 }
cliffBerg                         OBJECT IDENTIFIER ::= { enterprises 12929 }
cvsTravelhostInternationalPty     OBJECT IDENTIFIER ::= { enterprises 12930 }
dreefs                            OBJECT IDENTIFIER ::= { enterprises 12931 }
fesd                              OBJECT IDENTIFIER ::= { enterprises 12932 }
globalOrchestra                   OBJECT IDENTIFIER ::= { enterprises 12933 }
hunkelerAG                        OBJECT IDENTIFIER ::= { enterprises 12934 }
i3MicroTechnologyAb               OBJECT IDENTIFIER ::= { enterprises 12935 }
incertSoftwareCorporation         OBJECT IDENTIFIER ::= { enterprises 12936 }
infradigSystems                   OBJECT IDENTIFIER ::= { enterprises 12937 }
innovativeTechnologySolutions     OBJECT IDENTIFIER ::= { enterprises 12938 }
modus                             OBJECT IDENTIFIER ::= { enterprises 12939 }
pedestalNetworks                  OBJECT IDENTIFIER ::= { enterprises 12940 }
pressData                         OBJECT IDENTIFIER ::= { enterprises 12941 }
sanshaELECTRICMFGCO               OBJECT IDENTIFIER ::= { enterprises 12942 }
sengena                           OBJECT IDENTIFIER ::= { enterprises 12943 }
sockeyeNetworks                   OBJECT IDENTIFIER ::= { enterprises 12944 }
softproject                       OBJECT IDENTIFIER ::= { enterprises 12945 }
stateServicesCommission           OBJECT IDENTIFIER ::= { enterprises 12946 }
synthesysSecureTechnologies       OBJECT IDENTIFIER ::= { enterprises 12947 }
syredDataSystems                  OBJECT IDENTIFIER ::= { enterprises 12948 }
tOnlineFrance                     OBJECT IDENTIFIER ::= { enterprises 12949 }
venngo                            OBJECT IDENTIFIER ::= { enterprises 12950 }
verizonWireless                   OBJECT IDENTIFIER ::= { enterprises 12951 }
warpfactor                        OBJECT IDENTIFIER ::= { enterprises 12952 }
xandrosCorporation                OBJECT IDENTIFIER ::= { enterprises 12953 }
wmDataSDCAS                       OBJECT IDENTIFIER ::= { enterprises 12954 }
metareteSrl                       OBJECT IDENTIFIER ::= { enterprises 12955 }
aarhusUniversitet                 OBJECT IDENTIFIER ::= { enterprises 12956 }
blueMARS                          OBJECT IDENTIFIER ::= { enterprises 12957 }
questerra                         OBJECT IDENTIFIER ::= { enterprises 12958 }
amProfessionalServices            OBJECT IDENTIFIER ::= { enterprises 12959 }
andelinaCorporation               OBJECT IDENTIFIER ::= { enterprises 12960 }
andrewHewettConsulting            OBJECT IDENTIFIER ::= { enterprises 12961 }
decru                             OBJECT IDENTIFIER ::= { enterprises 12962 }
dimonsoft                         OBJECT IDENTIFIER ::= { enterprises 12963 }
ftlightnet                        OBJECT IDENTIFIER ::= { enterprises 12964 }
newMediaDataMarketing             OBJECT IDENTIFIER ::= { enterprises 12965 }
nextGenerationSystems             OBJECT IDENTIFIER ::= { enterprises 12966 }
petrobrasPetroleoBrasileiroSA     OBJECT IDENTIFIER ::= { enterprises 12967 }
stelvio                           OBJECT IDENTIFIER ::= { enterprises 12968 }
theRockefellerUniversity          OBJECT IDENTIFIER ::= { enterprises 12969 }
urbanDevelopmentCo                OBJECT IDENTIFIER ::= { enterprises 12970 }
bigdomcom                         OBJECT IDENTIFIER ::= { enterprises 12971 }
callionElectronicsCo              OBJECT IDENTIFIER ::= { enterprises 12972 }
wuhanPublicInformationCo          OBJECT IDENTIFIER ::= { enterprises 12973 }
barrigoncom                       OBJECT IDENTIFIER ::= { enterprises 12974 }
brainaid                          OBJECT IDENTIFIER ::= { enterprises 12975 }
cowlan                            OBJECT IDENTIFIER ::= { enterprises 12976 }
levelII                           OBJECT IDENTIFIER ::= { enterprises 12977 }
michaelFrommeEDVBeratung          OBJECT IDENTIFIER ::= { enterprises 12978 }
optimacyCorporation               OBJECT IDENTIFIER ::= { enterprises 12979 }
personCo                          OBJECT IDENTIFIER ::= { enterprises 12980 }
rotterdamCS                       OBJECT IDENTIFIER ::= { enterprises 12981 }
synergyInternational              OBJECT IDENTIFIER ::= { enterprises 12982 }
tbsINTERNET                       OBJECT IDENTIFIER ::= { enterprises 12983 }
terraplaySystemsAB                OBJECT IDENTIFIER ::= { enterprises 12984 }
universityOfStAndrews             OBJECT IDENTIFIER ::= { enterprises 12985 }
verlagsgruppeStraubingerTagblattLandshuterZeitung OBJECT IDENTIFIER ::= { enterprises 12986 }
vineyardnet                       OBJECT IDENTIFIER ::= { enterprises 12987 }
vistormLimited                    OBJECT IDENTIFIER ::= { enterprises 12988 }
xip                               OBJECT IDENTIFIER ::= { enterprises 12989 }
starCommunicationNetworkTechnologyCo OBJECT IDENTIFIER ::= { enterprises 12990 }
californiaCollegeOfArtsAndCrafts  OBJECT IDENTIFIER ::= { enterprises 12991 }
tAndaSYSTEME                      OBJECT IDENTIFIER ::= { enterprises 12992 }
weitlandtCommunication            OBJECT IDENTIFIER ::= { enterprises 12993 }
abisoft                           OBJECT IDENTIFIER ::= { enterprises 12994 }
accetNetwork                      OBJECT IDENTIFIER ::= { enterprises 12995 }
adconsysAG                        OBJECT IDENTIFIER ::= { enterprises 12996 }
advancedBiometrics                OBJECT IDENTIFIER ::= { enterprises 12997 }
agileSoftware                     OBJECT IDENTIFIER ::= { enterprises 12998 }
altiris                           OBJECT IDENTIFIER ::= { enterprises 12999 }
angliaPolytechnicUniversity       OBJECT IDENTIFIER ::= { enterprises 13000 }
anuvioTechnologies                OBJECT IDENTIFIER ::= { enterprises 13001 }
augsburgCollege                   OBJECT IDENTIFIER ::= { enterprises 13002 }
bancaIMI                          OBJECT IDENTIFIER ::= { enterprises 13003 }
beamnet                           OBJECT IDENTIFIER ::= { enterprises 13004 }
bitrage                           OBJECT IDENTIFIER ::= { enterprises 13005 }
caeTechnikSchmitt                 OBJECT IDENTIFIER ::= { enterprises 13006 }
californiaRegionalIntranet        OBJECT IDENTIFIER ::= { enterprises 13007 }
canprintCommunicationsPty         OBJECT IDENTIFIER ::= { enterprises 13008 }
coma                              OBJECT IDENTIFIER ::= { enterprises 13009 }
computerBusinessSciences          OBJECT IDENTIFIER ::= { enterprises 13010 }
consejoGeneralDelNotariado        OBJECT IDENTIFIER ::= { enterprises 13011 }
cramerSystemsLimited              OBJECT IDENTIFIER ::= { enterprises 13012 }
denisowskiConsulting              OBJECT IDENTIFIER ::= { enterprises 13013 }
dreamcodeSoftware                 OBJECT IDENTIFIER ::= { enterprises 13014 }
easternElectronicsCo              OBJECT IDENTIFIER ::= { enterprises 13015 }
emagiccom                         OBJECT IDENTIFIER ::= { enterprises 13016 }
eSolutionist                      OBJECT IDENTIFIER ::= { enterprises 13017 }
ethZurich                         OBJECT IDENTIFIER ::= { enterprises 13018 }
etsi                              OBJECT IDENTIFIER ::= { enterprises 13019 }
floridaInternationalUniversity    OBJECT IDENTIFIER ::= { enterprises 13020 }
halifaxCetelemCredit              OBJECT IDENTIFIER ::= { enterprises 13021 }
handheldsorg                      OBJECT IDENTIFIER ::= { enterprises 13022 }
hub2b                             OBJECT IDENTIFIER ::= { enterprises 13023 }
imagisticsInternational           OBJECT IDENTIFIER ::= { enterprises 13024 }
infernoLabs                       OBJECT IDENTIFIER ::= { enterprises 13025 }
itIntergroupApS                   OBJECT IDENTIFIER ::= { enterprises 13026 }
ixosSoftwareAG                    OBJECT IDENTIFIER ::= { enterprises 13027 }
kuokoaNetworks                    OBJECT IDENTIFIER ::= { enterprises 13028 }
managedServicePartnersInternational OBJECT IDENTIFIER ::= { enterprises 13029 }
monitor724ServicesLimited         OBJECT IDENTIFIER ::= { enterprises 13030 }
neix                              OBJECT IDENTIFIER ::= { enterprises 13031 }
reachTechnologies                 OBJECT IDENTIFIER ::= { enterprises 13032 }
shockunitProductions              OBJECT IDENTIFIER ::= { enterprises 13033 }
softnetSystems                    OBJECT IDENTIFIER ::= { enterprises 13034 }
sonangol                          OBJECT IDENTIFIER ::= { enterprises 13035 }
stradient                         OBJECT IDENTIFIER ::= { enterprises 13036 }
subnetworxCorporation             OBJECT IDENTIFIER ::= { enterprises 13037 }
teleGreenland                     OBJECT IDENTIFIER ::= { enterprises 13038 }
tennesseeTechnologicalUniversity  OBJECT IDENTIFIER ::= { enterprises 13039 }
theHordeProject                   OBJECT IDENTIFIER ::= { enterprises 13040 }
thinkDynamics                     OBJECT IDENTIFIER ::= { enterprises 13041 }
trustCompanyOfAmerica             OBJECT IDENTIFIER ::= { enterprises 13042 }
universityOfWisconsinRiverFalls   OBJECT IDENTIFIER ::= { enterprises 13043 }
unternehmensberatungRahn          OBJECT IDENTIFIER ::= { enterprises 13044 }
uptimeDevices                     OBJECT IDENTIFIER ::= { enterprises 13045 }
visionshare                       OBJECT IDENTIFIER ::= { enterprises 13046 }
welliverEnterprises               OBJECT IDENTIFIER ::= { enterprises 13047 }
xorba                             OBJECT IDENTIFIER ::= { enterprises 13048 }
yaccLabs                          OBJECT IDENTIFIER ::= { enterprises 13049 }
ydiloAdvancedVoiceSolutionsSA     OBJECT IDENTIFIER ::= { enterprises 13050 }
metasolvSoftware                  OBJECT IDENTIFIER ::= { enterprises 13051 }
telefonbauArthurSchwabe           OBJECT IDENTIFIER ::= { enterprises 13052 }
tisSystemService                  OBJECT IDENTIFIER ::= { enterprises 13053 }
ramCorp                           OBJECT IDENTIFIER ::= { enterprises 13054 }
shanghaiJingLunTechnologiesCO     OBJECT IDENTIFIER ::= { enterprises 13055 }
taiPingLifeInsuranceCo            OBJECT IDENTIFIER ::= { enterprises 13056 }
haysDSIAFrance                    OBJECT IDENTIFIER ::= { enterprises 13057 }
nationalHockeyLeague              OBJECT IDENTIFIER ::= { enterprises 13058 }
aholdSupermercados                OBJECT IDENTIFIER ::= { enterprises 13059 }
airpathWireless                   OBJECT IDENTIFIER ::= { enterprises 13060 }
alphacSrl                         OBJECT IDENTIFIER ::= { enterprises 13061 }
ascom                             OBJECT IDENTIFIER ::= { enterprises 13062 }
cambian                           OBJECT IDENTIFIER ::= { enterprises 13063 }
claymountainSolutionsOy           OBJECT IDENTIFIER ::= { enterprises 13064 }
colomsatSA                        OBJECT IDENTIFIER ::= { enterprises 13065 }
connaughtAirServices              OBJECT IDENTIFIER ::= { enterprises 13066 }
csh                               OBJECT IDENTIFIER ::= { enterprises 13067 }
czajsoft                          OBJECT IDENTIFIER ::= { enterprises 13068 }
diveoDoBrasilTelecomLTDA          OBJECT IDENTIFIER ::= { enterprises 13069 }
druttCorporation                  OBJECT IDENTIFIER ::= { enterprises 13070 }
esds                              OBJECT IDENTIFIER ::= { enterprises 13071 }
galleryIPTelephony                OBJECT IDENTIFIER ::= { enterprises 13072 }
gate5AG                           OBJECT IDENTIFIER ::= { enterprises 13073 }
labyrinthConnections              OBJECT IDENTIFIER ::= { enterprises 13074 }
myLinuxISP                        OBJECT IDENTIFIER ::= { enterprises 13075 }
mycompany                         OBJECT IDENTIFIER ::= { enterprises 13076 }
netwolvesTechnologiesCorporation  OBJECT IDENTIFIER ::= { enterprises 13077 }
nssoft                            OBJECT IDENTIFIER ::= { enterprises 13078 }
persayLTD                         OBJECT IDENTIFIER ::= { enterprises 13079 }
persona                           OBJECT IDENTIFIER ::= { enterprises 13080 }
pretaxSystemsOy                   OBJECT IDENTIFIER ::= { enterprises 13081 }
shanghaiSunriseElectronicTechnologyCo OBJECT IDENTIFIER ::= { enterprises 13082 }
signalTechnologyCorporation       OBJECT IDENTIFIER ::= { enterprises 13083 }
sonaeDistribui                    OBJECT IDENTIFIER ::= { enterprises 13084 }
streamsec                         OBJECT IDENTIFIER ::= { enterprises 13085 }
yamagataPrefecturalGovernment     OBJECT IDENTIFIER ::= { enterprises 13086 }
vaelitGroup                       OBJECT IDENTIFIER ::= { enterprises 13087 }
adquiraEspa                       OBJECT IDENTIFIER ::= { enterprises 13088 }
aristotleUniversityOfThessaloniki OBJECT IDENTIFIER ::= { enterprises 13089 }
artifactEntertainment             OBJECT IDENTIFIER ::= { enterprises 13090 }
bethelCollegeAndSeminary          OBJECT IDENTIFIER ::= { enterprises 13091 }
cellcloudTechnologiesPvt          OBJECT IDENTIFIER ::= { enterprises 13092 }
collegeOfEducation                OBJECT IDENTIFIER ::= { enterprises 13093 }
contegoSolutionsLLC               OBJECT IDENTIFIER ::= { enterprises 13094 }
dalhousieUniversity               OBJECT IDENTIFIER ::= { enterprises 13095 }
danOfSteel                        OBJECT IDENTIFIER ::= { enterprises 13096 }
dascomTechnologyCo                OBJECT IDENTIFIER ::= { enterprises 13097 }
dpaAFXWirtschaftsnachrichten      OBJECT IDENTIFIER ::= { enterprises 13098 }
drybridgeConsulting               OBJECT IDENTIFIER ::= { enterprises 13099 }
funCommunications                 OBJECT IDENTIFIER ::= { enterprises 13100 }
getedes                           OBJECT IDENTIFIER ::= { enterprises 13101 }
hauniMaschinenbauAG               OBJECT IDENTIFIER ::= { enterprises 13102 }
ilevoAB                           OBJECT IDENTIFIER ::= { enterprises 13103 }
infraservicesCorporation          OBJECT IDENTIFIER ::= { enterprises 13104 }
ingeniumTechnology                OBJECT IDENTIFIER ::= { enterprises 13105 }
jlfNetwork                        OBJECT IDENTIFIER ::= { enterprises 13106 }
jmaticaSrl                        OBJECT IDENTIFIER ::= { enterprises 13107 }
linuxlab                          OBJECT IDENTIFIER ::= { enterprises 13108 }
liontechCo                        OBJECT IDENTIFIER ::= { enterprises 13109 }
manageable                        OBJECT IDENTIFIER ::= { enterprises 13110 }
mcgunetConsulting                 OBJECT IDENTIFIER ::= { enterprises 13111 }
mdsProteomics                     OBJECT IDENTIFIER ::= { enterprises 13112 }
mindtribe                         OBJECT IDENTIFIER ::= { enterprises 13113 }
nextraInvestmentManagementSGRSpA  OBJECT IDENTIFIER ::= { enterprises 13114 }
openConnections                   OBJECT IDENTIFIER ::= { enterprises 13115 }
pAndJSystemsSupportStation        OBJECT IDENTIFIER ::= { enterprises 13116 }
plat                              OBJECT IDENTIFIER ::= { enterprises 13117 }
pointdx                           OBJECT IDENTIFIER ::= { enterprises 13118 }
ramexArsMedica                    OBJECT IDENTIFIER ::= { enterprises 13119 }
rasilientSystems                  OBJECT IDENTIFIER ::= { enterprises 13120 }
signatronTechnologyCorporation    OBJECT IDENTIFIER ::= { enterprises 13121 }
softwareResearchAssociates        OBJECT IDENTIFIER ::= { enterprises 13122 }
starbakCommunications             OBJECT IDENTIFIER ::= { enterprises 13123 }
terraMarketing                    OBJECT IDENTIFIER ::= { enterprises 13124 }
teytel                            OBJECT IDENTIFIER ::= { enterprises 13125 }
themountain                       OBJECT IDENTIFIER ::= { enterprises 13126 }
thomasJeffersonUniversityHospital OBJECT IDENTIFIER ::= { enterprises 13127 }
universeSoftware                  OBJECT IDENTIFIER ::= { enterprises 13128 }
upmc                              OBJECT IDENTIFIER ::= { enterprises 13129 }
videoProductsGroup                OBJECT IDENTIFIER ::= { enterprises 13130 }
dePassievruchten                  OBJECT IDENTIFIER ::= { enterprises 13131 }
softingEuropeSA                   OBJECT IDENTIFIER ::= { enterprises 13132 }
michelin                          OBJECT IDENTIFIER ::= { enterprises 13133 }
founderBroadbandNetworkTechnologyCo OBJECT IDENTIFIER ::= { enterprises 13134 }
sjtek                             OBJECT IDENTIFIER ::= { enterprises 13135 }
alexsdePrivateNetwork             OBJECT IDENTIFIER ::= { enterprises 13136 }
biocareSarl                       OBJECT IDENTIFIER ::= { enterprises 13137 }
boiledFrogTradingCoOperative      OBJECT IDENTIFIER ::= { enterprises 13138 }
caribnavHoldings                  OBJECT IDENTIFIER ::= { enterprises 13139 }
clusterFileSystems                OBJECT IDENTIFIER ::= { enterprises 13140 }
fdkCOLTD                          OBJECT IDENTIFIER ::= { enterprises 13141 }
iMConsultancyPty                  OBJECT IDENTIFIER ::= { enterprises 13142 }
iAndsiSpA                         OBJECT IDENTIFIER ::= { enterprises 13143 }
jakobHattelandComputerAS          OBJECT IDENTIFIER ::= { enterprises 13144 }
klikSystems                       OBJECT IDENTIFIER ::= { enterprises 13145 }
klomp                             OBJECT IDENTIFIER ::= { enterprises 13146 }
leadflyTechnologiesCo             OBJECT IDENTIFIER ::= { enterprises 13147 }
leanlogistics                     OBJECT IDENTIFIER ::= { enterprises 13148 }
leePrinting                       OBJECT IDENTIFIER ::= { enterprises 13149 }
mAndmConsultingIntl               OBJECT IDENTIFIER ::= { enterprises 13150 }
mbConsultants                     OBJECT IDENTIFIER ::= { enterprises 13151 }
octalisSA                         OBJECT IDENTIFIER ::= { enterprises 13152 }
rfsaw                             OBJECT IDENTIFIER ::= { enterprises 13153 }
rpost                             OBJECT IDENTIFIER ::= { enterprises 13154 }
shimanek                          OBJECT IDENTIFIER ::= { enterprises 13155 }
switchpointNetworks               OBJECT IDENTIFIER ::= { enterprises 13156 }
tsinghuaUnisplendourBitwayNetworkingTechnologyCo OBJECT IDENTIFIER ::= { enterprises 13157 }
universitaetMuenster              OBJECT IDENTIFIER ::= { enterprises 13158 }
zfFriedrichshafenAG               OBJECT IDENTIFIER ::= { enterprises 13159 }
cercacomSrl                       OBJECT IDENTIFIER ::= { enterprises 13160 }
quattroSoftwareLimited            OBJECT IDENTIFIER ::= { enterprises 13161 }
softwareQualityEngineering        OBJECT IDENTIFIER ::= { enterprises 13162 }
ministryOfJustice                 OBJECT IDENTIFIER ::= { enterprises 13163 }
cybersuperstore                   OBJECT IDENTIFIER ::= { enterprises 13164 }
three8Qu                          OBJECT IDENTIFIER ::= { enterprises 13165 }
acamarSystems                     OBJECT IDENTIFIER ::= { enterprises 13166 }
oekonetMuellerAndBrandt           OBJECT IDENTIFIER ::= { enterprises 13167 }
ariesEPublishing                  OBJECT IDENTIFIER ::= { enterprises 13168 }
cAnddTechnologies                 OBJECT IDENTIFIER ::= { enterprises 13169 }
caresys                           OBJECT IDENTIFIER ::= { enterprises 13170 }
cilys                             OBJECT IDENTIFIER ::= { enterprises 13171 }
darkSideOfTheMoonSoftware         OBJECT IDENTIFIER ::= { enterprises 13172 }
dilaxIntelcom                     OBJECT IDENTIFIER ::= { enterprises 13173 }
eglinAirForceBase                 OBJECT IDENTIFIER ::= { enterprises 13174 }
eurofer                           OBJECT IDENTIFIER ::= { enterprises 13175 }
europeanBankForReconstructionAndDevelopment OBJECT IDENTIFIER ::= { enterprises 13176 }
firmaprofesional                  OBJECT IDENTIFIER ::= { enterprises 13177 }
fremontComputerCorporation        OBJECT IDENTIFIER ::= { enterprises 13178 }
internetInformationGroup          OBJECT IDENTIFIER ::= { enterprises 13179 }
jrSoftware                        OBJECT IDENTIFIER ::= { enterprises 13180 }
junotSystems                      OBJECT IDENTIFIER ::= { enterprises 13181 }
kapschTrafficComAG                OBJECT IDENTIFIER ::= { enterprises 13182 }
kevabThebasestationcompany        OBJECT IDENTIFIER ::= { enterprises 13183 }
lanscapeNetzwerkdienste           OBJECT IDENTIFIER ::= { enterprises 13184 }
laqtib                            OBJECT IDENTIFIER ::= { enterprises 13185 }
lightComputingServices            OBJECT IDENTIFIER ::= { enterprises 13186 }
mdlink                            OBJECT IDENTIFIER ::= { enterprises 13187 }
miamiUniversityLibraries          OBJECT IDENTIFIER ::= { enterprises 13188 }
mitake                            OBJECT IDENTIFIER ::= { enterprises 13189 }
northropGrummanINRIDivision       OBJECT IDENTIFIER ::= { enterprises 13190 }
oneaccess                         OBJECT IDENTIFIER ::= { enterprises 13191 }
pclinxSnc                         OBJECT IDENTIFIER ::= { enterprises 13192 }
portelco                          OBJECT IDENTIFIER ::= { enterprises 13193 }
portsite                          OBJECT IDENTIFIER ::= { enterprises 13194 }
proditec                          OBJECT IDENTIFIER ::= { enterprises 13195 }
sbs                               OBJECT IDENTIFIER ::= { enterprises 13196 }
securityCrossing                  OBJECT IDENTIFIER ::= { enterprises 13197 }
signtrust                         OBJECT IDENTIFIER ::= { enterprises 13198 }
simind                            OBJECT IDENTIFIER ::= { enterprises 13199 }
bpkPenabur                        OBJECT IDENTIFIER ::= { enterprises 13200 }
tjhInternetSP                     OBJECT IDENTIFIER ::= { enterprises 13201 }
unitedStatesAdvancedNetwork       OBJECT IDENTIFIER ::= { enterprises 13202 }
universityOfPretoria              OBJECT IDENTIFIER ::= { enterprises 13203 }
viaNETWORKSDeutschland            OBJECT IDENTIFIER ::= { enterprises 13204 }
webswimmerLLC                     OBJECT IDENTIFIER ::= { enterprises 13205 }
bsmConsulting                     OBJECT IDENTIFIER ::= { enterprises 13206 }
ntnu                              OBJECT IDENTIFIER ::= { enterprises 13207 }
argsoft                           OBJECT IDENTIFIER ::= { enterprises 13208 }
aptiloNetworksAB                  OBJECT IDENTIFIER ::= { enterprises 13209 }
armstrongGroupOfCompanies         OBJECT IDENTIFIER ::= { enterprises 13210 }
at4netINTERNETYCOMUNICACION       OBJECT IDENTIFIER ::= { enterprises 13211 }
btrade                            OBJECT IDENTIFIER ::= { enterprises 13212 }
centreTecnologicDeManresa         OBJECT IDENTIFIER ::= { enterprises 13213 }
comunitelGlobalSA                 OBJECT IDENTIFIER ::= { enterprises 13214 }
cougaar                           OBJECT IDENTIFIER ::= { enterprises 13215 }
digitalAgeDesign                  OBJECT IDENTIFIER ::= { enterprises 13216 }
fhFurtwangen                      OBJECT IDENTIFIER ::= { enterprises 13217 }
flowringTechnology                OBJECT IDENTIFIER ::= { enterprises 13218 }
gliwickieStowarzyszenieInternaut  OBJECT IDENTIFIER ::= { enterprises 13219 }
interconnectedGeneration          OBJECT IDENTIFIER ::= { enterprises 13220 }
kubotaSystems                     OBJECT IDENTIFIER ::= { enterprises 13221 }
millicomPeru                      OBJECT IDENTIFIER ::= { enterprises 13222 }
mwainCorp                         OBJECT IDENTIFIER ::= { enterprises 13223 }
netIntegrationTechnologies        OBJECT IDENTIFIER ::= { enterprises 13224 }
networkServicesGroup              OBJECT IDENTIFIER ::= { enterprises 13225 }
networkTechnologySolutions        OBJECT IDENTIFIER ::= { enterprises 13226 }
officescape                       OBJECT IDENTIFIER ::= { enterprises 13227 }
redlineTelecommunicationsSA       OBJECT IDENTIFIER ::= { enterprises 13228 }
samadPty                          OBJECT IDENTIFIER ::= { enterprises 13229 }
sanDiegoSupercomputerCenter       OBJECT IDENTIFIER ::= { enterprises 13230 }
schlumbergersemaJapan             OBJECT IDENTIFIER ::= { enterprises 13231 }
spottedowlrecipescom              OBJECT IDENTIFIER ::= { enterprises 13232 }
stephenWinnall                    OBJECT IDENTIFIER ::= { enterprises 13233 }
telpro                            OBJECT IDENTIFIER ::= { enterprises 13234 }
teralinkCommunications            OBJECT IDENTIFIER ::= { enterprises 13235 }
theBrickWarehouseCorporation      OBJECT IDENTIFIER ::= { enterprises 13236 }
usProcess                         OBJECT IDENTIFIER ::= { enterprises 13237 }
viennaUniversityOfEconomicsAndBusinessAdministration OBJECT IDENTIFIER ::= { enterprises 13238 }
vodatel                           OBJECT IDENTIFIER ::= { enterprises 13239 }
voipPty                           OBJECT IDENTIFIER ::= { enterprises 13240 }
wielandGmeiner                    OBJECT IDENTIFIER ::= { enterprises 13241 }
infocrypt                         OBJECT IDENTIFIER ::= { enterprises 13242 }
chipPC                            OBJECT IDENTIFIER ::= { enterprises 13243 }
duniyaTechnologies                OBJECT IDENTIFIER ::= { enterprises 13244 }
hst                               OBJECT IDENTIFIER ::= { enterprises 13245 }
alliente                          OBJECT IDENTIFIER ::= { enterprises 13246 }
cityOfNaantali                    OBJECT IDENTIFIER ::= { enterprises 13247 }
generalElectricPowerManagement    OBJECT IDENTIFIER ::= { enterprises 13248 }
icemTechnologies                  OBJECT IDENTIFIER ::= { enterprises 13249 }
ineco                             OBJECT IDENTIFIER ::= { enterprises 13250 }
ingenix                           OBJECT IDENTIFIER ::= { enterprises 13251 }
kodansha                          OBJECT IDENTIFIER ::= { enterprises 13252 }
kyOn                              OBJECT IDENTIFIER ::= { enterprises 13253 }
londonStockExchange               OBJECT IDENTIFIER ::= { enterprises 13254 }
netMobileAG                       OBJECT IDENTIFIER ::= { enterprises 13255 }
rabidBadgers                      OBJECT IDENTIFIER ::= { enterprises 13256 }
registradoresDeLaPropiedadYMercantilDeEspa OBJECT IDENTIFIER ::= { enterprises 13257 }
secretariaDeEducaci               OBJECT IDENTIFIER ::= { enterprises 13258 }
solutionXSoftware                 OBJECT IDENTIFIER ::= { enterprises 13259 }
studyAreaTrainingCenter           OBJECT IDENTIFIER ::= { enterprises 13260 }
tSystemsITS                       OBJECT IDENTIFIER ::= { enterprises 13261 }
zbwZentrumFuerBeruflicheWeiterbildung OBJECT IDENTIFIER ::= { enterprises 13262 }
professionalSystemsIntegration    OBJECT IDENTIFIER ::= { enterprises 13263 }
atmelGermany                      OBJECT IDENTIFIER ::= { enterprises 13264 }
atofina                           OBJECT IDENTIFIER ::= { enterprises 13265 }
c2Creation                        OBJECT IDENTIFIER ::= { enterprises 13266 }
cityOfYorkCouncil                 OBJECT IDENTIFIER ::= { enterprises 13267 }
clarkHillPLC                      OBJECT IDENTIFIER ::= { enterprises 13268 }
completeNetworkSolutions          OBJECT IDENTIFIER ::= { enterprises 13269 }
computingCenterOfNortheasternUniv OBJECT IDENTIFIER ::= { enterprises 13270 }
currentTechnologies               OBJECT IDENTIFIER ::= { enterprises 13271 }
danilomassa                       OBJECT IDENTIFIER ::= { enterprises 13272 }
designITSolutions                 OBJECT IDENTIFIER ::= { enterprises 13273 }
digitalMediaLabCorporation        OBJECT IDENTIFIER ::= { enterprises 13274 }
goldenSquarePostProduction        OBJECT IDENTIFIER ::= { enterprises 13275 }
gsta                              OBJECT IDENTIFIER ::= { enterprises 13276 }
ieee80211                         OBJECT IDENTIFIER ::= { enterprises 13277 }
inablingTechnologies              OBJECT IDENTIFIER ::= { enterprises 13278 }
intergateBrowserSystems           OBJECT IDENTIFIER ::= { enterprises 13279 }
internetExpress                   OBJECT IDENTIFIER ::= { enterprises 13280 }
ipsyn                             OBJECT IDENTIFIER ::= { enterprises 13281 }
kaparelCorporation                OBJECT IDENTIFIER ::= { enterprises 13282 }
laitilanPuhelinosuuskunta         OBJECT IDENTIFIER ::= { enterprises 13283 }
londonStockExchange2              OBJECT IDENTIFIER ::= { enterprises 13284 }
lycosFRANCE                       OBJECT IDENTIFIER ::= { enterprises 13285 }
mdmIAndC                          OBJECT IDENTIFIER ::= { enterprises 13286 }
membrainTechnologies              OBJECT IDENTIFIER ::= { enterprises 13287 }
mis                               OBJECT IDENTIFIER ::= { enterprises 13288 }
neoscaleSystems                   OBJECT IDENTIFIER ::= { enterprises 13289 }
nextsource                        OBJECT IDENTIFIER ::= { enterprises 13290 }
ogangiCorporation                 OBJECT IDENTIFIER ::= { enterprises 13291 }
oneshellInternetServices          OBJECT IDENTIFIER ::= { enterprises 13292 }
ottoInternational                 OBJECT IDENTIFIER ::= { enterprises 13293 }
ph03n1xnetDevelopment             OBJECT IDENTIFIER ::= { enterprises 13294 }
portugalmail                      OBJECT IDENTIFIER ::= { enterprises 13295 }
softintegro                       OBJECT IDENTIFIER ::= { enterprises 13296 }
solitonAssociatesLimited          OBJECT IDENTIFIER ::= { enterprises 13297 }
synerSA                           OBJECT IDENTIFIER ::= { enterprises 13298 }
syntlogo                          OBJECT IDENTIFIER ::= { enterprises 13299 }
syr                               OBJECT IDENTIFIER ::= { enterprises 13300 }
teksouthCorporation               OBJECT IDENTIFIER ::= { enterprises 13301 }
theAdvantageMediaGroup            OBJECT IDENTIFIER ::= { enterprises 13302 }
theGilletteCompany                OBJECT IDENTIFIER ::= { enterprises 13303 }
tSystemsSolutionsForResearch      OBJECT IDENTIFIER ::= { enterprises 13304 }
universityOfAppliedSciences       OBJECT IDENTIFIER ::= { enterprises 13305 }
universityOfMontana               OBJECT IDENTIFIER ::= { enterprises 13306 }
vramRt                            OBJECT IDENTIFIER ::= { enterprises 13307 }
v                                 OBJECT IDENTIFIER ::= { enterprises 13308 }
visantiAS                         OBJECT IDENTIFIER ::= { enterprises 13309 }
wwwolf                            OBJECT IDENTIFIER ::= { enterprises 13310 }
joysOnline                        OBJECT IDENTIFIER ::= { enterprises 13311 }
factorTS                          OBJECT IDENTIFIER ::= { enterprises 13312 }
analogDevices                     OBJECT IDENTIFIER ::= { enterprises 13313 }
blank                             OBJECT IDENTIFIER ::= { enterprises 13314 }
bluecatNetworks                   OBJECT IDENTIFIER ::= { enterprises 13315 }
byteworks                         OBJECT IDENTIFIER ::= { enterprises 13316 }
celiteSystems                     OBJECT IDENTIFIER ::= { enterprises 13317 }
clarityAG                         OBJECT IDENTIFIER ::= { enterprises 13318 }
dipartimentoDiBiochimicaEBiotecnologieMediche OBJECT IDENTIFIER ::= { enterprises 13319 }
griffinDevelopment                OBJECT IDENTIFIER ::= { enterprises 13320 }
incardSpa                         OBJECT IDENTIFIER ::= { enterprises 13321 }
peelTeachingAssistantsAssociation OBJECT IDENTIFIER ::= { enterprises 13322 }
softlogicSolutions                OBJECT IDENTIFIER ::= { enterprises 13323 }
webAddrLLC                        OBJECT IDENTIFIER ::= { enterprises 13324 }
associatedPress                   OBJECT IDENTIFIER ::= { enterprises 13325 }
bermai                            OBJECT IDENTIFIER ::= { enterprises 13326 }
htds                              OBJECT IDENTIFIER ::= { enterprises 13327 }
apoapsis                          OBJECT IDENTIFIER ::= { enterprises 13328 }
area51                            OBJECT IDENTIFIER ::= { enterprises 13329 }
ceyoniq                           OBJECT IDENTIFIER ::= { enterprises 13330 }
cicaiaUniversita                  OBJECT IDENTIFIER ::= { enterprises 13331 }
creditUnionCentralAlbertaLimited  OBJECT IDENTIFIER ::= { enterprises 13332 }
dataOnAir                         OBJECT IDENTIFIER ::= { enterprises 13333 }
hewett                            OBJECT IDENTIFIER ::= { enterprises 13334 }
internetInformationServices       OBJECT IDENTIFIER ::= { enterprises 13335 }
ironhideCorp                      OBJECT IDENTIFIER ::= { enterprises 13336 }
kochanUndPartner                  OBJECT IDENTIFIER ::= { enterprises 13337 }
krocusCommunicationsOy            OBJECT IDENTIFIER ::= { enterprises 13338 }
langeSoftware                     OBJECT IDENTIFIER ::= { enterprises 13339 }
leeBradshaw                       OBJECT IDENTIFIER ::= { enterprises 13340 }
liveSystemsIntegration            OBJECT IDENTIFIER ::= { enterprises 13341 }
unassigned6                       OBJECT IDENTIFIER ::= { enterprises 13342 }
networkingLaboratoryOfDMIS        OBJECT IDENTIFIER ::= { enterprises 13343 }
ningboSuccessInformationIndustryCO OBJECT IDENTIFIER ::= { enterprises 13344 }
pacificorp                        OBJECT IDENTIFIER ::= { enterprises 13345 }
philipsCESTB                      OBJECT IDENTIFIER ::= { enterprises 13346 }
qbranch                           OBJECT IDENTIFIER ::= { enterprises 13347 }
randallKunkee                     OBJECT IDENTIFIER ::= { enterprises 13348 }
rmpAndAssociates                  OBJECT IDENTIFIER ::= { enterprises 13349 }
sdnOnline                         OBJECT IDENTIFIER ::= { enterprises 13350 }
shanghaiMiningComputerSoftwareCo  OBJECT IDENTIFIER ::= { enterprises 13351 }
snsSolutions                      OBJECT IDENTIFIER ::= { enterprises 13352 }
sonofon                           OBJECT IDENTIFIER ::= { enterprises 13353 }
spacetimeCo                       OBJECT IDENTIFIER ::= { enterprises 13354 }
stodgeorg                         OBJECT IDENTIFIER ::= { enterprises 13355 }
summitImaging                     OBJECT IDENTIFIER ::= { enterprises 13356 }
sungardBiTech                     OBJECT IDENTIFIER ::= { enterprises 13357 }
timOCallaghan                     OBJECT IDENTIFIER ::= { enterprises 13358 }
tmRyderInsuranceAgency            OBJECT IDENTIFIER ::= { enterprises 13359 }
trinityConvergence                OBJECT IDENTIFIER ::= { enterprises 13360 }
universit5                        OBJECT IDENTIFIER ::= { enterprises 13361 }
universityOfAppliedSciencesStralsund OBJECT IDENTIFIER ::= { enterprises 13362 }
universityOfSouthernCalifornia    OBJECT IDENTIFIER ::= { enterprises 13363 }
viabridge                         OBJECT IDENTIFIER ::= { enterprises 13364 }
viewbridgeTechnologies            OBJECT IDENTIFIER ::= { enterprises 13365 }
wHInteractive                     OBJECT IDENTIFIER ::= { enterprises 13366 }
whaleQueensOrg                    OBJECT IDENTIFIER ::= { enterprises 13367 }
zandElektronic                    OBJECT IDENTIFIER ::= { enterprises 13368 }
zetaAssociates                    OBJECT IDENTIFIER ::= { enterprises 13369 }
computerNetworks                  OBJECT IDENTIFIER ::= { enterprises 13370 }
qualitywareInform                 OBJECT IDENTIFIER ::= { enterprises 13371 }
ugc                               OBJECT IDENTIFIER ::= { enterprises 13372 }
aptMinds                          OBJECT IDENTIFIER ::= { enterprises 13373 }
axitus                            OBJECT IDENTIFIER ::= { enterprises 13374 }
brainzsquare                      OBJECT IDENTIFIER ::= { enterprises 13375 }
carambole                         OBJECT IDENTIFIER ::= { enterprises 13376 }
conceptisTechnologies             OBJECT IDENTIFIER ::= { enterprises 13377 }
concretioIndiaPrivateLimited      OBJECT IDENTIFIER ::= { enterprises 13378 }
crysec                            OBJECT IDENTIFIER ::= { enterprises 13379 }
dotstarTechnology                 OBJECT IDENTIFIER ::= { enterprises 13380 }
drpData                           OBJECT IDENTIFIER ::= { enterprises 13381 }
intecInternational                OBJECT IDENTIFIER ::= { enterprises 13382 }
intelego                          OBJECT IDENTIFIER ::= { enterprises 13383 }
letinsCorporation                 OBJECT IDENTIFIER ::= { enterprises 13384 }
mountSaintMaryCollege             OBJECT IDENTIFIER ::= { enterprises 13385 }
nagar                             OBJECT IDENTIFIER ::= { enterprises 13386 }
neurostarSolutions                OBJECT IDENTIFIER ::= { enterprises 13387 }
ticoonTechnology                  OBJECT IDENTIFIER ::= { enterprises 13388 }
wraithComputerSystems             OBJECT IDENTIFIER ::= { enterprises 13389 }
avAutomotiveGroup                 OBJECT IDENTIFIER ::= { enterprises 13390 }
callawayGolf                      OBJECT IDENTIFIER ::= { enterprises 13391 }
cavenaImageProductsAB             OBJECT IDENTIFIER ::= { enterprises 13392 }
citeSI                            OBJECT IDENTIFIER ::= { enterprises 13393 }
colligoNetworks                   OBJECT IDENTIFIER ::= { enterprises 13394 }
commercequest                     OBJECT IDENTIFIER ::= { enterprises 13395 }
danvilleASSOCIATES                OBJECT IDENTIFIER ::= { enterprises 13396 }
demandtec                         OBJECT IDENTIFIER ::= { enterprises 13397 }
drRalfSchwedlerInternetSicherheit OBJECT IDENTIFIER ::= { enterprises 13398 }
duneSemiconductor                 OBJECT IDENTIFIER ::= { enterprises 13399 }
emersonNetworkPowerCo             OBJECT IDENTIFIER ::= { enterprises 13400 }
eteSoftware                       OBJECT IDENTIFIER ::= { enterprises 13401 }
exentTechnologies                 OBJECT IDENTIFIER ::= { enterprises 13402 }
foton2000Kft                      OBJECT IDENTIFIER ::= { enterprises 13403 }
fsonaCommunications               OBJECT IDENTIFIER ::= { enterprises 13404 }
insideProducts                    OBJECT IDENTIFIER ::= { enterprises 13405 }
instituteOfMedicalAndVeterinaryScience OBJECT IDENTIFIER ::= { enterprises 13406 }
link2itCorp                       OBJECT IDENTIFIER ::= { enterprises 13407 }
macrobyteResources                OBJECT IDENTIFIER ::= { enterprises 13408 }
megaSystemTechnologies            OBJECT IDENTIFIER ::= { enterprises 13409 }
nationalPublicRadio               OBJECT IDENTIFIER ::= { enterprises 13410 }
neumannElektronik                 OBJECT IDENTIFIER ::= { enterprises 13411 }
ophios                            OBJECT IDENTIFIER ::= { enterprises 13412 }
olabisicom                        OBJECT IDENTIFIER ::= { enterprises 13413 }
pairlink                          OBJECT IDENTIFIER ::= { enterprises 13414 }
schlagAndrahm                     OBJECT IDENTIFIER ::= { enterprises 13415 }
securitymatrix                    OBJECT IDENTIFIER ::= { enterprises 13416 }
siliconBroadcasts                 OBJECT IDENTIFIER ::= { enterprises 13417 }
skkuInformationAndComunicationLab OBJECT IDENTIFIER ::= { enterprises 13418 }
srsSAKURAInternet                 OBJECT IDENTIFIER ::= { enterprises 13419 }
surgitecPte                       OBJECT IDENTIFIER ::= { enterprises 13420 }
tangoTelecomLimited               OBJECT IDENTIFIER ::= { enterprises 13421 }
uniscope                          OBJECT IDENTIFIER ::= { enterprises 13422 }
universiteDeValenciennesJeanLucPetit OBJECT IDENTIFIER ::= { enterprises 13423 }
upcNetherlands                    OBJECT IDENTIFIER ::= { enterprises 13424 }
virtualSpaceResearch              OBJECT IDENTIFIER ::= { enterprises 13425 }
wzabSoftware                      OBJECT IDENTIFIER ::= { enterprises 13426 }
artesynTechnologies               OBJECT IDENTIFIER ::= { enterprises 13427 }
japanSTORAGEBATTERYCO             OBJECT IDENTIFIER ::= { enterprises 13428 }
queenElizabethSchoolOldStudents   OBJECT IDENTIFIER ::= { enterprises 13429 }
shanghaiOnlineBussinessCo         OBJECT IDENTIFIER ::= { enterprises 13430 }
a2e                               OBJECT IDENTIFIER ::= { enterprises 13431 }
campusedgeApartments              OBJECT IDENTIFIER ::= { enterprises 13432 }
codezombiecom                     OBJECT IDENTIFIER ::= { enterprises 13433 }
dyserSRL                          OBJECT IDENTIFIER ::= { enterprises 13434 }
generalMagic                      OBJECT IDENTIFIER ::= { enterprises 13435 }
icontrols                         OBJECT IDENTIFIER ::= { enterprises 13436 }
libits                            OBJECT IDENTIFIER ::= { enterprises 13437 }
logicEastern                      OBJECT IDENTIFIER ::= { enterprises 13438 }
melleService                      OBJECT IDENTIFIER ::= { enterprises 13439 }
networkTelephone                  OBJECT IDENTIFIER ::= { enterprises 13440 }
norfolkSouthernCorp               OBJECT IDENTIFIER ::= { enterprises 13441 }
openves                           OBJECT IDENTIFIER ::= { enterprises 13442 }
ozis                              OBJECT IDENTIFIER ::= { enterprises 13443 }
robertBirdAndPartners             OBJECT IDENTIFIER ::= { enterprises 13444 }
siliconCocoonPty                  OBJECT IDENTIFIER ::= { enterprises 13445 }
singaporeCableVisionLimited       OBJECT IDENTIFIER ::= { enterprises 13446 }
theTrainingMann                   OBJECT IDENTIFIER ::= { enterprises 13447 }
transatTechnologies               OBJECT IDENTIFIER ::= { enterprises 13448 }
trusdatacom                       OBJECT IDENTIFIER ::= { enterprises 13449 }
ttAndsTecnologiaESistemas         OBJECT IDENTIFIER ::= { enterprises 13450 }
networkInformationCenter          OBJECT IDENTIFIER ::= { enterprises 13451 }
myLanGuys                         OBJECT IDENTIFIER ::= { enterprises 13452 }
lanmixTechnologyCo                OBJECT IDENTIFIER ::= { enterprises 13453 }
haysSupplyChain                   OBJECT IDENTIFIER ::= { enterprises 13454 }
deutscheRentenversicherungRechenzentrumLeipzig OBJECT IDENTIFIER ::= { enterprises 13455 }
aetEuropeBV                       OBJECT IDENTIFIER ::= { enterprises 13456 }
armHoldingsPlc                    OBJECT IDENTIFIER ::= { enterprises 13457 }
atmedia                           OBJECT IDENTIFIER ::= { enterprises 13458 }
cais                              OBJECT IDENTIFIER ::= { enterprises 13459 }
comelis                           OBJECT IDENTIFIER ::= { enterprises 13460 }
ebsuccessSolutions                OBJECT IDENTIFIER ::= { enterprises 13461 }
estei                             OBJECT IDENTIFIER ::= { enterprises 13462 }
fortWayneCommunitySchools         OBJECT IDENTIFIER ::= { enterprises 13463 }
greennetTECHNOLOGYCO              OBJECT IDENTIFIER ::= { enterprises 13464 }
ingateSystemsAB                   OBJECT IDENTIFIER ::= { enterprises 13465 }
jabber                            OBJECT IDENTIFIER ::= { enterprises 13466 }
medasys                           OBJECT IDENTIFIER ::= { enterprises 13467 }
montclairStateUniversity          OBJECT IDENTIFIER ::= { enterprises 13468 }
netlibrary                        OBJECT IDENTIFIER ::= { enterprises 13469 }
ottoSecurityAndSoftwareTechnologie OBJECT IDENTIFIER ::= { enterprises 13470 }
powerwan                          OBJECT IDENTIFIER ::= { enterprises 13471 }
rtsRealtimesSystems               OBJECT IDENTIFIER ::= { enterprises 13472 }
safeweb2                          OBJECT IDENTIFIER ::= { enterprises 13473 }
sierraSystemsGroup                OBJECT IDENTIFIER ::= { enterprises 13474 }
snaptrack                         OBJECT IDENTIFIER ::= { enterprises 13475 }
telemantCorp                      OBJECT IDENTIFIER ::= { enterprises 13476 }
shanghaiHAORUNTechnologies        OBJECT IDENTIFIER ::= { enterprises 13477 }
clear2talk                        OBJECT IDENTIFIER ::= { enterprises 13478 }
dstl                              OBJECT IDENTIFIER ::= { enterprises 13479 }
anywareTechnology                 OBJECT IDENTIFIER ::= { enterprises 13480 }
apploadNordicAB                   OBJECT IDENTIFIER ::= { enterprises 13481 }
atlTelecom                        OBJECT IDENTIFIER ::= { enterprises 13482 }
aviri                             OBJECT IDENTIFIER ::= { enterprises 13483 }
choiceOneCommunications           OBJECT IDENTIFIER ::= { enterprises 13484 }
comindico                         OBJECT IDENTIFIER ::= { enterprises 13485 }
computerScienceDept               OBJECT IDENTIFIER ::= { enterprises 13486 }
corvuCorporation                  OBJECT IDENTIFIER ::= { enterprises 13487 }
dncp                              OBJECT IDENTIFIER ::= { enterprises 13488 }
easternGoldfieldsSeniorHighSchool OBJECT IDENTIFIER ::= { enterprises 13489 }
eplication                        OBJECT IDENTIFIER ::= { enterprises 13490 }
euromacc                          OBJECT IDENTIFIER ::= { enterprises 13491 }
firstDataMerchantServices         OBJECT IDENTIFIER ::= { enterprises 13492 }
globalScienceAndTechnology        OBJECT IDENTIFIER ::= { enterprises 13493 }
illinoisMathematicsAndScienceAcademy OBJECT IDENTIFIER ::= { enterprises 13494 }
inat                              OBJECT IDENTIFIER ::= { enterprises 13495 }
instituteOfInformatics            OBJECT IDENTIFIER ::= { enterprises 13496 }
it3Consultants                    OBJECT IDENTIFIER ::= { enterprises 13497 }
kke                               OBJECT IDENTIFIER ::= { enterprises 13498 }
metodaSpA                         OBJECT IDENTIFIER ::= { enterprises 13499 }
mplAG                             OBJECT IDENTIFIER ::= { enterprises 13500 }
nexstarFinancialCorporation       OBJECT IDENTIFIER ::= { enterprises 13501 }
onesquared                        OBJECT IDENTIFIER ::= { enterprises 13502 }
orchestriaLimited                 OBJECT IDENTIFIER ::= { enterprises 13503 }
polkomtelSA                       OBJECT IDENTIFIER ::= { enterprises 13504 }
procosAG                          OBJECT IDENTIFIER ::= { enterprises 13505 }
psionicSoftware                   OBJECT IDENTIFIER ::= { enterprises 13506 }
radcomSoftwareRomania             OBJECT IDENTIFIER ::= { enterprises 13507 }
sigdci                            OBJECT IDENTIFIER ::= { enterprises 13508 }
skyComputers                      OBJECT IDENTIFIER ::= { enterprises 13509 }
somomaCountyWaterAgency           OBJECT IDENTIFIER ::= { enterprises 13510 }
spaceip                           OBJECT IDENTIFIER ::= { enterprises 13511 }
teamwarrior                       OBJECT IDENTIFIER ::= { enterprises 13512 }
theTechnologyPartner              OBJECT IDENTIFIER ::= { enterprises 13513 }
unassigned7                       OBJECT IDENTIFIER ::= { enterprises 13514 }
unitechNetworks                   OBJECT IDENTIFIER ::= { enterprises 13515 }
vilokeOy                          OBJECT IDENTIFIER ::= { enterprises 13516 }
xi3                               OBJECT IDENTIFIER ::= { enterprises 13517 }
abnAMRONLCCC                      OBJECT IDENTIFIER ::= { enterprises 13518 }
amsoftSystemsIndia                OBJECT IDENTIFIER ::= { enterprises 13519 }
bizwebapps                        OBJECT IDENTIFIER ::= { enterprises 13520 }
sysnight                          OBJECT IDENTIFIER ::= { enterprises 13521 }
accountSynchronizationProject     OBJECT IDENTIFIER ::= { enterprises 13522 }
australianIndustryGroup           OBJECT IDENTIFIER ::= { enterprises 13523 }
barhamHousePublishing             OBJECT IDENTIFIER ::= { enterprises 13524 }
blarg-OnlineServices              OBJECT IDENTIFIER ::= { enterprises 13525 }
clickmarks                        OBJECT IDENTIFIER ::= { enterprises 13526 }
digitasaru                        OBJECT IDENTIFIER ::= { enterprises 13527 }
dlese                             OBJECT IDENTIFIER ::= { enterprises 13528 }
dreamlanNetworkConsulting         OBJECT IDENTIFIER ::= { enterprises 13529 }
fahnestockAndCo                   OBJECT IDENTIFIER ::= { enterprises 13530 }
mierComunicaciones                OBJECT IDENTIFIER ::= { enterprises 13531 }
pennantSystems                    OBJECT IDENTIFIER ::= { enterprises 13532 }
petrZahradnikComputerLaboratory   OBJECT IDENTIFIER ::= { enterprises 13533 }
proteusMobile                     OBJECT IDENTIFIER ::= { enterprises 13534 }
rocksteadyNetworks                OBJECT IDENTIFIER ::= { enterprises 13535 }
seromeTechnology                  OBJECT IDENTIFIER ::= { enterprises 13536 }
shineGlobal                       OBJECT IDENTIFIER ::= { enterprises 13537 }
videobureau                       OBJECT IDENTIFIER ::= { enterprises 13538 }
voorhoutDataConnectionBV          OBJECT IDENTIFIER ::= { enterprises 13539 }
shenzhenKeybridgeCommunicationsCo OBJECT IDENTIFIER ::= { enterprises 13540 }
dbvWinterthurVersicherungen       OBJECT IDENTIFIER ::= { enterprises 13541 }
datapacSro                        OBJECT IDENTIFIER ::= { enterprises 13542 }
percentIT                         OBJECT IDENTIFIER ::= { enterprises 13543 }
acopiaNetworks                    OBJECT IDENTIFIER ::= { enterprises 13544 }
adverbSoftware                    OBJECT IDENTIFIER ::= { enterprises 13545 }
altaAS                            OBJECT IDENTIFIER ::= { enterprises 13546 }
axiomSystemsLimited               OBJECT IDENTIFIER ::= { enterprises 13547 }
bakboneSoftware                   OBJECT IDENTIFIER ::= { enterprises 13548 }
banqueDeFrance                    OBJECT IDENTIFIER ::= { enterprises 13549 }
celstreamTechnologies             OBJECT IDENTIFIER ::= { enterprises 13550 }
cofundsLTD                        OBJECT IDENTIFIER ::= { enterprises 13551 }
cqg                               OBJECT IDENTIFIER ::= { enterprises 13552 }
cyberSpaceSystems                 OBJECT IDENTIFIER ::= { enterprises 13553 }
dtnSpeedNetServices               OBJECT IDENTIFIER ::= { enterprises 13554 }
enterpriseBusinessSolutions       OBJECT IDENTIFIER ::= { enterprises 13555 }
filtronicPlc                      OBJECT IDENTIFIER ::= { enterprises 13556 }
floorgraphics                     OBJECT IDENTIFIER ::= { enterprises 13557 }
garyReynolds                      OBJECT IDENTIFIER ::= { enterprises 13558 }
globalTechnologyAssociates        OBJECT IDENTIFIER ::= { enterprises 13559 }
grantCountyPUDnum2                OBJECT IDENTIFIER ::= { enterprises 13560 }
griffithUniversity                OBJECT IDENTIFIER ::= { enterprises 13561 }
informationSciencesInstitute      OBJECT IDENTIFIER ::= { enterprises 13562 }
integratedSoftwareTechnologies    OBJECT IDENTIFIER ::= { enterprises 13563 }
logistikWorld                     OBJECT IDENTIFIER ::= { enterprises 13564 }
lucentTechnologiesIndia           OBJECT IDENTIFIER ::= { enterprises 13565 }
neolytica                         OBJECT IDENTIFIER ::= { enterprises 13566 }
netcelo                           OBJECT IDENTIFIER ::= { enterprises 13567 }
neustar                           OBJECT IDENTIFIER ::= { enterprises 13568 }
oiz                               OBJECT IDENTIFIER ::= { enterprises 13569 }
securityIntegration               OBJECT IDENTIFIER ::= { enterprises 13570 }
tesisSYSware                      OBJECT IDENTIFIER ::= { enterprises 13571 }
tjedwards                         OBJECT IDENTIFIER ::= { enterprises 13572 }
tranEmpireIndustries              OBJECT IDENTIFIER ::= { enterprises 13573 }
tvgTechnologies                   OBJECT IDENTIFIER ::= { enterprises 13574 }
universityOfWindsor               OBJECT IDENTIFIER ::= { enterprises 13575 }
wagoKontakttechnik                OBJECT IDENTIFIER ::= { enterprises 13576 }
youjin                            OBJECT IDENTIFIER ::= { enterprises 13577 }
apogeeSolutions                   OBJECT IDENTIFIER ::= { enterprises 13578 }
lmnAssociates                     OBJECT IDENTIFIER ::= { enterprises 13579 }
europAssistanceFrance             OBJECT IDENTIFIER ::= { enterprises 13580 }
tamagawaUNIV                      OBJECT IDENTIFIER ::= { enterprises 13581 }
nordijaAS                         OBJECT IDENTIFIER ::= { enterprises 13582 }
ucbirl                            OBJECT IDENTIFIER ::= { enterprises 13583 }
scheringAG                        OBJECT IDENTIFIER ::= { enterprises 13584 }
mangaloreRefineryAndPetrochemicalsLimited OBJECT IDENTIFIER ::= { enterprises 13585 }
woodsideNetworks                  OBJECT IDENTIFIER ::= { enterprises 13586 }
universiteDeFrancheComte          OBJECT IDENTIFIER ::= { enterprises 13587 }
acegiTechnologyPtyLimited         OBJECT IDENTIFIER ::= { enterprises 13588 }
airTrafficControlAndBusinessSystems OBJECT IDENTIFIER ::= { enterprises 13589 }
americreditCorp                   OBJECT IDENTIFIER ::= { enterprises 13590 }
beIntelligentSystems              OBJECT IDENTIFIER ::= { enterprises 13591 }
blunkMicrosystems                 OBJECT IDENTIFIER ::= { enterprises 13592 }
commerceflow                      OBJECT IDENTIFIER ::= { enterprises 13593 }
companyWatchLimited               OBJECT IDENTIFIER ::= { enterprises 13594 }
emkaElectronicAG                  OBJECT IDENTIFIER ::= { enterprises 13595 }
fachhochschuleBingen              OBJECT IDENTIFIER ::= { enterprises 13596 }
feis                              OBJECT IDENTIFIER ::= { enterprises 13597 }
generalDynamicsCanada             OBJECT IDENTIFIER ::= { enterprises 13598 }
goldenTriangleOnline              OBJECT IDENTIFIER ::= { enterprises 13599 }
greenmokeynet                     OBJECT IDENTIFIER ::= { enterprises 13600 }
hwaChongJuniorCollege             OBJECT IDENTIFIER ::= { enterprises 13601 }
is4O                              OBJECT IDENTIFIER ::= { enterprises 13602 }
kpnqwestCzechiaSro                OBJECT IDENTIFIER ::= { enterprises 13603 }
liberateTechnologies              OBJECT IDENTIFIER ::= { enterprises 13604 }
maverickWorkgroup                 OBJECT IDENTIFIER ::= { enterprises 13605 }
nicomaque                         OBJECT IDENTIFIER ::= { enterprises 13606 }
northCarolinaState                OBJECT IDENTIFIER ::= { enterprises 13607 }
openhandhome                      OBJECT IDENTIFIER ::= { enterprises 13608 }
palladiumConsulting               OBJECT IDENTIFIER ::= { enterprises 13609 }
qSolutions                        OBJECT IDENTIFIER ::= { enterprises 13610 }
rbcData                           OBJECT IDENTIFIER ::= { enterprises 13611 }
schlundPartnerAG                  OBJECT IDENTIFIER ::= { enterprises 13612 }
strataverio                       OBJECT IDENTIFIER ::= { enterprises 13613 }
tartuK                            OBJECT IDENTIFIER ::= { enterprises 13614 }
th                                OBJECT IDENTIFIER ::= { enterprises 13615 }
thalesSYSTEMINTEGRATION           OBJECT IDENTIFIER ::= { enterprises 13616 }
thoseInteractiveGuys              OBJECT IDENTIFIER ::= { enterprises 13617 }
transimTechnologyCorp             OBJECT IDENTIFIER ::= { enterprises 13618 }
undercoverwearCollection          OBJECT IDENTIFIER ::= { enterprises 13619 }
universityOfWisconsinEauClaire    OBJECT IDENTIFIER ::= { enterprises 13620 }
windTelecom                       OBJECT IDENTIFIER ::= { enterprises 13621 }
yaina                             OBJECT IDENTIFIER ::= { enterprises 13622 }
pointIt                           OBJECT IDENTIFIER ::= { enterprises 13623 }
eastcomBUPTINFORMATIONTECHNOLOGYCO OBJECT IDENTIFIER ::= { enterprises 13624 }
pohlcityde                        OBJECT IDENTIFIER ::= { enterprises 13625 }
rastel                            OBJECT IDENTIFIER ::= { enterprises 13626 }
netfor                            OBJECT IDENTIFIER ::= { enterprises 13627 }
sercon                            OBJECT IDENTIFIER ::= { enterprises 13628 }
agtechNetworkService              OBJECT IDENTIFIER ::= { enterprises 13629 }
afxNews                           OBJECT IDENTIFIER ::= { enterprises 13630 }
araxCommunications                OBJECT IDENTIFIER ::= { enterprises 13631 }
atomixDESiGN                      OBJECT IDENTIFIER ::= { enterprises 13632 }
avaAfzarCo                        OBJECT IDENTIFIER ::= { enterprises 13633 }
bAndbComputersystemeGbR           OBJECT IDENTIFIER ::= { enterprises 13634 }
bsws                              OBJECT IDENTIFIER ::= { enterprises 13635 }
corestreet                        OBJECT IDENTIFIER ::= { enterprises 13636 }
cresentSoftwareProducts           OBJECT IDENTIFIER ::= { enterprises 13637 }
expertSystemsIVR                  OBJECT IDENTIFIER ::= { enterprises 13638 }
fibrotec                          OBJECT IDENTIFIER ::= { enterprises 13639 }
jonWood                           OBJECT IDENTIFIER ::= { enterprises 13640 }
kremlinComputingLimited           OBJECT IDENTIFIER ::= { enterprises 13641 }
litas                             OBJECT IDENTIFIER ::= { enterprises 13642 }
mimosBerhad                       OBJECT IDENTIFIER ::= { enterprises 13643 }
musenki                           OBJECT IDENTIFIER ::= { enterprises 13644 }
okbMEI                            OBJECT IDENTIFIER ::= { enterprises 13645 }
oninit                            OBJECT IDENTIFIER ::= { enterprises 13646 }
ostseeZeitung                     OBJECT IDENTIFIER ::= { enterprises 13647 }
pointredTechnologies              OBJECT IDENTIFIER ::= { enterprises 13648 }
polizeiRheinlandPfalz             OBJECT IDENTIFIER ::= { enterprises 13649 }
relativity                        OBJECT IDENTIFIER ::= { enterprises 13650 }
rexkramer                         OBJECT IDENTIFIER ::= { enterprises 13651 }
seoulMobileTelecom                OBJECT IDENTIFIER ::= { enterprises 13653 }
shenzhenXIFENGNETWORKTECHNOLOGIESCO OBJECT IDENTIFIER ::= { enterprises 13654 }
spacemonsterGamingNetwork         OBJECT IDENTIFIER ::= { enterprises 13655 }
sunnybellTechnology               OBJECT IDENTIFIER ::= { enterprises 13656 }
tangoSA                           OBJECT IDENTIFIER ::= { enterprises 13657 }
teddy                             OBJECT IDENTIFIER ::= { enterprises 13658 }
theWorleyCompanies                OBJECT IDENTIFIER ::= { enterprises 13659 }
usArmyCECOM                       OBJECT IDENTIFIER ::= { enterprises 13660 }
umist                             OBJECT IDENTIFIER ::= { enterprises 13661 }
universidadDePalermo              OBJECT IDENTIFIER ::= { enterprises 13662 }
vrgroupcom                        OBJECT IDENTIFIER ::= { enterprises 13663 }
vssKB                             OBJECT IDENTIFIER ::= { enterprises 13664 }
websAreus                         OBJECT IDENTIFIER ::= { enterprises 13665 }
wolfHill                          OBJECT IDENTIFIER ::= { enterprises 13666 }
wozzleInternetSolutions           OBJECT IDENTIFIER ::= { enterprises 13667 }
yesTechnology                     OBJECT IDENTIFIER ::= { enterprises 13668 }
cubicTransportationSystems        OBJECT IDENTIFIER ::= { enterprises 13669 }
sanDiegoDataProcessingCorporation OBJECT IDENTIFIER ::= { enterprises 13670 }
techtv                            OBJECT IDENTIFIER ::= { enterprises 13671 }
generalDynamicsDecisionSystemsSecureProducts OBJECT IDENTIFIER ::= { enterprises 13672 }
internetCz                        OBJECT IDENTIFIER ::= { enterprises 13673 }
pesaSwitchingSystems              OBJECT IDENTIFIER ::= { enterprises 13674 }
bandwaveInternet                  OBJECT IDENTIFIER ::= { enterprises 13675 }
frenchDataNetwork                 OBJECT IDENTIFIER ::= { enterprises 13676 }
kbTELTelecomunicacionesSADeCV     OBJECT IDENTIFIER ::= { enterprises 13677 }
acterAG                           OBJECT IDENTIFIER ::= { enterprises 13678 }
altigenCommunications             OBJECT IDENTIFIER ::= { enterprises 13679 }
avivaSolutions                    OBJECT IDENTIFIER ::= { enterprises 13680 }
childlockSolutions                OBJECT IDENTIFIER ::= { enterprises 13681 }
ecoleDesMinesDeNantes             OBJECT IDENTIFIER ::= { enterprises 13682 }
eftechnologies                    OBJECT IDENTIFIER ::= { enterprises 13683 }
elpromaElektronika                OBJECT IDENTIFIER ::= { enterprises 13684 }
facultyOfMathematicsAndComputerScience OBJECT IDENTIFIER ::= { enterprises 13685 }
goWin                             OBJECT IDENTIFIER ::= { enterprises 13686 }
humboldtUniversitaetZuBerlin      OBJECT IDENTIFIER ::= { enterprises 13687 }
icequakeNetworks                  OBJECT IDENTIFIER ::= { enterprises 13688 }
inTownConsultingLLC               OBJECT IDENTIFIER ::= { enterprises 13689 }
madrasComputerVertriebsgesmbH     OBJECT IDENTIFIER ::= { enterprises 13690 }
maisonD                           OBJECT IDENTIFIER ::= { enterprises 13691 }
mediface                          OBJECT IDENTIFIER ::= { enterprises 13692 }
mirageNetworks                    OBJECT IDENTIFIER ::= { enterprises 13693 }
nervusSystems                     OBJECT IDENTIFIER ::= { enterprises 13694 }
neurosphereConsulting             OBJECT IDENTIFIER ::= { enterprises 13695 }
ohioWesleyanUniversity            OBJECT IDENTIFIER ::= { enterprises 13696 }
paulDlug                          OBJECT IDENTIFIER ::= { enterprises 13697 }
runcircle                         OBJECT IDENTIFIER ::= { enterprises 13698 }
sarvega                           OBJECT IDENTIFIER ::= { enterprises 13699 }
scaleEight                        OBJECT IDENTIFIER ::= { enterprises 13700 }
sonicSoftware                     OBJECT IDENTIFIER ::= { enterprises 13701 }
storeMediaEngineering             OBJECT IDENTIFIER ::= { enterprises 13702 }
sundatacomPvt                     OBJECT IDENTIFIER ::= { enterprises 13703 }
tno                               OBJECT IDENTIFIER ::= { enterprises 13704 }
universitasIndonesia              OBJECT IDENTIFIER ::= { enterprises 13705 }
volvoEventManagement              OBJECT IDENTIFIER ::= { enterprises 13706 }
wasilianaSolutions                OBJECT IDENTIFIER ::= { enterprises 13707 }
aicNETWORK                        OBJECT IDENTIFIER ::= { enterprises 13708 }
theBankOfNewYork                  OBJECT IDENTIFIER ::= { enterprises 13709 }
lvmVersicherungen                 OBJECT IDENTIFIER ::= { enterprises 13710 }
primusTelecommunicationsAustraliaPty OBJECT IDENTIFIER ::= { enterprises 13711 }
arinc                             OBJECT IDENTIFIER ::= { enterprises 13712 }
gateweaver                        OBJECT IDENTIFIER ::= { enterprises 13713 }
reea                              OBJECT IDENTIFIER ::= { enterprises 13714 }
alescere                          OBJECT IDENTIFIER ::= { enterprises 13715 }
cajaMadrid                        OBJECT IDENTIFIER ::= { enterprises 13716 }
carrekerCorporation               OBJECT IDENTIFIER ::= { enterprises 13717 }
ccitriad                          OBJECT IDENTIFIER ::= { enterprises 13718 }
cegetelSI                         OBJECT IDENTIFIER ::= { enterprises 13719 }
coremediaAG                       OBJECT IDENTIFIER ::= { enterprises 13720 }
corningCableSystems               OBJECT IDENTIFIER ::= { enterprises 13721 }
deotnet                           OBJECT IDENTIFIER ::= { enterprises 13722 }
divisionOfBITL                    OBJECT IDENTIFIER ::= { enterprises 13723 }
erasmusUniversityRotterdam        OBJECT IDENTIFIER ::= { enterprises 13724 }
euronetics                        OBJECT IDENTIFIER ::= { enterprises 13725 }
fhBonnRheinSieg                   OBJECT IDENTIFIER ::= { enterprises 13726 }
funda                             OBJECT IDENTIFIER ::= { enterprises 13727 }
fundaci                           OBJECT IDENTIFIER ::= { enterprises 13728 }
funktionalSolutionsGroup          OBJECT IDENTIFIER ::= { enterprises 13729 }
geobot                            OBJECT IDENTIFIER ::= { enterprises 13730 }
huthEngineering                   OBJECT IDENTIFIER ::= { enterprises 13731 }
idirect                           OBJECT IDENTIFIER ::= { enterprises 13732 }
imservEurope                      OBJECT IDENTIFIER ::= { enterprises 13733 }
institutFuerTheorieDerElektrotechnik OBJECT IDENTIFIER ::= { enterprises 13734 }
integra5                          OBJECT IDENTIFIER ::= { enterprises 13735 }
manufactureDesMontresRolexSA      OBJECT IDENTIFIER ::= { enterprises 13736 }
markWilcoxAndAssociates           OBJECT IDENTIFIER ::= { enterprises 13737 }
mindmaticsAG                      OBJECT IDENTIFIER ::= { enterprises 13738 }
pacesetterElectronics             OBJECT IDENTIFIER ::= { enterprises 13739 }
popwireTechnologyAB               OBJECT IDENTIFIER ::= { enterprises 13740 }
proinos                           OBJECT IDENTIFIER ::= { enterprises 13741 }
raritanComputer                   OBJECT IDENTIFIER ::= { enterprises 13742 }
sgteIES                           OBJECT IDENTIFIER ::= { enterprises 13743 }
skytel                            OBJECT IDENTIFIER ::= { enterprises 13744 }
somixTechnologies                 OBJECT IDENTIFIER ::= { enterprises 13745 }
universityOfDetroitMercy          OBJECT IDENTIFIER ::= { enterprises 13746 }
virtualHealthNetworks             OBJECT IDENTIFIER ::= { enterprises 13747 }
wizzbit                           OBJECT IDENTIFIER ::= { enterprises 13748 }
madisonConsulting                 OBJECT IDENTIFIER ::= { enterprises 13749 }
juergenWeberUnternehmensberatung  OBJECT IDENTIFIER ::= { enterprises 13750 }
agyTherapeutics                   OBJECT IDENTIFIER ::= { enterprises 13751 }
amarnaSoftwareProductions         OBJECT IDENTIFIER ::= { enterprises 13752 }
ascentComputingGroup              OBJECT IDENTIFIER ::= { enterprises 13753 }
bancoZaragozano                   OBJECT IDENTIFIER ::= { enterprises 13754 }
carletonCollege                   OBJECT IDENTIFIER ::= { enterprises 13755 }
cLOGInternational                 OBJECT IDENTIFIER ::= { enterprises 13756 }
coxInteractiveMedia               OBJECT IDENTIFIER ::= { enterprises 13757 }
crTeamde                          OBJECT IDENTIFIER ::= { enterprises 13758 }
examen                            OBJECT IDENTIFIER ::= { enterprises 13759 }
fourthHouseSecurity               OBJECT IDENTIFIER ::= { enterprises 13760 }
glencoreInternationalAG           OBJECT IDENTIFIER ::= { enterprises 13761 }
innovery                          OBJECT IDENTIFIER ::= { enterprises 13762 }
johannesPassingSoftwareentwicklung OBJECT IDENTIFIER ::= { enterprises 13763 }
khodayssSystemsLimited            OBJECT IDENTIFIER ::= { enterprises 13764 }
lifeTimeFitness                   OBJECT IDENTIFIER ::= { enterprises 13765 }
loeweOpta                         OBJECT IDENTIFIER ::= { enterprises 13766 }
metalogueCommunications           OBJECT IDENTIFIER ::= { enterprises 13767 }
movaris                           OBJECT IDENTIFIER ::= { enterprises 13768 }
mozillaorg                        OBJECT IDENTIFIER ::= { enterprises 13769 }
mtaSolutions                      OBJECT IDENTIFIER ::= { enterprises 13770 }
navicSystems                      OBJECT IDENTIFIER ::= { enterprises 13771 }
npulseSoftware                    OBJECT IDENTIFIER ::= { enterprises 13772 }
ntelos                            OBJECT IDENTIFIER ::= { enterprises 13773 }
onetta                            OBJECT IDENTIFIER ::= { enterprises 13774 }
pomonaCollege                     OBJECT IDENTIFIER ::= { enterprises 13775 }
potlatchCorporation               OBJECT IDENTIFIER ::= { enterprises 13776 }
rakuten                           OBJECT IDENTIFIER ::= { enterprises 13777 }
sociedadeDiginet                  OBJECT IDENTIFIER ::= { enterprises 13778 }
sumixCorporation                  OBJECT IDENTIFIER ::= { enterprises 13779 }
ubernulProjekt                    OBJECT IDENTIFIER ::= { enterprises 13780 }
universiteD                       OBJECT IDENTIFIER ::= { enterprises 13781 }
universityOfDortmund              OBJECT IDENTIFIER ::= { enterprises 13782 }
vikingSocietyOfSA                 OBJECT IDENTIFIER ::= { enterprises 13783 }
whidbeynet                        OBJECT IDENTIFIER ::= { enterprises 13784 }
yh                                OBJECT IDENTIFIER ::= { enterprises 13785 }
zpSystem                          OBJECT IDENTIFIER ::= { enterprises 13786 }
pagemail                          OBJECT IDENTIFIER ::= { enterprises 13787 }
devLabs                           OBJECT IDENTIFIER ::= { enterprises 13788 }
innovations                       OBJECT IDENTIFIER ::= { enterprises 13789 }
uKingCommunicationsCorp           OBJECT IDENTIFIER ::= { enterprises 13790 }
associa                           OBJECT IDENTIFIER ::= { enterprises 13791 }
activeTelecom2                    OBJECT IDENTIFIER ::= { enterprises 13792 }
acumenSciences                    OBJECT IDENTIFIER ::= { enterprises 13793 }
beijingEducationalInformationNetwork OBJECT IDENTIFIER ::= { enterprises 13794 }
blueEdgeBulgaria                  OBJECT IDENTIFIER ::= { enterprises 13795 }
caliariResearchSpANicola          OBJECT IDENTIFIER ::= { enterprises 13796 }
cirad                             OBJECT IDENTIFIER ::= { enterprises 13797 }
globenet                          OBJECT IDENTIFIER ::= { enterprises 13798 }
internet78                        OBJECT IDENTIFIER ::= { enterprises 13799 }
isServices                        OBJECT IDENTIFIER ::= { enterprises 13800 }
iufmDesPaysDeLaLoire              OBJECT IDENTIFIER ::= { enterprises 13801 }
mundeeInternetServices            OBJECT IDENTIFIER ::= { enterprises 13802 }
navajoLawEnforcementTrainingAcademy OBJECT IDENTIFIER ::= { enterprises 13803 }
pontificalCollegeJosephinum       OBJECT IDENTIFIER ::= { enterprises 13804 }
southlandChristianChurch          OBJECT IDENTIFIER ::= { enterprises 13805 }
sysopenPlc                        OBJECT IDENTIFIER ::= { enterprises 13806 }
tpack                             OBJECT IDENTIFIER ::= { enterprises 13807 }
ubernulProjekt2                   OBJECT IDENTIFIER ::= { enterprises 13808 }
universit6                        OBJECT IDENTIFIER ::= { enterprises 13809 }
universityOfAlaska                OBJECT IDENTIFIER ::= { enterprises 13810 }
israelDiscountBank                OBJECT IDENTIFIER ::= { enterprises 13811 }
smartpriceSA                      OBJECT IDENTIFIER ::= { enterprises 13812 }
evalescoSystemsApS                OBJECT IDENTIFIER ::= { enterprises 13813 }
alfaMediaPartner                  OBJECT IDENTIFIER ::= { enterprises 13814 }
angelIglesias                     OBJECT IDENTIFIER ::= { enterprises 13815 }
appsenseTechnologies              OBJECT IDENTIFIER ::= { enterprises 13816 }
ausw                              OBJECT IDENTIFIER ::= { enterprises 13817 }
bhi                               OBJECT IDENTIFIER ::= { enterprises 13818 }
btiCommunicationsCo               OBJECT IDENTIFIER ::= { enterprises 13819 }
ceskyTELECOM                      OBJECT IDENTIFIER ::= { enterprises 13820 }
cniPrairienet                     OBJECT IDENTIFIER ::= { enterprises 13821 }
commandSoftwareSystems            OBJECT IDENTIFIER ::= { enterprises 13822 }
comtarsiaITServices               OBJECT IDENTIFIER ::= { enterprises 13823 }
consus                            OBJECT IDENTIFIER ::= { enterprises 13824 }
crispHughesEvansLLP2              OBJECT IDENTIFIER ::= { enterprises 13825 }
deptOfVeteransAffairs             OBJECT IDENTIFIER ::= { enterprises 13826 }
endrunTechnologiesLLC             OBJECT IDENTIFIER ::= { enterprises 13827 }
etmInternationalAustria           OBJECT IDENTIFIER ::= { enterprises 13828 }
flechaDeLimaAssociados            OBJECT IDENTIFIER ::= { enterprises 13829 }
gedSOFTWARE                       OBJECT IDENTIFIER ::= { enterprises 13830 }
geoMarine                         OBJECT IDENTIFIER ::= { enterprises 13831 }
theGoDaddyGroup                   OBJECT IDENTIFIER ::= { enterprises 13832 }
gobiernoDeCanarias                OBJECT IDENTIFIER ::= { enterprises 13833 }
imach                             OBJECT IDENTIFIER ::= { enterprises 13834 }
inetLogistics                     OBJECT IDENTIFIER ::= { enterprises 13835 }
informationAndLogisticsConsultancy OBJECT IDENTIFIER ::= { enterprises 13836 }
introtec                          OBJECT IDENTIFIER ::= { enterprises 13837 }
kadelDataServisSro                OBJECT IDENTIFIER ::= { enterprises 13838 }
logicscopeRealisations            OBJECT IDENTIFIER ::= { enterprises 13839 }
mediaDriver                       OBJECT IDENTIFIER ::= { enterprises 13840 }
metilinx                          OBJECT IDENTIFIER ::= { enterprises 13841 }
moserBaerAG                       OBJECT IDENTIFIER ::= { enterprises 13842 }
nedDavisResearchGroup             OBJECT IDENTIFIER ::= { enterprises 13843 }
newCollege                        OBJECT IDENTIFIER ::= { enterprises 13844 }
ohioNorthernUniversity            OBJECT IDENTIFIER ::= { enterprises 13845 }
patientkeeper                     OBJECT IDENTIFIER ::= { enterprises 13846 }
pearcoServices                    OBJECT IDENTIFIER ::= { enterprises 13847 }
rnixcom                           OBJECT IDENTIFIER ::= { enterprises 13848 }
seproTelecom                      OBJECT IDENTIFIER ::= { enterprises 13849 }
static                            OBJECT IDENTIFIER ::= { enterprises 13850 }
swisscomITSErvicesAG              OBJECT IDENTIFIER ::= { enterprises 13851 }
topologica                        OBJECT IDENTIFIER ::= { enterprises 13852 }
tularik                           OBJECT IDENTIFIER ::= { enterprises 13853 }
universitaetMannheim              OBJECT IDENTIFIER ::= { enterprises 13854 }
universitaetOldenburg             OBJECT IDENTIFIER ::= { enterprises 13855 }
universityOfMichiganHealthSystem  OBJECT IDENTIFIER ::= { enterprises 13856 }
ursysPtyLTD                       OBJECT IDENTIFIER ::= { enterprises 13857 }
valerePower                       OBJECT IDENTIFIER ::= { enterprises 13858 }
voxpilot                          OBJECT IDENTIFIER ::= { enterprises 13859 }
wasko                             OBJECT IDENTIFIER ::= { enterprises 13860 }
wolfITConcepts                    OBJECT IDENTIFIER ::= { enterprises 13861 }
xtec                              OBJECT IDENTIFIER ::= { enterprises 13862 }
airwolfSystems                    OBJECT IDENTIFIER ::= { enterprises 13863 }
maminos                           OBJECT IDENTIFIER ::= { enterprises 13864 }
universit7                        OBJECT IDENTIFIER ::= { enterprises 13865 }
aceTIMING                         OBJECT IDENTIFIER ::= { enterprises 13866 }
adfinis                           OBJECT IDENTIFIER ::= { enterprises 13867 }
bahrainCredit                     OBJECT IDENTIFIER ::= { enterprises 13868 }
blumCapitalPartners               OBJECT IDENTIFIER ::= { enterprises 13869 }
corporateOxygen                   OBJECT IDENTIFIER ::= { enterprises 13870 }
falconSoftwareNV                  OBJECT IDENTIFIER ::= { enterprises 13871 }
federalUniversityOfSaoPaulo       OBJECT IDENTIFIER ::= { enterprises 13872 }
fmc                               OBJECT IDENTIFIER ::= { enterprises 13873 }
goeppnet                          OBJECT IDENTIFIER ::= { enterprises 13874 }
interact2                         OBJECT IDENTIFIER ::= { enterprises 13875 }
ionicProductionsLLC               OBJECT IDENTIFIER ::= { enterprises 13876 }
kandaTsushinKogyoCo               OBJECT IDENTIFIER ::= { enterprises 13877 }
karibooTechnologiesSA             OBJECT IDENTIFIER ::= { enterprises 13878 }
naturalSoftSA                     OBJECT IDENTIFIER ::= { enterprises 13879 }
adsNetworksPvt                    OBJECT IDENTIFIER ::= { enterprises 13880 }
neobeenet                         OBJECT IDENTIFIER ::= { enterprises 13881 }
netillaNetworks                   OBJECT IDENTIFIER ::= { enterprises 13882 }
newMorningWindows                 OBJECT IDENTIFIER ::= { enterprises 13883 }
pepcoAS                           OBJECT IDENTIFIER ::= { enterprises 13884 }
polycom                           OBJECT IDENTIFIER ::= { enterprises 13885 }
prosodicCommunications            OBJECT IDENTIFIER ::= { enterprises 13886 }
redRobySoftware                   OBJECT IDENTIFIER ::= { enterprises 13887 }
southTexasLighthouseForTheBlind   OBJECT IDENTIFIER ::= { enterprises 13888 }
spriralDesigns                    OBJECT IDENTIFIER ::= { enterprises 13889 }
teltierTechnologies               OBJECT IDENTIFIER ::= { enterprises 13890 }
theAdvantageGroup                 OBJECT IDENTIFIER ::= { enterprises 13891 }
universityOfNewHampshire          OBJECT IDENTIFIER ::= { enterprises 13892 }
internationalTruckAndEngineCorporation OBJECT IDENTIFIER ::= { enterprises 13893 }
lgnsys                            OBJECT IDENTIFIER ::= { enterprises 13894 }
lagrangeSchoolDistrict102         OBJECT IDENTIFIER ::= { enterprises 13895 }
atosOriginCMSTSP                  OBJECT IDENTIFIER ::= { enterprises 13896 }
advancedTechnologiesLab           OBJECT IDENTIFIER ::= { enterprises 13897 }
alexanderHorschUndThomasBalbachITSolutions OBJECT IDENTIFIER ::= { enterprises 13898 }
ankaSystems                       OBJECT IDENTIFIER ::= { enterprises 13899 }
blueGargoyleConsulting            OBJECT IDENTIFIER ::= { enterprises 13900 }
broadwave                         OBJECT IDENTIFIER ::= { enterprises 13901 }
businessInternetTrends            OBJECT IDENTIFIER ::= { enterprises 13902 }
camhPETCentre                     OBJECT IDENTIFIER ::= { enterprises 13903 }
caymasSystems                     OBJECT IDENTIFIER ::= { enterprises 13904 }
cemagref                          OBJECT IDENTIFIER ::= { enterprises 13905 }
chantryNetworks                   OBJECT IDENTIFIER ::= { enterprises 13906 }
compera                           OBJECT IDENTIFIER ::= { enterprises 13907 }
croatianPhysicalSociety           OBJECT IDENTIFIER ::= { enterprises 13908 }
cttcCentreTecnol                  OBJECT IDENTIFIER ::= { enterprises 13909 }
dasB                              OBJECT IDENTIFIER ::= { enterprises 13910 }
epsilonDoo                        OBJECT IDENTIFIER ::= { enterprises 13911 }
everestConnections                OBJECT IDENTIFIER ::= { enterprises 13912 }
evotoTeam                         OBJECT IDENTIFIER ::= { enterprises 13913 }
freakysoft                        OBJECT IDENTIFIER ::= { enterprises 13914 }
harryR                            OBJECT IDENTIFIER ::= { enterprises 13915 }
heimatDiAndreaRota                OBJECT IDENTIFIER ::= { enterprises 13916 }
hostcentric                       OBJECT IDENTIFIER ::= { enterprises 13917 }
inkasbank                         OBJECT IDENTIFIER ::= { enterprises 13918 }
instinctInternetSolutions         OBJECT IDENTIFIER ::= { enterprises 13919 }
magicHosting                      OBJECT IDENTIFIER ::= { enterprises 13920 }
nebs                              OBJECT IDENTIFIER ::= { enterprises 13921 }
nologin                           OBJECT IDENTIFIER ::= { enterprises 13922 }
peterVerhas                       OBJECT IDENTIFIER ::= { enterprises 13923 }
powell                            OBJECT IDENTIFIER ::= { enterprises 13924 }
realTimeProductions               OBJECT IDENTIFIER ::= { enterprises 13925 }
roadTechCompterSystems            OBJECT IDENTIFIER ::= { enterprises 13926 }
sccnetSOHOConsulting              OBJECT IDENTIFIER ::= { enterprises 13927 }
tcCommunications                  OBJECT IDENTIFIER ::= { enterprises 13928 }
teragenPty                        OBJECT IDENTIFIER ::= { enterprises 13929 }
theAquariusNetwork                OBJECT IDENTIFIER ::= { enterprises 13930 }
uberlanTechnologies               OBJECT IDENTIFIER ::= { enterprises 13931 }
vogonnet                          OBJECT IDENTIFIER ::= { enterprises 13932 }
alstomTransportInformationSolutionsTelecommunicationsDivision OBJECT IDENTIFIER ::= { enterprises 13933 }
micchi                            OBJECT IDENTIFIER ::= { enterprises 13934 }
comm                              OBJECT IDENTIFIER ::= { enterprises 13935 }
aegisMortgageCorp                 OBJECT IDENTIFIER ::= { enterprises 13936 }
artGlobalLimited                  OBJECT IDENTIFIER ::= { enterprises 13937 }
ashtonRaggattMcDougall            OBJECT IDENTIFIER ::= { enterprises 13938 }
automatx                          OBJECT IDENTIFIER ::= { enterprises 13939 }
coe                               OBJECT IDENTIFIER ::= { enterprises 13940 }
communicator                      OBJECT IDENTIFIER ::= { enterprises 13941 }
candera                           OBJECT IDENTIFIER ::= { enterprises 13942 }
datanet                           OBJECT IDENTIFIER ::= { enterprises 13943 }
denaliSA                          OBJECT IDENTIFIER ::= { enterprises 13944 }
deutscheForschungsgemeinschaft    OBJECT IDENTIFIER ::= { enterprises 13945 }
educationalSystems                OBJECT IDENTIFIER ::= { enterprises 13946 }
eema                              OBJECT IDENTIFIER ::= { enterprises 13947 }
exostarLLC                        OBJECT IDENTIFIER ::= { enterprises 13948 }
frankEDVSERVICEGesellschaftMbH    OBJECT IDENTIFIER ::= { enterprises 13949 }
galileo                           OBJECT IDENTIFIER ::= { enterprises 13950 }
gentekMarketing                   OBJECT IDENTIFIER ::= { enterprises 13951 }
globalSUNTECHNOLOGY               OBJECT IDENTIFIER ::= { enterprises 13952 }
heliographLimited                 OBJECT IDENTIFIER ::= { enterprises 13953 }
itGuardian                        OBJECT IDENTIFIER ::= { enterprises 13954 }
jpconsulting                      OBJECT IDENTIFIER ::= { enterprises 13955 }
katchNetwork                      OBJECT IDENTIFIER ::= { enterprises 13956 }
liquidsite                        OBJECT IDENTIFIER ::= { enterprises 13957 }
mnRamosFerreira                   OBJECT IDENTIFIER ::= { enterprises 13958 }
mlaPowerSystems                   OBJECT IDENTIFIER ::= { enterprises 13959 }
nestar                            OBJECT IDENTIFIER ::= { enterprises 13960 }
nlipDutchISPAssociation           OBJECT IDENTIFIER ::= { enterprises 13961 }
qosLabs                           OBJECT IDENTIFIER ::= { enterprises 13962 }
rvrElettronicaSpA                 OBJECT IDENTIFIER ::= { enterprises 13963 }
swcsChanPakShaSchool              OBJECT IDENTIFIER ::= { enterprises 13964 }
tpgpost                           OBJECT IDENTIFIER ::= { enterprises 13965 }
universityOfBath                  OBJECT IDENTIFIER ::= { enterprises 13966 }
vaporware                         OBJECT IDENTIFIER ::= { enterprises 13967 }
verlagFurNeueMedien               OBJECT IDENTIFIER ::= { enterprises 13968 }
voxsisInform                      OBJECT IDENTIFIER ::= { enterprises 13969 }
aerostrongScienceAndTechnologyCo  OBJECT IDENTIFIER ::= { enterprises 13970 }
chinabizoneInfomationTechnologyCo OBJECT IDENTIFIER ::= { enterprises 13971 }
vargaLimited                      OBJECT IDENTIFIER ::= { enterprises 13972 }
investirPublications              OBJECT IDENTIFIER ::= { enterprises 13973 }
epigenomicsAG                     OBJECT IDENTIFIER ::= { enterprises 13974 }
navalGlobalDirectoryService       OBJECT IDENTIFIER ::= { enterprises 13975 }
interaktivnaConsulting            OBJECT IDENTIFIER ::= { enterprises 13976 }
shayneENTERPRISES                 OBJECT IDENTIFIER ::= { enterprises 13977 }
guardednet                        OBJECT IDENTIFIER ::= { enterprises 13978 }
compucs                           OBJECT IDENTIFIER ::= { enterprises 13979 }
platinumWebPages                  OBJECT IDENTIFIER ::= { enterprises 13980 }
ingchem                           OBJECT IDENTIFIER ::= { enterprises 13981 }
fibrespeed                        OBJECT IDENTIFIER ::= { enterprises 13982 }
wwrDevelopment                    OBJECT IDENTIFIER ::= { enterprises 13983 }
cybrickInformationSystems         OBJECT IDENTIFIER ::= { enterprises 13984 }
taeKWANGINDUSTRIALCO              OBJECT IDENTIFIER ::= { enterprises 13985 }
larryDrummond                     OBJECT IDENTIFIER ::= { enterprises 13986 }
cPlath                            OBJECT IDENTIFIER ::= { enterprises 13987 }
teleAkademieDerFachhochschuleFurtwangen OBJECT IDENTIFIER ::= { enterprises 13988 }
markusHeidenSAPECConsulting       OBJECT IDENTIFIER ::= { enterprises 13989 }
colomaCommunitySchools            OBJECT IDENTIFIER ::= { enterprises 13990 }
accellenceTechnologies            OBJECT IDENTIFIER ::= { enterprises 13991 }
mNetSys                           OBJECT IDENTIFIER ::= { enterprises 13992 }
itworx                            OBJECT IDENTIFIER ::= { enterprises 13993 }
stnATLASElektronik                OBJECT IDENTIFIER ::= { enterprises 13994 }
amperion                          OBJECT IDENTIFIER ::= { enterprises 13995 }
kbox                              OBJECT IDENTIFIER ::= { enterprises 13996 }
invisibleIndustries               OBJECT IDENTIFIER ::= { enterprises 13997 }
conceptualMindWorks               OBJECT IDENTIFIER ::= { enterprises 13998 }
itsnotacom                        OBJECT IDENTIFIER ::= { enterprises 13999 }
interzone                         OBJECT IDENTIFIER ::= { enterprises 14000 }
drsFlightSafetyAndCommunications  OBJECT IDENTIFIER ::= { enterprises 14001 }
universityOfWisconsinWhitewater   OBJECT IDENTIFIER ::= { enterprises 14002 }
saintMary                         OBJECT IDENTIFIER ::= { enterprises 14003 }
gap                               OBJECT IDENTIFIER ::= { enterprises 14004 }
kelly                             OBJECT IDENTIFIER ::= { enterprises 14005 }
thomasMelzerSoftwareentwicklung   OBJECT IDENTIFIER ::= { enterprises 14006 }
impactScienceAndTechnology        OBJECT IDENTIFIER ::= { enterprises 14007 }
kt                                OBJECT IDENTIFIER ::= { enterprises 14008 }
onsynergySolutions                OBJECT IDENTIFIER ::= { enterprises 14009 }
cirrusRealTimeProcessing          OBJECT IDENTIFIER ::= { enterprises 14010 }
cyberProject                      OBJECT IDENTIFIER ::= { enterprises 14011 }
netSafeCo                         OBJECT IDENTIFIER ::= { enterprises 14012 }
tataConsultancyServices           OBJECT IDENTIFIER ::= { enterprises 14013 }
tpEmiTelSpZOo                     OBJECT IDENTIFIER ::= { enterprises 14014 }
unet                              OBJECT IDENTIFIER ::= { enterprises 14015 }
hgFrance                          OBJECT IDENTIFIER ::= { enterprises 14016 }
fachhochschuleTechnikumWien       OBJECT IDENTIFIER ::= { enterprises 14017 }
bryanBellamy                      OBJECT IDENTIFIER ::= { enterprises 14018 }
betronicDesignBV                  OBJECT IDENTIFIER ::= { enterprises 14019 }
zencod                            OBJECT IDENTIFIER ::= { enterprises 14020 }
shapers                           OBJECT IDENTIFIER ::= { enterprises 14021 }
arachne                           OBJECT IDENTIFIER ::= { enterprises 14022 }
mistralInternetGroup              OBJECT IDENTIFIER ::= { enterprises 14023 }
fiscus                            OBJECT IDENTIFIER ::= { enterprises 14024 }
landesversicherungsanstalt        OBJECT IDENTIFIER ::= { enterprises 14025 }
slapdnet                          OBJECT IDENTIFIER ::= { enterprises 14026 }
rivernorthSystems                 OBJECT IDENTIFIER ::= { enterprises 14027 }
realTimeEngineering               OBJECT IDENTIFIER ::= { enterprises 14028 }
netzwerkLehmann                   OBJECT IDENTIFIER ::= { enterprises 14029 }
smartologyVof                     OBJECT IDENTIFIER ::= { enterprises 14030 }
statoMAGGIOREDIFESAREPARTOTEI     OBJECT IDENTIFIER ::= { enterprises 14031 }
sunyGeneseo                       OBJECT IDENTIFIER ::= { enterprises 14032 }
samartInternetCo                  OBJECT IDENTIFIER ::= { enterprises 14033 }
ouArtaxis                         OBJECT IDENTIFIER ::= { enterprises 14034 }
cyberstar                         OBJECT IDENTIFIER ::= { enterprises 14035 }
linecom                           OBJECT IDENTIFIER ::= { enterprises 14036 }
dasw-lab                          OBJECT IDENTIFIER ::= { enterprises 14037 }
karnsTechnology                   OBJECT IDENTIFIER ::= { enterprises 14038 }
gaglianoAndCia                    OBJECT IDENTIFIER ::= { enterprises 14039 }
brandaTech                        OBJECT IDENTIFIER ::= { enterprises 14040 }
railwayInformationSystemsCo       OBJECT IDENTIFIER ::= { enterprises 14041 }
freudenbergHaushaltsprodukteKF    OBJECT IDENTIFIER ::= { enterprises 14042 }
sociedadAndaluzaParaElDesarrolloDeLaSociedadDeLaInformacion OBJECT IDENTIFIER ::= { enterprises 14043 }
kernfysischVersnellerInstituut    OBJECT IDENTIFIER ::= { enterprises 14044 }
iserve                            OBJECT IDENTIFIER ::= { enterprises 14045 }
statensBostadsfinansieringsAB     OBJECT IDENTIFIER ::= { enterprises 14046 }
iset                              OBJECT IDENTIFIER ::= { enterprises 14047 }
lyseEnergi                        OBJECT IDENTIFIER ::= { enterprises 14048 }
proactivethoughtTechnologies      OBJECT IDENTIFIER ::= { enterprises 14049 }
desertAcademyAtSanteFe            OBJECT IDENTIFIER ::= { enterprises 14050 }
netmasterDigitalSecurity          OBJECT IDENTIFIER ::= { enterprises 14051 }
profluentSystemsAustralia         OBJECT IDENTIFIER ::= { enterprises 14052 }
prosumSolutions                   OBJECT IDENTIFIER ::= { enterprises 14053 }
fibercom                          OBJECT IDENTIFIER ::= { enterprises 14054 }
ipMobileNet                       OBJECT IDENTIFIER ::= { enterprises 14055 }
cegelec                           OBJECT IDENTIFIER ::= { enterprises 14056 }
longhillHighSchool                OBJECT IDENTIFIER ::= { enterprises 14057 }
excogitaSrl                       OBJECT IDENTIFIER ::= { enterprises 14058 }
oberoesterreichischeVersicherungAG OBJECT IDENTIFIER ::= { enterprises 14059 }
ens                               OBJECT IDENTIFIER ::= { enterprises 14060 }
conectivaSA                       OBJECT IDENTIFIER ::= { enterprises 14061 }
escritorioJuridicoAlcalaRhodeAndAsociados OBJECT IDENTIFIER ::= { enterprises 14062 }
seafireNetworks                   OBJECT IDENTIFIER ::= { enterprises 14063 }
ucBerkeleyResidentialComputing    OBJECT IDENTIFIER ::= { enterprises 14064 }
shanghaiFOCIFiberOpticCommunicationEquipments OBJECT IDENTIFIER ::= { enterprises 14065 }
pitat                             OBJECT IDENTIFIER ::= { enterprises 14066 }
alliedNetworks                    OBJECT IDENTIFIER ::= { enterprises 14067 }
teagNetkom                        OBJECT IDENTIFIER ::= { enterprises 14068 }
syngenioAG                        OBJECT IDENTIFIER ::= { enterprises 14069 }
c3t                               OBJECT IDENTIFIER ::= { enterprises 14070 }
bohrUndRohrtechnik                OBJECT IDENTIFIER ::= { enterprises 14071 }
mistralSoftwarePrivate            OBJECT IDENTIFIER ::= { enterprises 14072 }
smartTechnology                   OBJECT IDENTIFIER ::= { enterprises 14073 }
shorcanBrokers                    OBJECT IDENTIFIER ::= { enterprises 14074 }
rationalSoftwareCorporation       OBJECT IDENTIFIER ::= { enterprises 14075 }
marsh                             OBJECT IDENTIFIER ::= { enterprises 14076 }
esial                             OBJECT IDENTIFIER ::= { enterprises 14077 }
anectAS                           OBJECT IDENTIFIER ::= { enterprises 14078 }
activeTools                       OBJECT IDENTIFIER ::= { enterprises 14079 }
brivoSystems                      OBJECT IDENTIFIER ::= { enterprises 14080 }
armstrongWorldIndustries          OBJECT IDENTIFIER ::= { enterprises 14081 }
uplinkCoherentSolutions           OBJECT IDENTIFIER ::= { enterprises 14082 }
thomasEnterprises                 OBJECT IDENTIFIER ::= { enterprises 14083 }
cochranConsulting                 OBJECT IDENTIFIER ::= { enterprises 14084 }
advfncomPLC                       OBJECT IDENTIFIER ::= { enterprises 14085 }
eshaResearch                      OBJECT IDENTIFIER ::= { enterprises 14086 }
zultysTechnologies                OBJECT IDENTIFIER ::= { enterprises 14087 }
navisLLc                          OBJECT IDENTIFIER ::= { enterprises 14088 }
cityOfOntario                     OBJECT IDENTIFIER ::= { enterprises 14089 }
powerviewSystems                  OBJECT IDENTIFIER ::= { enterprises 14090 }
hawkerCollege                     OBJECT IDENTIFIER ::= { enterprises 14091 }
universityOfRhodeIsland           OBJECT IDENTIFIER ::= { enterprises 14092 }
medibaseTechnologiesCo            OBJECT IDENTIFIER ::= { enterprises 14093 }
snowBV                            OBJECT IDENTIFIER ::= { enterprises 14094 }
techdirection                     OBJECT IDENTIFIER ::= { enterprises 14095 }
forlinkSoftwareCorporation        OBJECT IDENTIFIER ::= { enterprises 14096 }
itwInformationstechnik            OBJECT IDENTIFIER ::= { enterprises 14097 }
hotelequip                        OBJECT IDENTIFIER ::= { enterprises 14098 }
butchwaxSoftware                  OBJECT IDENTIFIER ::= { enterprises 14099 }
wlanAllianceAB                    OBJECT IDENTIFIER ::= { enterprises 14100 }
datsenovEA                        OBJECT IDENTIFIER ::= { enterprises 14101 }
dacoreDatenbanksystemeAG          OBJECT IDENTIFIER ::= { enterprises 14102 }
iceSystems                        OBJECT IDENTIFIER ::= { enterprises 14103 }
tetronik                          OBJECT IDENTIFIER ::= { enterprises 14104 }
businessInteractif                OBJECT IDENTIFIER ::= { enterprises 14105 }
syndicatInterhospitalierDeBretagne OBJECT IDENTIFIER ::= { enterprises 14106 }
wienstrom                         OBJECT IDENTIFIER ::= { enterprises 14107 }
odenseKommune                     OBJECT IDENTIFIER ::= { enterprises 14108 }
jaguarCarsLimited                 OBJECT IDENTIFIER ::= { enterprises 14109 }
orimos                            OBJECT IDENTIFIER ::= { enterprises 14110 }
oxspringNetworkSolutions          OBJECT IDENTIFIER ::= { enterprises 14111 }
hzwDesign                         OBJECT IDENTIFIER ::= { enterprises 14112 }
magnetek                          OBJECT IDENTIFIER ::= { enterprises 14113 }
aeponaEngland                     OBJECT IDENTIFIER ::= { enterprises 14114 }
platespin                         OBJECT IDENTIFIER ::= { enterprises 14115 }
telecore                          OBJECT IDENTIFIER ::= { enterprises 14116 }
aostar                            OBJECT IDENTIFIER ::= { enterprises 14117 }
hanoverCollege                    OBJECT IDENTIFIER ::= { enterprises 14118 }
netlifeAG                         OBJECT IDENTIFIER ::= { enterprises 14119 }
letiferorg                        OBJECT IDENTIFIER ::= { enterprises 14120 }
stoneIT                           OBJECT IDENTIFIER ::= { enterprises 14121 }
wecaWirelessEthernetCompatibilityAlliance OBJECT IDENTIFIER ::= { enterprises 14122 }
expertcity                        OBJECT IDENTIFIER ::= { enterprises 14123 }
ukCAJNJointAstronomyCentre        OBJECT IDENTIFIER ::= { enterprises 14124 }
senaoINTERNATIONALCO              OBJECT IDENTIFIER ::= { enterprises 14125 }
newWorldPCSLimited                OBJECT IDENTIFIER ::= { enterprises 14126 }
onechannel                        OBJECT IDENTIFIER ::= { enterprises 14127 }
programmingArts                   OBJECT IDENTIFIER ::= { enterprises 14128 }
sevanNetworks                     OBJECT IDENTIFIER ::= { enterprises 14129 }
bifco                             OBJECT IDENTIFIER ::= { enterprises 14130 }
ifoundrySystems                   OBJECT IDENTIFIER ::= { enterprises 14131 }
csSystemesD                       OBJECT IDENTIFIER ::= { enterprises 14132 }
buergernetzWeihenstephanEV        OBJECT IDENTIFIER ::= { enterprises 14133 }
universityOfSzeged                OBJECT IDENTIFIER ::= { enterprises 14134 }
sysdm                             OBJECT IDENTIFIER ::= { enterprises 14135 }
pontonConsulting                  OBJECT IDENTIFIER ::= { enterprises 14136 }
karis                             OBJECT IDENTIFIER ::= { enterprises 14137 }
tgm                               OBJECT IDENTIFIER ::= { enterprises 14138 }
cityOfNottinghamCouncil           OBJECT IDENTIFIER ::= { enterprises 14139 }
fachhochschuleLippeUndHoexter     OBJECT IDENTIFIER ::= { enterprises 14140 }
ereca                             OBJECT IDENTIFIER ::= { enterprises 14141 }
alpware                           OBJECT IDENTIFIER ::= { enterprises 14142 }
fimosschoberAndHartlOEG           OBJECT IDENTIFIER ::= { enterprises 14143 }
malkomSJ                          OBJECT IDENTIFIER ::= { enterprises 14144 }
societyForHumanityAndInternationalTrancendentalism OBJECT IDENTIFIER ::= { enterprises 14145 }
blackboxConsultingCorporation     OBJECT IDENTIFIER ::= { enterprises 14146 }
fermiNationalAcceleratorLaboratory OBJECT IDENTIFIER ::= { enterprises 14147 }
officinaDiIdee                    OBJECT IDENTIFIER ::= { enterprises 14148 }
waddellAndReedServices            OBJECT IDENTIFIER ::= { enterprises 14149 }
transactionAuditingGroup          OBJECT IDENTIFIER ::= { enterprises 14150 }
splentec                          OBJECT IDENTIFIER ::= { enterprises 14151 }
dyncorpSystemsAndSolutions        OBJECT IDENTIFIER ::= { enterprises 14152 }
sigmaSaA                          OBJECT IDENTIFIER ::= { enterprises 14153 }
ntkoNetworkCo                     OBJECT IDENTIFIER ::= { enterprises 14154 }
tilTECHNOLOGIES                   OBJECT IDENTIFIER ::= { enterprises 14155 }
universityOfReading               OBJECT IDENTIFIER ::= { enterprises 14156 }
fhlbankTopeka                     OBJECT IDENTIFIER ::= { enterprises 14157 }
consultoriaYEstrategiaElectr      OBJECT IDENTIFIER ::= { enterprises 14158 }
fluent                            OBJECT IDENTIFIER ::= { enterprises 14159 }
tribuneInteractive                OBJECT IDENTIFIER ::= { enterprises 14160 }
epcnet                            OBJECT IDENTIFIER ::= { enterprises 14161 }
itSolution                        OBJECT IDENTIFIER ::= { enterprises 14162 }
sagaDC                            OBJECT IDENTIFIER ::= { enterprises 14163 }
sanavigator                       OBJECT IDENTIFIER ::= { enterprises 14164 }
iready                            OBJECT IDENTIFIER ::= { enterprises 14165 }
savisoConsulting                  OBJECT IDENTIFIER ::= { enterprises 14166 }
seattleUniversity                 OBJECT IDENTIFIER ::= { enterprises 14167 }
owlRiverCompany                   OBJECT IDENTIFIER ::= { enterprises 14168 }
informedia                        OBJECT IDENTIFIER ::= { enterprises 14169 }
australianResearchCentreForMedicalEngineering OBJECT IDENTIFIER ::= { enterprises 14170 }
memorialUniversityOfNewfoundland  OBJECT IDENTIFIER ::= { enterprises 14171 }
bocaSoftware                      OBJECT IDENTIFIER ::= { enterprises 14172 }
etri                              OBJECT IDENTIFIER ::= { enterprises 14173 }
softforumCo                       OBJECT IDENTIFIER ::= { enterprises 14174 }
hospitalLaFe                      OBJECT IDENTIFIER ::= { enterprises 14175 }
katholiekeHogeschoolLeuven        OBJECT IDENTIFIER ::= { enterprises 14176 }
implementa                        OBJECT IDENTIFIER ::= { enterprises 14177 }
jniCorporation                    OBJECT IDENTIFIER ::= { enterprises 14178 }
airespace                         OBJECT IDENTIFIER ::= { enterprises 14179 }
dsConsulting                      OBJECT IDENTIFIER ::= { enterprises 14180 }
cygnusTechnologies                OBJECT IDENTIFIER ::= { enterprises 14181 }
globallocate                      OBJECT IDENTIFIER ::= { enterprises 14182 }
arezzoTelecomunicazioniSrl        OBJECT IDENTIFIER ::= { enterprises 14183 }
getabiggerNetwork                 OBJECT IDENTIFIER ::= { enterprises 14184 }
cyberSERVICE                      OBJECT IDENTIFIER ::= { enterprises 14185 }
gallantTechnologies               OBJECT IDENTIFIER ::= { enterprises 14186 }
chinaNetcomCorporation            OBJECT IDENTIFIER ::= { enterprises 14187 }
thomasKWilliams                   OBJECT IDENTIFIER ::= { enterprises 14188 }
probusinessAG                     OBJECT IDENTIFIER ::= { enterprises 14189 }
westernOutdoorInteractive         OBJECT IDENTIFIER ::= { enterprises 14190 }
mnofbb                            OBJECT IDENTIFIER ::= { enterprises 14191 }
graniteTechnologies               OBJECT IDENTIFIER ::= { enterprises 14192 }
strabon                           OBJECT IDENTIFIER ::= { enterprises 14193 }
ministryOfSocialDevelopment       OBJECT IDENTIFIER ::= { enterprises 14194 }
nowSoftware                       OBJECT IDENTIFIER ::= { enterprises 14195 }
californiaStateUniversity4        OBJECT IDENTIFIER ::= { enterprises 14196 }
sisnemaInformatica                OBJECT IDENTIFIER ::= { enterprises 14197 }
pannawayTechnologies              OBJECT IDENTIFIER ::= { enterprises 14198 }
accelrys                          OBJECT IDENTIFIER ::= { enterprises 14199 }
hclComnet                         OBJECT IDENTIFIER ::= { enterprises 14200 }
daxworld                          OBJECT IDENTIFIER ::= { enterprises 14201 }
dottechInternational              OBJECT IDENTIFIER ::= { enterprises 14202 }
aql                               OBJECT IDENTIFIER ::= { enterprises 14203 }
reksoft                           OBJECT IDENTIFIER ::= { enterprises 14204 }
maiInsuranceBrokers               OBJECT IDENTIFIER ::= { enterprises 14205 }
informatieBeheerGroep             OBJECT IDENTIFIER ::= { enterprises 14206 }
leroySomer                        OBJECT IDENTIFIER ::= { enterprises 14207 }
openwide                          OBJECT IDENTIFIER ::= { enterprises 14208 }
accellent                         OBJECT IDENTIFIER ::= { enterprises 14209 }
theStoryteller                    OBJECT IDENTIFIER ::= { enterprises 14210 }
tiffanyAndCompany                 OBJECT IDENTIFIER ::= { enterprises 14211 }
universitaetMuenchen              OBJECT IDENTIFIER ::= { enterprises 14212 }
scitechItSolutions                OBJECT IDENTIFIER ::= { enterprises 14213 }
tycoServices                      OBJECT IDENTIFIER ::= { enterprises 14214 }
interactiveVisuals                OBJECT IDENTIFIER ::= { enterprises 14215 }
sendfarTechnologyCo               OBJECT IDENTIFIER ::= { enterprises 14216 }
wuestenrotDatenservice            OBJECT IDENTIFIER ::= { enterprises 14217 }
facultesUniversitairesNotreDameDeLaPaix OBJECT IDENTIFIER ::= { enterprises 14218 }
hapagLloydContainerLinieAG        OBJECT IDENTIFIER ::= { enterprises 14219 }
akafliegMunchenEV                 OBJECT IDENTIFIER ::= { enterprises 14220 }
prodigyLabs                       OBJECT IDENTIFIER ::= { enterprises 14221 }
electricReliabilityCouncilOfTexas OBJECT IDENTIFIER ::= { enterprises 14222 }
sourcefire                        OBJECT IDENTIFIER ::= { enterprises 14223 }
softwareMachine                   OBJECT IDENTIFIER ::= { enterprises 14224 }
splACTWireless                    OBJECT IDENTIFIER ::= { enterprises 14225 }
vizafone                          OBJECT IDENTIFIER ::= { enterprises 14226 }
tamperePolytechnic                OBJECT IDENTIFIER ::= { enterprises 14227 }
flandersElectric                  OBJECT IDENTIFIER ::= { enterprises 14228 }
universityOfArkansasFayetteville  OBJECT IDENTIFIER ::= { enterprises 14229 }
engine                            OBJECT IDENTIFIER ::= { enterprises 14230 }
theShmooGroup                     OBJECT IDENTIFIER ::= { enterprises 14231 }
exelonCorporation                 OBJECT IDENTIFIER ::= { enterprises 14232 }
sonagCompany                      OBJECT IDENTIFIER ::= { enterprises 14233 }
isotomicTechnologies              OBJECT IDENTIFIER ::= { enterprises 14234 }
spincircuit                       OBJECT IDENTIFIER ::= { enterprises 14235 }
bancoDeLaRepublica                OBJECT IDENTIFIER ::= { enterprises 14236 }
sarawakInformationSystemsSdnBhd   OBJECT IDENTIFIER ::= { enterprises 14237 }
dilithiumNetworks                 OBJECT IDENTIFIER ::= { enterprises 14238 }
spriteinc                         OBJECT IDENTIFIER ::= { enterprises 14239 }
topGlobalTechnology               OBJECT IDENTIFIER ::= { enterprises 14240 }
mentorgen                         OBJECT IDENTIFIER ::= { enterprises 14241 }
aosaTelekom                       OBJECT IDENTIFIER ::= { enterprises 14242 }
rtsRealTimeComputersoftwareGesmbH OBJECT IDENTIFIER ::= { enterprises 14243 }
bjerkesetConsulting               OBJECT IDENTIFIER ::= { enterprises 14244 }
theCaudiumGroup                   OBJECT IDENTIFIER ::= { enterprises 14245 }
naturalConvergence                OBJECT IDENTIFIER ::= { enterprises 14246 }
signaflex                         OBJECT IDENTIFIER ::= { enterprises 14247 }
geminiSecuritySolutions           OBJECT IDENTIFIER ::= { enterprises 14248 }
vienneInformatique                OBJECT IDENTIFIER ::= { enterprises 14249 }
conseilGeneralDeLaVienne          OBJECT IDENTIFIER ::= { enterprises 14250 }
stellarCraft                      OBJECT IDENTIFIER ::= { enterprises 14251 }
primeSolutions                    OBJECT IDENTIFIER ::= { enterprises 14252 }
gridxpert                         OBJECT IDENTIFIER ::= { enterprises 14253 }
enhansiv                          OBJECT IDENTIFIER ::= { enterprises 14254 }
brvenikcom                        OBJECT IDENTIFIER ::= { enterprises 14255 }
arlysSA                           OBJECT IDENTIFIER ::= { enterprises 14256 }
linkMargin                        OBJECT IDENTIFIER ::= { enterprises 14257 }
northernTrustCompany              OBJECT IDENTIFIER ::= { enterprises 14258 }
groupeECEParis                    OBJECT IDENTIFIER ::= { enterprises 14259 }
linuxSystemberatung               OBJECT IDENTIFIER ::= { enterprises 14260 }
bankLeumiLeIsrael                 OBJECT IDENTIFIER ::= { enterprises 14261 }
diplIngFelixBeer                  OBJECT IDENTIFIER ::= { enterprises 14262 }
svenMeinhardtEDVService           OBJECT IDENTIFIER ::= { enterprises 14263 }
outpostSentinel                   OBJECT IDENTIFIER ::= { enterprises 14264 }
itouch                            OBJECT IDENTIFIER ::= { enterprises 14265 }
bulletproffNetworks               OBJECT IDENTIFIER ::= { enterprises 14266 }
wrjtec                            OBJECT IDENTIFIER ::= { enterprises 14267 }
projektAvalon                     OBJECT IDENTIFIER ::= { enterprises 14268 }
beijingVanlinkCommunicationCoPRChinaYu OBJECT IDENTIFIER ::= { enterprises 14269 }
technologyHackworks               OBJECT IDENTIFIER ::= { enterprises 14270 }
iliad                             OBJECT IDENTIFIER ::= { enterprises 14271 }
awoKreisverbandEssenEV            OBJECT IDENTIFIER ::= { enterprises 14272 }
ifen                              OBJECT IDENTIFIER ::= { enterprises 14273 }
bdilukaszTylski                   OBJECT IDENTIFIER ::= { enterprises 14274 }
deutscheBundeswehr                OBJECT IDENTIFIER ::= { enterprises 14275 }
osystemAB                         OBJECT IDENTIFIER ::= { enterprises 14276 }
tylerfamnet                       OBJECT IDENTIFIER ::= { enterprises 14277 }
dinx                              OBJECT IDENTIFIER ::= { enterprises 14278 }
nethereInternetServices           OBJECT IDENTIFIER ::= { enterprises 14279 }
allOpticalNetworks                OBJECT IDENTIFIER ::= { enterprises 14280 }
rcatnet                           OBJECT IDENTIFIER ::= { enterprises 14281 }
vertrian                          OBJECT IDENTIFIER ::= { enterprises 14282 }
webraska                          OBJECT IDENTIFIER ::= { enterprises 14283 }
technischeUniversitatChemnitz     OBJECT IDENTIFIER ::= { enterprises 14284 }
cegetelSI2                        OBJECT IDENTIFIER ::= { enterprises 14285 }
nvisia                            OBJECT IDENTIFIER ::= { enterprises 14286 }
aegis-net                         OBJECT IDENTIFIER ::= { enterprises 14287 }
lucterraInformatica               OBJECT IDENTIFIER ::= { enterprises 14288 }
a3Design                          OBJECT IDENTIFIER ::= { enterprises 14289 }
infocorpComputerSolutions         OBJECT IDENTIFIER ::= { enterprises 14290 }
stefanLefnaer                     OBJECT IDENTIFIER ::= { enterprises 14291 }
theDocumentAcademy                OBJECT IDENTIFIER ::= { enterprises 14292 }
aditelNv                          OBJECT IDENTIFIER ::= { enterprises 14293 }
pyramidComputerSysteme            OBJECT IDENTIFIER ::= { enterprises 14294 }
dopSystems                        OBJECT IDENTIFIER ::= { enterprises 14295 }
confmonCorp                       OBJECT IDENTIFIER ::= { enterprises 14296 }
oneteluk                          OBJECT IDENTIFIER ::= { enterprises 14297 }
controlProducts                   OBJECT IDENTIFIER ::= { enterprises 14298 }
sitesuiteAustralasia              OBJECT IDENTIFIER ::= { enterprises 14299 }
cyberSwitching                    OBJECT IDENTIFIER ::= { enterprises 14300 }
proMedicus                        OBJECT IDENTIFIER ::= { enterprises 14301 }
papinetorg                        OBJECT IDENTIFIER ::= { enterprises 14302 }
nextgen                           OBJECT IDENTIFIER ::= { enterprises 14303 }
scenpro                           OBJECT IDENTIFIER ::= { enterprises 14304 }
koraInstituteOfScienceAndTechnologyInformation OBJECT IDENTIFIER ::= { enterprises 14305 }
fociFiberOpticCommunications      OBJECT IDENTIFIER ::= { enterprises 14306 }
kawamuraElectric                  OBJECT IDENTIFIER ::= { enterprises 14307 }
rep                               OBJECT IDENTIFIER ::= { enterprises 14308 }
technischeUniversitaetClausthal   OBJECT IDENTIFIER ::= { enterprises 14309 }
adjoinSolutions                   OBJECT IDENTIFIER ::= { enterprises 14310 }
technionCommunicationsCorporation OBJECT IDENTIFIER ::= { enterprises 14311 }
skypathNetworks                   OBJECT IDENTIFIER ::= { enterprises 14312 }
procedaTecnologiaEInformaticaSA   OBJECT IDENTIFIER ::= { enterprises 14313 }
imaginet                          OBJECT IDENTIFIER ::= { enterprises 14314 }
ubservices                        OBJECT IDENTIFIER ::= { enterprises 14315 }
shanghaiHuatengSoftwareSystemCo   OBJECT IDENTIFIER ::= { enterprises 14316 }
ratwater                          OBJECT IDENTIFIER ::= { enterprises 14317 }
alstomTAndDPAndD                  OBJECT IDENTIFIER ::= { enterprises 14318 }
dddDesign                         OBJECT IDENTIFIER ::= { enterprises 14319 }
creditLyonnaisDSTIDSATPLANET      OBJECT IDENTIFIER ::= { enterprises 14320 }
techelpKy                         OBJECT IDENTIFIER ::= { enterprises 14321 }
arnoldDesignAndInformatica        OBJECT IDENTIFIER ::= { enterprises 14322 }
dennisIT                          OBJECT IDENTIFIER ::= { enterprises 14323 }
theWrittenWord                    OBJECT IDENTIFIER ::= { enterprises 14324 }
pucebaboon                        OBJECT IDENTIFIER ::= { enterprises 14325 }
siriusSatelliteRadio              OBJECT IDENTIFIER ::= { enterprises 14326 }
vaLinuxSystemsJapanKK             OBJECT IDENTIFIER ::= { enterprises 14327 }
jagProductions                    OBJECT IDENTIFIER ::= { enterprises 14328 }
timecertain                       OBJECT IDENTIFIER ::= { enterprises 14329 }
shanghaiEwaytekCo                 OBJECT IDENTIFIER ::= { enterprises 14330 }
beijingTopsecNetworkSecurityTechnologyCo OBJECT IDENTIFIER ::= { enterprises 14331 }
deadsquidCommunications           OBJECT IDENTIFIER ::= { enterprises 14332 }
phonologies                       OBJECT IDENTIFIER ::= { enterprises 14333 }
miltonKeynesCouncil               OBJECT IDENTIFIER ::= { enterprises 14334 }
econnect                          OBJECT IDENTIFIER ::= { enterprises 14335 }
theChesapeakeComputerGroup        OBJECT IDENTIFIER ::= { enterprises 14336 }
superintendenciaDeServiciosDeSalud OBJECT IDENTIFIER ::= { enterprises 14337 }
impsatSAColombia                  OBJECT IDENTIFIER ::= { enterprises 14338 }
hioptel                           OBJECT IDENTIFIER ::= { enterprises 14339 }
linuxtek                          OBJECT IDENTIFIER ::= { enterprises 14340 }
ministryOfPacificIslandAffairs    OBJECT IDENTIFIER ::= { enterprises 14341 }
netwayNetworksPty                 OBJECT IDENTIFIER ::= { enterprises 14342 }
ospreyNetworkTechnologies         OBJECT IDENTIFIER ::= { enterprises 14343 }
electronicCommerceTechnologies    OBJECT IDENTIFIER ::= { enterprises 14344 }
etg                               OBJECT IDENTIFIER ::= { enterprises 14345 }
erichJaeger                       OBJECT IDENTIFIER ::= { enterprises 14346 }
realnetKft                        OBJECT IDENTIFIER ::= { enterprises 14347 }
swistGroupTechnologies            OBJECT IDENTIFIER ::= { enterprises 14348 }
dybandCorporation                 OBJECT IDENTIFIER ::= { enterprises 14349 }
storbit                           OBJECT IDENTIFIER ::= { enterprises 14350 }
appliedEngineering                OBJECT IDENTIFIER ::= { enterprises 14351 }
pennStateUniversity               OBJECT IDENTIFIER ::= { enterprises 14352 }
alessandroBertela                 OBJECT IDENTIFIER ::= { enterprises 14353 }
menloParkPresbyterianChurch       OBJECT IDENTIFIER ::= { enterprises 14354 }
chapmanUniversity                 OBJECT IDENTIFIER ::= { enterprises 14355 }
bankOfBermuda                     OBJECT IDENTIFIER ::= { enterprises 14356 }
worldpac                          OBJECT IDENTIFIER ::= { enterprises 14357 }
snapgearPty                       OBJECT IDENTIFIER ::= { enterprises 14358 }
abacus                            OBJECT IDENTIFIER ::= { enterprises 14359 }
routrekNetworks                   OBJECT IDENTIFIER ::= { enterprises 14360 }
foresearch                        OBJECT IDENTIFIER ::= { enterprises 14361 }
telekomSlovenijeDd                OBJECT IDENTIFIER ::= { enterprises 14362 }
blueOakWireless                   OBJECT IDENTIFIER ::= { enterprises 14363 }
clg                               OBJECT IDENTIFIER ::= { enterprises 14364 }
ighEssen                          OBJECT IDENTIFIER ::= { enterprises 14365 }
energyResearchFoundation          OBJECT IDENTIFIER ::= { enterprises 14366 }
ironicDesign                      OBJECT IDENTIFIER ::= { enterprises 14367 }
publicatInternet                  OBJECT IDENTIFIER ::= { enterprises 14368 }
tsi                               OBJECT IDENTIFIER ::= { enterprises 14369 }
geotrust                          OBJECT IDENTIFIER ::= { enterprises 14370 }
iotac                             OBJECT IDENTIFIER ::= { enterprises 14371 }
universidadSimonBolivar           OBJECT IDENTIFIER ::= { enterprises 14372 }
mystrotv                          OBJECT IDENTIFIER ::= { enterprises 14373 }
internationalSoftwareSolutions    OBJECT IDENTIFIER ::= { enterprises 14374 }
wirelessServicesCorp              OBJECT IDENTIFIER ::= { enterprises 14375 }
appliedSignalTechnology           OBJECT IDENTIFIER ::= { enterprises 14376 }
coreSECURITYTECHNOLOGIES          OBJECT IDENTIFIER ::= { enterprises 14377 }
lmjncom                           OBJECT IDENTIFIER ::= { enterprises 14378 }
ambisys                           OBJECT IDENTIFIER ::= { enterprises 14379 }
ktICOM                            OBJECT IDENTIFIER ::= { enterprises 14380 }
telecis                           OBJECT IDENTIFIER ::= { enterprises 14381 }
superlongIT                       OBJECT IDENTIFIER ::= { enterprises 14382 }
openexpertisePty                  OBJECT IDENTIFIER ::= { enterprises 14383 }
romsymData                        OBJECT IDENTIFIER ::= { enterprises 14384 }
rteSoftware                       OBJECT IDENTIFIER ::= { enterprises 14385 }
solnet2                           OBJECT IDENTIFIER ::= { enterprises 14386 }
absoluteSystems                   OBJECT IDENTIFIER ::= { enterprises 14387 }
tollCollect                       OBJECT IDENTIFIER ::= { enterprises 14388 }
spiderInternetTechnologies        OBJECT IDENTIFIER ::= { enterprises 14389 }
qrsHealthcareSolutions            OBJECT IDENTIFIER ::= { enterprises 14390 }
aceSuares                         OBJECT IDENTIFIER ::= { enterprises 14391 }
siSolucoesDeInformatica           OBJECT IDENTIFIER ::= { enterprises 14392 }
prodasalCompanhiaDeProcessamentoDeDadosDeSalvador OBJECT IDENTIFIER ::= { enterprises 14393 }
newMassMedia                      OBJECT IDENTIFIER ::= { enterprises 14394 }
universityOfOregon                OBJECT IDENTIFIER ::= { enterprises 14395 }
c4net                             OBJECT IDENTIFIER ::= { enterprises 14396 }
icss                              OBJECT IDENTIFIER ::= { enterprises 14397 }
behavioralInformatics             OBJECT IDENTIFIER ::= { enterprises 14398 }
necInfrontiaCorp                  OBJECT IDENTIFIER ::= { enterprises 14399 }
venturetechsCorp                  OBJECT IDENTIFIER ::= { enterprises 14400 }
jointStockCompanyVolgatelecom     OBJECT IDENTIFIER ::= { enterprises 14401 }
universityOfGeneva                OBJECT IDENTIFIER ::= { enterprises 14402 }
gymnasiumHermannBoeseStr          OBJECT IDENTIFIER ::= { enterprises 14403 }
spediantSystems                   OBJECT IDENTIFIER ::= { enterprises 14404 }
charonSystems                     OBJECT IDENTIFIER ::= { enterprises 14405 }
unitedLandServices                OBJECT IDENTIFIER ::= { enterprises 14406 }
xidusnet                          OBJECT IDENTIFIER ::= { enterprises 14407 }
ndosaTechnologies                 OBJECT IDENTIFIER ::= { enterprises 14408 }
dcanet                            OBJECT IDENTIFIER ::= { enterprises 14409 }
tssx                              OBJECT IDENTIFIER ::= { enterprises 14410 }
beijingQXCOMMTechnologyCO         OBJECT IDENTIFIER ::= { enterprises 14411 }
europeanTransactionBankAG         OBJECT IDENTIFIER ::= { enterprises 14412 }
togewanet                         OBJECT IDENTIFIER ::= { enterprises 14413 }
regio                             OBJECT IDENTIFIER ::= { enterprises 14414 }
eMobilizer                        OBJECT IDENTIFIER ::= { enterprises 14415 }
ntl                               OBJECT IDENTIFIER ::= { enterprises 14416 }
continentaleKrankenversicherungAG OBJECT IDENTIFIER ::= { enterprises 14417 }
ciagriCentroDeInformaticaNaAgricultura OBJECT IDENTIFIER ::= { enterprises 14418 }
emigratusCommunications           OBJECT IDENTIFIER ::= { enterprises 14419 }
ltinetworkscom                    OBJECT IDENTIFIER ::= { enterprises 14420 }
mocanaCorporation                 OBJECT IDENTIFIER ::= { enterprises 14421 }
tazmenTechnologies                OBJECT IDENTIFIER ::= { enterprises 14422 }
rondosoft                         OBJECT IDENTIFIER ::= { enterprises 14423 }
humatix                           OBJECT IDENTIFIER ::= { enterprises 14424 }
telkonet                          OBJECT IDENTIFIER ::= { enterprises 14425 }
enterpriseInnovationsCorporation  OBJECT IDENTIFIER ::= { enterprises 14426 }
nactTelecommunications            OBJECT IDENTIFIER ::= { enterprises 14427 }
welstand                          OBJECT IDENTIFIER ::= { enterprises 14428 }
mcluckieAndAssociates             OBJECT IDENTIFIER ::= { enterprises 14429 }
polivec                           OBJECT IDENTIFIER ::= { enterprises 14430 }
universitasKristenKridaWacana     OBJECT IDENTIFIER ::= { enterprises 14431 }
skysoftPty                        OBJECT IDENTIFIER ::= { enterprises 14432 }
chinaFinancialCertificationAuthority OBJECT IDENTIFIER ::= { enterprises 14433 }
networkSystemsAndTechnologies     OBJECT IDENTIFIER ::= { enterprises 14434 }
vrijeUniversiteitAmsterdam        OBJECT IDENTIFIER ::= { enterprises 14435 }
quiconnectcom                     OBJECT IDENTIFIER ::= { enterprises 14436 }
baltzorg                          OBJECT IDENTIFIER ::= { enterprises 14437 }
polarlake                         OBJECT IDENTIFIER ::= { enterprises 14438 }
hitInternetTechnologiesSpA        OBJECT IDENTIFIER ::= { enterprises 14439 }
longshipScoutGroup                OBJECT IDENTIFIER ::= { enterprises 14440 }
millerZell                        OBJECT IDENTIFIER ::= { enterprises 14441 }
xybase                            OBJECT IDENTIFIER ::= { enterprises 14442 }
julySystems                       OBJECT IDENTIFIER ::= { enterprises 14443 }
redbackITPty                      OBJECT IDENTIFIER ::= { enterprises 14444 }
elecsIndustryCo                   OBJECT IDENTIFIER ::= { enterprises 14445 }
indeo                             OBJECT IDENTIFIER ::= { enterprises 14446 }
spektraGroup                      OBJECT IDENTIFIER ::= { enterprises 14447 }
iatrogenixcom                     OBJECT IDENTIFIER ::= { enterprises 14448 }
hitnetEV                          OBJECT IDENTIFIER ::= { enterprises 14449 }
twicom                            OBJECT IDENTIFIER ::= { enterprises 14450 }
industrialComputing               OBJECT IDENTIFIER ::= { enterprises 14451 }
everyonenet                       OBJECT IDENTIFIER ::= { enterprises 14452 }
isisNetworks                      OBJECT IDENTIFIER ::= { enterprises 14453 }
telAvivUniversity                 OBJECT IDENTIFIER ::= { enterprises 14454 }
intercontinentalexchange          OBJECT IDENTIFIER ::= { enterprises 14455 }
lemuriaAsesoresInformaticosCA     OBJECT IDENTIFIER ::= { enterprises 14456 }
lorexIndustries                   OBJECT IDENTIFIER ::= { enterprises 14457 }
ilient                            OBJECT IDENTIFIER ::= { enterprises 14458 }
hennessyDigital                   OBJECT IDENTIFIER ::= { enterprises 14459 }
bDigital                          OBJECT IDENTIFIER ::= { enterprises 14460 }
keywareSolutions                  OBJECT IDENTIFIER ::= { enterprises 14461 }
psgueCorporation                  OBJECT IDENTIFIER ::= { enterprises 14462 }
tour2000Co                        OBJECT IDENTIFIER ::= { enterprises 14463 }
valuecommerce                     OBJECT IDENTIFIER ::= { enterprises 14464 }
nocGrove                          OBJECT IDENTIFIER ::= { enterprises 14465 }
heinrichHeineUniversitaetDuesseldorf OBJECT IDENTIFIER ::= { enterprises 14466 }
stime                             OBJECT IDENTIFIER ::= { enterprises 14467 }
marconiIntegratedSystems          OBJECT IDENTIFIER ::= { enterprises 14468 }
cycloneComputerConsultants        OBJECT IDENTIFIER ::= { enterprises 14469 }
plahlKarlConsult                  OBJECT IDENTIFIER ::= { enterprises 14470 }
wasabiSystems                     OBJECT IDENTIFIER ::= { enterprises 14471 }
viaNETWORKSServicesAG             OBJECT IDENTIFIER ::= { enterprises 14472 }
queen                             OBJECT IDENTIFIER ::= { enterprises 14473 }
nextaxiomTechnology               OBJECT IDENTIFIER ::= { enterprises 14474 }
ralphDeHart                       OBJECT IDENTIFIER ::= { enterprises 14475 }
networkExecutiveSoftware          OBJECT IDENTIFIER ::= { enterprises 14476 }
relix                             OBJECT IDENTIFIER ::= { enterprises 14477 }
melbourneIT                       OBJECT IDENTIFIER ::= { enterprises 14478 }
koreaNationalDefenceUniversity    OBJECT IDENTIFIER ::= { enterprises 14479 }
norisbankAG                       OBJECT IDENTIFIER ::= { enterprises 14480 }
kobilSystems                      OBJECT IDENTIFIER ::= { enterprises 14481 }
system5                           OBJECT IDENTIFIER ::= { enterprises 14482 }
unicInternetConsulting            OBJECT IDENTIFIER ::= { enterprises 14483 }
digitalV6Corp                     OBJECT IDENTIFIER ::= { enterprises 14484 }
sanminaSCI                        OBJECT IDENTIFIER ::= { enterprises 14485 }
marlboroCollege                   OBJECT IDENTIFIER ::= { enterprises 14486 }
erkkilaConsulting                 OBJECT IDENTIFIER ::= { enterprises 14487 }
darkmist                          OBJECT IDENTIFIER ::= { enterprises 14488 }
mcgrewnet                         OBJECT IDENTIFIER ::= { enterprises 14489 }
ariadneInternetServices           OBJECT IDENTIFIER ::= { enterprises 14490 }
standardSchoolDistrict            OBJECT IDENTIFIER ::= { enterprises 14491 }
dialogueTechnologyCorporation     OBJECT IDENTIFIER ::= { enterprises 14492 }
aurigoSoftwareTechnologies        OBJECT IDENTIFIER ::= { enterprises 14493 }
aspedi                            OBJECT IDENTIFIER ::= { enterprises 14494 }
hansLie                           OBJECT IDENTIFIER ::= { enterprises 14495 }
swedishamericanHealthSystemCorporation OBJECT IDENTIFIER ::= { enterprises 14496 }
gistCommunications                OBJECT IDENTIFIER ::= { enterprises 14497 }
styleNetworks                     OBJECT IDENTIFIER ::= { enterprises 14498 }
eBank                             OBJECT IDENTIFIER ::= { enterprises 14499 }
icmWarsawUniversity               OBJECT IDENTIFIER ::= { enterprises 14500 }
blueCoatSystems                   OBJECT IDENTIFIER ::= { enterprises 14501 }
samAsherComputingServices         OBJECT IDENTIFIER ::= { enterprises 14502 }
asylumVisualEffects               OBJECT IDENTIFIER ::= { enterprises 14503 }
packetSignalCorporation           OBJECT IDENTIFIER ::= { enterprises 14504 }
spiralDesigns                     OBJECT IDENTIFIER ::= { enterprises 14505 }
ministerulAparariiNationale       OBJECT IDENTIFIER ::= { enterprises 14506 }
russianAmericanGlassCompanyRASKO  OBJECT IDENTIFIER ::= { enterprises 14507 }
teknovus                          OBJECT IDENTIFIER ::= { enterprises 14508 }
mercateoAG                        OBJECT IDENTIFIER ::= { enterprises 14509 }
astraDatentechnik                 OBJECT IDENTIFIER ::= { enterprises 14510 }
londonMetropolitanUniversity      OBJECT IDENTIFIER ::= { enterprises 14511 }
aspivia                           OBJECT IDENTIFIER ::= { enterprises 14512 }
webflex                           OBJECT IDENTIFIER ::= { enterprises 14513 }
daveSrl                           OBJECT IDENTIFIER ::= { enterprises 14514 }
genogrid                          OBJECT IDENTIFIER ::= { enterprises 14515 }
sanomaBudapestPublishing          OBJECT IDENTIFIER ::= { enterprises 14516 }
tactelAB                          OBJECT IDENTIFIER ::= { enterprises 14517 }
pihanaPacific                     OBJECT IDENTIFIER ::= { enterprises 14518 }
washingtonUniversity              OBJECT IDENTIFIER ::= { enterprises 14519 }
wolframResearch                   OBJECT IDENTIFIER ::= { enterprises 14520 }
hKMooreLimited                    OBJECT IDENTIFIER ::= { enterprises 14521 }
gviMedicalDevices                 OBJECT IDENTIFIER ::= { enterprises 14522 }
hermitorg                         OBJECT IDENTIFIER ::= { enterprises 14523 }
pharosSystems                     OBJECT IDENTIFIER ::= { enterprises 14524 }
trapezeNetworks                   OBJECT IDENTIFIER ::= { enterprises 14525 }
safenetInformatica                OBJECT IDENTIFIER ::= { enterprises 14526 }
iwiring                           OBJECT IDENTIFIER ::= { enterprises 14527 }
newlandsCollege                   OBJECT IDENTIFIER ::= { enterprises 14528 }
fhpwireless                       OBJECT IDENTIFIER ::= { enterprises 14529 }
robertBaptista                    OBJECT IDENTIFIER ::= { enterprises 14530 }
blackwellConsultingServices       OBJECT IDENTIFIER ::= { enterprises 14531 }
theAsylum                         OBJECT IDENTIFIER ::= { enterprises 14532 }
apoteketAB                        OBJECT IDENTIFIER ::= { enterprises 14533 }
schiffko                          OBJECT IDENTIFIER ::= { enterprises 14534 }
europointNetworking               OBJECT IDENTIFIER ::= { enterprises 14535 }
inceritus                         OBJECT IDENTIFIER ::= { enterprises 14536 }
tmpConsultoriaDeInformaticaSC     OBJECT IDENTIFIER ::= { enterprises 14537 }
beijingSinceTimesCommunicationCo  OBJECT IDENTIFIER ::= { enterprises 14538 }
realprogrammerscom                OBJECT IDENTIFIER ::= { enterprises 14539 }
leszekPisarek                     OBJECT IDENTIFIER ::= { enterprises 14540 }
deano                             OBJECT IDENTIFIER ::= { enterprises 14541 }
verizonESG                        OBJECT IDENTIFIER ::= { enterprises 14542 }
n30d                              OBJECT IDENTIFIER ::= { enterprises 14543 }
shanghaiPostsAndTelecommunicationsEquipmentCO OBJECT IDENTIFIER ::= { enterprises 14544 }
ict                               OBJECT IDENTIFIER ::= { enterprises 14545 }
nto                               OBJECT IDENTIFIER ::= { enterprises 14546 }
neueZurcherZeitung                OBJECT IDENTIFIER ::= { enterprises 14547 }
autovalley                        OBJECT IDENTIFIER ::= { enterprises 14548 }
awanim                            OBJECT IDENTIFIER ::= { enterprises 14549 }
metawareSpA                       OBJECT IDENTIFIER ::= { enterprises 14550 }
gsiMbH                            OBJECT IDENTIFIER ::= { enterprises 14551 }
risonCraft                        OBJECT IDENTIFIER ::= { enterprises 14552 }
daimlerchryslerCorp               OBJECT IDENTIFIER ::= { enterprises 14553 }
vuMIF                             OBJECT IDENTIFIER ::= { enterprises 14554 }
cmgcc                             OBJECT IDENTIFIER ::= { enterprises 14555 }
gravenSoftware                    OBJECT IDENTIFIER ::= { enterprises 14556 }
infowaveSoftware                  OBJECT IDENTIFIER ::= { enterprises 14557 }
sungardBSR                        OBJECT IDENTIFIER ::= { enterprises 14558 }
mondruAB                          OBJECT IDENTIFIER ::= { enterprises 14559 }
tscnet                            OBJECT IDENTIFIER ::= { enterprises 14560 }
vocentSolutions                   OBJECT IDENTIFIER ::= { enterprises 14561 }
eProjectSolutionsPte              OBJECT IDENTIFIER ::= { enterprises 14562 }
nationalInformationAndCommunicationTechnologyAustralia OBJECT IDENTIFIER ::= { enterprises 14563 }
elberscom                         OBJECT IDENTIFIER ::= { enterprises 14564 }
zForce                            OBJECT IDENTIFIER ::= { enterprises 14565 }
bmf                               OBJECT IDENTIFIER ::= { enterprises 14566 }
coventryUniversityEnterprises     OBJECT IDENTIFIER ::= { enterprises 14567 }
weiser                            OBJECT IDENTIFIER ::= { enterprises 14568 }
heidelberg                        OBJECT IDENTIFIER ::= { enterprises 14569 }
majentisTechnologies              OBJECT IDENTIFIER ::= { enterprises 14570 }
atomzCorporation                  OBJECT IDENTIFIER ::= { enterprises 14571 }
ediwise                           OBJECT IDENTIFIER ::= { enterprises 14572 }
abestResearchCorp                 OBJECT IDENTIFIER ::= { enterprises 14573 }
celliciumSA                       OBJECT IDENTIFIER ::= { enterprises 14574 }
attentionSoftware                 OBJECT IDENTIFIER ::= { enterprises 14575 }
totalNetwork                      OBJECT IDENTIFIER ::= { enterprises 14576 }
forestexpress                     OBJECT IDENTIFIER ::= { enterprises 14577 }
geacLibrarySolutions              OBJECT IDENTIFIER ::= { enterprises 14578 }
qLinuxSolutions                   OBJECT IDENTIFIER ::= { enterprises 14579 }
theManticoreGroup                 OBJECT IDENTIFIER ::= { enterprises 14580 }
manasoft                          OBJECT IDENTIFIER ::= { enterprises 14581 }
luzEngenhariaFinanceira           OBJECT IDENTIFIER ::= { enterprises 14582 }
truteqWireless                    OBJECT IDENTIFIER ::= { enterprises 14583 }
celestixNetworks                  OBJECT IDENTIFIER ::= { enterprises 14584 }
compassInternet                   OBJECT IDENTIFIER ::= { enterprises 14585 }
tmaxSoft                          OBJECT IDENTIFIER ::= { enterprises 14586 }
technologicalCentre               OBJECT IDENTIFIER ::= { enterprises 14587 }
neosymmetria                      OBJECT IDENTIFIER ::= { enterprises 14588 }
sicap                             OBJECT IDENTIFIER ::= { enterprises 14589 }
passave                           OBJECT IDENTIFIER ::= { enterprises 14590 }
nccNetworkConsulting              OBJECT IDENTIFIER ::= { enterprises 14591 }
iorangeInternetSoftwareAndService OBJECT IDENTIFIER ::= { enterprises 14592 }
dyode                             OBJECT IDENTIFIER ::= { enterprises 14593 }
rudolfBahr                        OBJECT IDENTIFIER ::= { enterprises 14594 }
billreilly                        OBJECT IDENTIFIER ::= { enterprises 14595 }
martinWismans                     OBJECT IDENTIFIER ::= { enterprises 14596 }
dolphinsearch                     OBJECT IDENTIFIER ::= { enterprises 14597 }
usds                              OBJECT IDENTIFIER ::= { enterprises 14598 }
corman                            OBJECT IDENTIFIER ::= { enterprises 14599 }
cryptallLimited                   OBJECT IDENTIFIER ::= { enterprises 14600 }
baazeecom                         OBJECT IDENTIFIER ::= { enterprises 14601 }
intervalMedia                     OBJECT IDENTIFIER ::= { enterprises 14602 }
cyberportde                       OBJECT IDENTIFIER ::= { enterprises 14603 }
commvaultSystems                  OBJECT IDENTIFIER ::= { enterprises 14604 }
wesleyanUniversity                OBJECT IDENTIFIER ::= { enterprises 14605 }
hewlettWard                       OBJECT IDENTIFIER ::= { enterprises 14606 }
futuroTechnologies                OBJECT IDENTIFIER ::= { enterprises 14607 }
transfinityCorp                   OBJECT IDENTIFIER ::= { enterprises 14608 }
toditocomSADeCV                   OBJECT IDENTIFIER ::= { enterprises 14609 }
solutionsFirst                    OBJECT IDENTIFIER ::= { enterprises 14610 }
webAlm                            OBJECT IDENTIFIER ::= { enterprises 14611 }
link                              OBJECT IDENTIFIER ::= { enterprises 14612 }
ecora                             OBJECT IDENTIFIER ::= { enterprises 14613 }
avantcomCorporation               OBJECT IDENTIFIER ::= { enterprises 14614 }
vivato                            OBJECT IDENTIFIER ::= { enterprises 14615 }
universityOfArkansasAtLittleRock  OBJECT IDENTIFIER ::= { enterprises 14616 }
dise                              OBJECT IDENTIFIER ::= { enterprises 14617 }
mennenMedical                     OBJECT IDENTIFIER ::= { enterprises 14618 }
quadrox                           OBJECT IDENTIFIER ::= { enterprises 14619 }
saintGobain                       OBJECT IDENTIFIER ::= { enterprises 14620 }
wendy                             OBJECT IDENTIFIER ::= { enterprises 14621 }
vtls                              OBJECT IDENTIFIER ::= { enterprises 14622 }
riverstyxInternet                 OBJECT IDENTIFIER ::= { enterprises 14623 }
vergerus                          OBJECT IDENTIFIER ::= { enterprises 14624 }
servecomm                         OBJECT IDENTIFIER ::= { enterprises 14625 }
applicationNetworks               OBJECT IDENTIFIER ::= { enterprises 14626 }
idtCorp                           OBJECT IDENTIFIER ::= { enterprises 14627 }
resel                             OBJECT IDENTIFIER ::= { enterprises 14628 }
sourcetechAB                      OBJECT IDENTIFIER ::= { enterprises 14629 }
binarySystems                     OBJECT IDENTIFIER ::= { enterprises 14630 }
americanInstituteOfPhysics        OBJECT IDENTIFIER ::= { enterprises 14631 }
viaInternaathional                OBJECT IDENTIFIER ::= { enterprises 14632 }
nuberry                           OBJECT IDENTIFIER ::= { enterprises 14633 }
itoolSystems                      OBJECT IDENTIFIER ::= { enterprises 14634 }
daviesco                          OBJECT IDENTIFIER ::= { enterprises 14635 }
ontainCorporation                 OBJECT IDENTIFIER ::= { enterprises 14636 }
solectron                         OBJECT IDENTIFIER ::= { enterprises 14637 }
concurrentRealityPty              OBJECT IDENTIFIER ::= { enterprises 14638 }
hxtp                              OBJECT IDENTIFIER ::= { enterprises 14639 }
wurleySolutions                   OBJECT IDENTIFIER ::= { enterprises 14640 }
raymondJamesFinancial             OBJECT IDENTIFIER ::= { enterprises 14641 }
com                               OBJECT IDENTIFIER ::= { enterprises 14642 }
futureBeacon                      OBJECT IDENTIFIER ::= { enterprises 14643 }
hiflycomCorp                      OBJECT IDENTIFIER ::= { enterprises 14644 }
wIbedaHighTechDevelopCo           OBJECT IDENTIFIER ::= { enterprises 14645 }
buptnkl                           OBJECT IDENTIFIER ::= { enterprises 14646 }
rossberryConsulting               OBJECT IDENTIFIER ::= { enterprises 14647 }
surfnshopECommerce                OBJECT IDENTIFIER ::= { enterprises 14648 }
holleyismcom                      OBJECT IDENTIFIER ::= { enterprises 14649 }
leadUpSoftwarePty                 OBJECT IDENTIFIER ::= { enterprises 14650 }
tSystemsGNFSN                     OBJECT IDENTIFIER ::= { enterprises 14651 }
universityOfStThomas              OBJECT IDENTIFIER ::= { enterprises 14652 }
metawaysInfosystems               OBJECT IDENTIFIER ::= { enterprises 14653 }
muzo                              OBJECT IDENTIFIER ::= { enterprises 14654 }
gatespace                         OBJECT IDENTIFIER ::= { enterprises 14655 }
itSA                              OBJECT IDENTIFIER ::= { enterprises 14656 }
universita                        OBJECT IDENTIFIER ::= { enterprises 14657 }
dieterKluenterSystemBeratung      OBJECT IDENTIFIER ::= { enterprises 14658 }
vividlinkDetlefIngendorf          OBJECT IDENTIFIER ::= { enterprises 14659 }
fachhochschuleWiesbaden           OBJECT IDENTIFIER ::= { enterprises 14660 }
kavEMB                            OBJECT IDENTIFIER ::= { enterprises 14661 }
bidOwlBildungImDialogOstwestfalenLippe OBJECT IDENTIFIER ::= { enterprises 14662 }
ixifLimited                       OBJECT IDENTIFIER ::= { enterprises 14663 }
initSystems                       OBJECT IDENTIFIER ::= { enterprises 14664 }
comlabTelecommunications          OBJECT IDENTIFIER ::= { enterprises 14665 }
mcleodLakeIndianBand              OBJECT IDENTIFIER ::= { enterprises 14666 }
nextiraoneLLC                     OBJECT IDENTIFIER ::= { enterprises 14667 }
intelligentCompressionTechnologies OBJECT IDENTIFIER ::= { enterprises 14668 }
systemhausXTeam                   OBJECT IDENTIFIER ::= { enterprises 14669 }
mtxNetworks                       OBJECT IDENTIFIER ::= { enterprises 14670 }
genfourCommunications             OBJECT IDENTIFIER ::= { enterprises 14671 }
datamaxxAppliedTechnologies       OBJECT IDENTIFIER ::= { enterprises 14672 }
prefeituraMunicipalDeAlegrete     OBJECT IDENTIFIER ::= { enterprises 14673 }
infoqualityConsultoriaEmInform    OBJECT IDENTIFIER ::= { enterprises 14674 }
centellKingdomTechnologiesCorporationShanghaiBranch OBJECT IDENTIFIER ::= { enterprises 14675 }
obsidianSystems                   OBJECT IDENTIFIER ::= { enterprises 14676 }
geekhosting                       OBJECT IDENTIFIER ::= { enterprises 14677 }
bfwInformationssysteme            OBJECT IDENTIFIER ::= { enterprises 14678 }
hansardInternational              OBJECT IDENTIFIER ::= { enterprises 14679 }
brightGrey                        OBJECT IDENTIFIER ::= { enterprises 14680 }
institutFuerRechnernetzeUndTelekommunikationProfDrWKowalk OBJECT IDENTIFIER ::= { enterprises 14681 }
asoposDeVliet                     OBJECT IDENTIFIER ::= { enterprises 14682 }
centellKingdomTechnologiesCorporationShanghai OBJECT IDENTIFIER ::= { enterprises 14683 }
systemManagementNetwork           OBJECT IDENTIFIER ::= { enterprises 14684 }
datapowerTechnology               OBJECT IDENTIFIER ::= { enterprises 14685 }
megasoftLimited                   OBJECT IDENTIFIER ::= { enterprises 14686 }
halionSystems                     OBJECT IDENTIFIER ::= { enterprises 14687 }
systemsExperience                 OBJECT IDENTIFIER ::= { enterprises 14688 }
urbancodeSoftwareDevelopment      OBJECT IDENTIFIER ::= { enterprises 14689 }
greymoose                         OBJECT IDENTIFIER ::= { enterprises 14690 }
fingerlos                         OBJECT IDENTIFIER ::= { enterprises 14691 }
integratorsAG                     OBJECT IDENTIFIER ::= { enterprises 14692 }
cislSystems                       OBJECT IDENTIFIER ::= { enterprises 14693 }
bmdWirelessAG                     OBJECT IDENTIFIER ::= { enterprises 14694 }
herrmannsdoerferSoftwareEntwicklung OBJECT IDENTIFIER ::= { enterprises 14695 }
absolutOK                         OBJECT IDENTIFIER ::= { enterprises 14696 }
rrdtool                           OBJECT IDENTIFIER ::= { enterprises 14697 }
csri                              OBJECT IDENTIFIER ::= { enterprises 14698 }
hagenSoftware                     OBJECT IDENTIFIER ::= { enterprises 14699 }
frontiertech                      OBJECT IDENTIFIER ::= { enterprises 14700 }
persistTechnologies               OBJECT IDENTIFIER ::= { enterprises 14701 }
neusoftDigitalMedicalSystemCO     OBJECT IDENTIFIER ::= { enterprises 14702 }
miyakawaELECTRICWORKSLTD          OBJECT IDENTIFIER ::= { enterprises 14703 }
pingosEV                          OBJECT IDENTIFIER ::= { enterprises 14704 }
provinceOfBritishColumbia         OBJECT IDENTIFIER ::= { enterprises 14705 }
sfloworg                          OBJECT IDENTIFIER ::= { enterprises 14706 }
tataraSystems                     OBJECT IDENTIFIER ::= { enterprises 14707 }
gracelandUniversity               OBJECT IDENTIFIER ::= { enterprises 14708 }
reactivity                        OBJECT IDENTIFIER ::= { enterprises 14709 }
tauaBiomatica                     OBJECT IDENTIFIER ::= { enterprises 14710 }
vakaTechnologyLimited             OBJECT IDENTIFIER ::= { enterprises 14711 }
saschaGrowe                       OBJECT IDENTIFIER ::= { enterprises 14712 }
blacksburgElectronicVillage       OBJECT IDENTIFIER ::= { enterprises 14713 }
questraCorporation                OBJECT IDENTIFIER ::= { enterprises 14714 }
manystreams                       OBJECT IDENTIFIER ::= { enterprises 14715 }
britishColumbiaInstituteOfTechnology OBJECT IDENTIFIER ::= { enterprises 14716 }
sunhostingCompany                 OBJECT IDENTIFIER ::= { enterprises 14717 }
bkitGruppenAB                     OBJECT IDENTIFIER ::= { enterprises 14718 }
harmonyGoldOperations             OBJECT IDENTIFIER ::= { enterprises 14719 }
hdInfo                            OBJECT IDENTIFIER ::= { enterprises 14720 }
techemAG                          OBJECT IDENTIFIER ::= { enterprises 14721 }
peterShillan                      OBJECT IDENTIFIER ::= { enterprises 14722 }
canalSystems                      OBJECT IDENTIFIER ::= { enterprises 14723 }
businessObjects                   OBJECT IDENTIFIER ::= { enterprises 14724 }
samSolutions                      OBJECT IDENTIFIER ::= { enterprises 14725 }
serverSideSA                      OBJECT IDENTIFIER ::= { enterprises 14726 }
henrikEdlund                      OBJECT IDENTIFIER ::= { enterprises 14727 }
pronetSpJ                         OBJECT IDENTIFIER ::= { enterprises 14728 }
innerwall                         OBJECT IDENTIFIER ::= { enterprises 14729 }
telecomItaliaLab                  OBJECT IDENTIFIER ::= { enterprises 14730 }
christianKuelker                  OBJECT IDENTIFIER ::= { enterprises 14731 }
nodotsDevelopment                 OBJECT IDENTIFIER ::= { enterprises 14732 }
yaskawaINFORMATIONSYSTEMSCorporation OBJECT IDENTIFIER ::= { enterprises 14733 }
flowCommunications                OBJECT IDENTIFIER ::= { enterprises 14734 }
esoo                              OBJECT IDENTIFIER ::= { enterprises 14735 }
ghipSystems                       OBJECT IDENTIFIER ::= { enterprises 14736 }
globalGridForum                   OBJECT IDENTIFIER ::= { enterprises 14737 }
hendersonAndco                    OBJECT IDENTIFIER ::= { enterprises 14738 }
rleaguecom                        OBJECT IDENTIFIER ::= { enterprises 14739 }
techangle                         OBJECT IDENTIFIER ::= { enterprises 14740 }
catalystInternational             OBJECT IDENTIFIER ::= { enterprises 14741 }
digitalMultitools                 OBJECT IDENTIFIER ::= { enterprises 14742 }
wachoviaBank                      OBJECT IDENTIFIER ::= { enterprises 14743 }
telenovaResearchAndDevelopmentCentre OBJECT IDENTIFIER ::= { enterprises 14744 }
pumpkinNetworks                   OBJECT IDENTIFIER ::= { enterprises 14745 }
interstorm                        OBJECT IDENTIFIER ::= { enterprises 14746 }
visionInternetServices            OBJECT IDENTIFIER ::= { enterprises 14747 }
computerSupportSystemsPty         OBJECT IDENTIFIER ::= { enterprises 14748 }
universityOfRochester             OBJECT IDENTIFIER ::= { enterprises 14749 }
awareServers                      OBJECT IDENTIFIER ::= { enterprises 14750 }
skywareCommunicationsLimited      OBJECT IDENTIFIER ::= { enterprises 14751 }
prowareTechnologyCorp             OBJECT IDENTIFIER ::= { enterprises 14752 }
ppyworld                          OBJECT IDENTIFIER ::= { enterprises 14753 }
kochMikrosystemeAG                OBJECT IDENTIFIER ::= { enterprises 14754 }
lynxTechnikAG                     OBJECT IDENTIFIER ::= { enterprises 14755 }
progtec                           OBJECT IDENTIFIER ::= { enterprises 14756 }
groissInformatics                 OBJECT IDENTIFIER ::= { enterprises 14757 }
bpsCo                             OBJECT IDENTIFIER ::= { enterprises 14758 }
adesiumR                          OBJECT IDENTIFIER ::= { enterprises 14759 }
wincorNixdorfInternational        OBJECT IDENTIFIER ::= { enterprises 14760 }
ubisecureSolutions                OBJECT IDENTIFIER ::= { enterprises 14761 }
intarsysConsulting                OBJECT IDENTIFIER ::= { enterprises 14762 }
videoNetSystems                   OBJECT IDENTIFIER ::= { enterprises 14763 }
misrnet                           OBJECT IDENTIFIER ::= { enterprises 14764 }
grafixProfesionalSRL              OBJECT IDENTIFIER ::= { enterprises 14765 }
aviconsult                        OBJECT IDENTIFIER ::= { enterprises 14766 }
bwxtPANTEX                        OBJECT IDENTIFIER ::= { enterprises 14767 }
agmarine                          OBJECT IDENTIFIER ::= { enterprises 14768 }
sybariSoftware                    OBJECT IDENTIFIER ::= { enterprises 14769 }
teleportConsultingAndSystemmangement OBJECT IDENTIFIER ::= { enterprises 14770 }
computerSciencesCorporation       OBJECT IDENTIFIER ::= { enterprises 14771 }
neptuneProject                    OBJECT IDENTIFIER ::= { enterprises 14772 }
engitech                          OBJECT IDENTIFIER ::= { enterprises 14773 }
gnuInternet                       OBJECT IDENTIFIER ::= { enterprises 14774 }
peakInternet                      OBJECT IDENTIFIER ::= { enterprises 14775 }
mysticCoders                      OBJECT IDENTIFIER ::= { enterprises 14776 }
izenpeSa                          OBJECT IDENTIFIER ::= { enterprises 14777 }
gevEcoleDesMines                  OBJECT IDENTIFIER ::= { enterprises 14778 }
e2Technology                      OBJECT IDENTIFIER ::= { enterprises 14779 }
kaevee                            OBJECT IDENTIFIER ::= { enterprises 14780 }
thoughtportAuthorityOfChicacgo    OBJECT IDENTIFIER ::= { enterprises 14781 }
coleInnovations                   OBJECT IDENTIFIER ::= { enterprises 14782 }
asociacionParaLaPromocionDelArteATravesDeInternet OBJECT IDENTIFIER ::= { enterprises 14783 }
altatrust                         OBJECT IDENTIFIER ::= { enterprises 14784 }
five4321                          OBJECT IDENTIFIER ::= { enterprises 14785 }
openNetworkSolutions              OBJECT IDENTIFIER ::= { enterprises 14786 }
zymLinux                          OBJECT IDENTIFIER ::= { enterprises 14787 }
williamDPetitt                    OBJECT IDENTIFIER ::= { enterprises 14788 }
principalFinancialGroup           OBJECT IDENTIFIER ::= { enterprises 14789 }
statsbiblioteket                  OBJECT IDENTIFIER ::= { enterprises 14790 }
nakuaTechnologies                 OBJECT IDENTIFIER ::= { enterprises 14791 }
dataConseil                       OBJECT IDENTIFIER ::= { enterprises 14792 }
systemEntwicklungDietrichSchulten OBJECT IDENTIFIER ::= { enterprises 14793 }
bancoHerrero                      OBJECT IDENTIFIER ::= { enterprises 14794 }
intellocity                       OBJECT IDENTIFIER ::= { enterprises 14795 }
aucosElektronischeGeraete         OBJECT IDENTIFIER ::= { enterprises 14796 }
dynastarCommunications            OBJECT IDENTIFIER ::= { enterprises 14797 }
netdeliveryCorporation            OBJECT IDENTIFIER ::= { enterprises 14798 }
starnetServices                   OBJECT IDENTIFIER ::= { enterprises 14799 }
legraSystems                      OBJECT IDENTIFIER ::= { enterprises 14800 }
tangroSoftwareComponentsGmbh      OBJECT IDENTIFIER ::= { enterprises 14801 }
indernet                          OBJECT IDENTIFIER ::= { enterprises 14802 }
schubertInformationssysteme       OBJECT IDENTIFIER ::= { enterprises 14803 }
innotracDiagnosticsOy             OBJECT IDENTIFIER ::= { enterprises 14804 }
afp7                              OBJECT IDENTIFIER ::= { enterprises 14805 }
tadiranElectronicSystems          OBJECT IDENTIFIER ::= { enterprises 14806 }
fricNet                           OBJECT IDENTIFIER ::= { enterprises 14807 }
theSageColleges                   OBJECT IDENTIFIER ::= { enterprises 14808 }
datasulMEDSA                      OBJECT IDENTIFIER ::= { enterprises 14809 }
advancedDigitalBroadcast          OBJECT IDENTIFIER ::= { enterprises 14810 }
xilithLLC                         OBJECT IDENTIFIER ::= { enterprises 14811 }
cedarsSinaiHealthSystems          OBJECT IDENTIFIER ::= { enterprises 14812 }
fujitsuTransactionSolutions       OBJECT IDENTIFIER ::= { enterprises 14813 }
carotechnologyBV                  OBJECT IDENTIFIER ::= { enterprises 14814 }
datasulSA                         OBJECT IDENTIFIER ::= { enterprises 14815 }
thomasPolnik                      OBJECT IDENTIFIER ::= { enterprises 14816 }
rfCommunications                  OBJECT IDENTIFIER ::= { enterprises 14817 }
voiceMobility                     OBJECT IDENTIFIER ::= { enterprises 14818 }
universityOfCyprus                OBJECT IDENTIFIER ::= { enterprises 14819 }
netOutremerCaledonie              OBJECT IDENTIFIER ::= { enterprises 14820 }
stibo                             OBJECT IDENTIFIER ::= { enterprises 14821 }
fajode                            OBJECT IDENTIFIER ::= { enterprises 14822 }
arubaNetworks                     OBJECT IDENTIFIER ::= { enterprises 14823 }
centaurTechnology                 OBJECT IDENTIFIER ::= { enterprises 14824 }
aldataSolutionsSA                 OBJECT IDENTIFIER ::= { enterprises 14825 }
adageNetworks                     OBJECT IDENTIFIER ::= { enterprises 14826 }
foopeeorg                         OBJECT IDENTIFIER ::= { enterprises 14827 }
sonorysTechnology                 OBJECT IDENTIFIER ::= { enterprises 14828 }
centraSoftware                    OBJECT IDENTIFIER ::= { enterprises 14829 }
uptimeSysteml                     OBJECT IDENTIFIER ::= { enterprises 14830 }
voetterat                         OBJECT IDENTIFIER ::= { enterprises 14831 }
esoConsortium                     OBJECT IDENTIFIER ::= { enterprises 14832 }
portalSolutionsTechnology         OBJECT IDENTIFIER ::= { enterprises 14833 }
mediales                          OBJECT IDENTIFIER ::= { enterprises 14834 }
infotec                           OBJECT IDENTIFIER ::= { enterprises 14835 }
vartaMicrobattery                 OBJECT IDENTIFIER ::= { enterprises 14836 }
trenchantConsulting               OBJECT IDENTIFIER ::= { enterprises 14837 }
nationalManagementAndOrganizationSA OBJECT IDENTIFIER ::= { enterprises 14838 }
newtechBT                         OBJECT IDENTIFIER ::= { enterprises 14839 }
smartwaveSA                       OBJECT IDENTIFIER ::= { enterprises 14840 }
lea                               OBJECT IDENTIFIER ::= { enterprises 14841 }
lanergy                           OBJECT IDENTIFIER ::= { enterprises 14842 }
satnetSARL                        OBJECT IDENTIFIER ::= { enterprises 14843 }
upfrontSystems                    OBJECT IDENTIFIER ::= { enterprises 14844 }
engineeringIngegneriaInformaticaSpA OBJECT IDENTIFIER ::= { enterprises 14845 }
padtecOpticalComponentsAndSystems OBJECT IDENTIFIER ::= { enterprises 14846 }
orderOfPreachers                  OBJECT IDENTIFIER ::= { enterprises 14847 }
betterNetworks                    OBJECT IDENTIFIER ::= { enterprises 14848 }
corporateComputerServices         OBJECT IDENTIFIER ::= { enterprises 14849 }
arcSolutionsLimited               OBJECT IDENTIFIER ::= { enterprises 14850 }
storageNetworkingIndustryAssociation OBJECT IDENTIFIER ::= { enterprises 14851 }
kinpoElectronics                  OBJECT IDENTIFIER ::= { enterprises 14852 }
cipherquest                       OBJECT IDENTIFIER ::= { enterprises 14853 }
beijingHisenseDigiTechCo          OBJECT IDENTIFIER ::= { enterprises 14854 }
ceramistaRecomServiex             OBJECT IDENTIFIER ::= { enterprises 14855 }
trinitelCorporation               OBJECT IDENTIFIER ::= { enterprises 14856 }
xcatCo                            OBJECT IDENTIFIER ::= { enterprises 14857 }
azundrisConsulting                OBJECT IDENTIFIER ::= { enterprises 14858 }
lawoAG                            OBJECT IDENTIFIER ::= { enterprises 14859 }
gwsMbH                            OBJECT IDENTIFIER ::= { enterprises 14860 }
britanniaBuildingSociety          OBJECT IDENTIFIER ::= { enterprises 14861 }
ministerioDeAdministracionesP     OBJECT IDENTIFIER ::= { enterprises 14862 }
atmava                            OBJECT IDENTIFIER ::= { enterprises 14863 }
tnce                              OBJECT IDENTIFIER ::= { enterprises 14864 }
interplexTelecom                  OBJECT IDENTIFIER ::= { enterprises 14865 }
cottonwoodTechnologyGroup         OBJECT IDENTIFIER ::= { enterprises 14866 }
halcyonSoftwareLimited            OBJECT IDENTIFIER ::= { enterprises 14867 }
mavINFORMATIKA                    OBJECT IDENTIFIER ::= { enterprises 14868 }
saudiTelecom                      OBJECT IDENTIFIER ::= { enterprises 14869 }
avaya                             OBJECT IDENTIFIER ::= { enterprises 14870 }
interLandNet                      OBJECT IDENTIFIER ::= { enterprises 14871 }
avkAdherSIS                       OBJECT IDENTIFIER ::= { enterprises 14872 }
broadbandServices                 OBJECT IDENTIFIER ::= { enterprises 14873 }
rockstormTechnologyAB             OBJECT IDENTIFIER ::= { enterprises 14874 }
leadglobe                         OBJECT IDENTIFIER ::= { enterprises 14875 }
openTextCorporation               OBJECT IDENTIFIER ::= { enterprises 14876 }
plexusTechnology                  OBJECT IDENTIFIER ::= { enterprises 14877 }
vcrdev                            OBJECT IDENTIFIER ::= { enterprises 14878 }
woko                              OBJECT IDENTIFIER ::= { enterprises 14879 }
systemhausKalkhoff                OBJECT IDENTIFIER ::= { enterprises 14880 }
qunatech                          OBJECT IDENTIFIER ::= { enterprises 14881 }
smartbridges                      OBJECT IDENTIFIER ::= { enterprises 14882 }
antekNetworksINC                  OBJECT IDENTIFIER ::= { enterprises 14883 }
exelmonTechnologies               OBJECT IDENTIFIER ::= { enterprises 14884 }
polygonGroup                      OBJECT IDENTIFIER ::= { enterprises 14885 }
airCo                             OBJECT IDENTIFIER ::= { enterprises 14886 }
nomuraResearchInstitute           OBJECT IDENTIFIER ::= { enterprises 14887 }
dasWerk                           OBJECT IDENTIFIER ::= { enterprises 14888 }
openforumus                       OBJECT IDENTIFIER ::= { enterprises 14889 }
teamKonzeptInformationstechnologien OBJECT IDENTIFIER ::= { enterprises 14890 }
lawseal                           OBJECT IDENTIFIER ::= { enterprises 14891 }
netsyntSpA                        OBJECT IDENTIFIER ::= { enterprises 14892 }
noxa                              OBJECT IDENTIFIER ::= { enterprises 14893 }
teatica                           OBJECT IDENTIFIER ::= { enterprises 14894 }
propelSoftwareCorporation         OBJECT IDENTIFIER ::= { enterprises 14895 }
attingo                           OBJECT IDENTIFIER ::= { enterprises 14896 }
yorkConsulting                    OBJECT IDENTIFIER ::= { enterprises 14897 }
accessCommunications              OBJECT IDENTIFIER ::= { enterprises 14898 }
townOfSuffield                    OBJECT IDENTIFIER ::= { enterprises 14899 }
integratedConceptsInternational   OBJECT IDENTIFIER ::= { enterprises 14900 }
vodafoneLibertelNV                OBJECT IDENTIFIER ::= { enterprises 14901 }
datamark                          OBJECT IDENTIFIER ::= { enterprises 14902 }
digiroseTechnologyCo              OBJECT IDENTIFIER ::= { enterprises 14903 }
twtec                             OBJECT IDENTIFIER ::= { enterprises 14904 }
devauLemppenau                    OBJECT IDENTIFIER ::= { enterprises 14905 }
nvision                           OBJECT IDENTIFIER ::= { enterprises 14906 }
nocCCEUSP                         OBJECT IDENTIFIER ::= { enterprises 14907 }
upcast                            OBJECT IDENTIFIER ::= { enterprises 14908 }
igendaSoftware                    OBJECT IDENTIFIER ::= { enterprises 14909 }
ipSolutions                       OBJECT IDENTIFIER ::= { enterprises 14910 }
rfpDepot                          OBJECT IDENTIFIER ::= { enterprises 14911 }
smithsAerospace                   OBJECT IDENTIFIER ::= { enterprises 14912 }
retrieverCommunications           OBJECT IDENTIFIER ::= { enterprises 14913 }
vexusConsultingGroup              OBJECT IDENTIFIER ::= { enterprises 14914 }
aspireTechnologies                OBJECT IDENTIFIER ::= { enterprises 14915 }
utahInteractive                   OBJECT IDENTIFIER ::= { enterprises 14916 }
simpletech                        OBJECT IDENTIFIER ::= { enterprises 14917 }
algarTelecomLeste                 OBJECT IDENTIFIER ::= { enterprises 14918 }
singlestepTechnologies            OBJECT IDENTIFIER ::= { enterprises 14919 }
mineco                            OBJECT IDENTIFIER ::= { enterprises 14920 }
ctwComputer                       OBJECT IDENTIFIER ::= { enterprises 14921 }
realnode                          OBJECT IDENTIFIER ::= { enterprises 14922 }
abileneChristianUniversity        OBJECT IDENTIFIER ::= { enterprises 14923 }
theNewSofGroup                    OBJECT IDENTIFIER ::= { enterprises 14924 }
wavecentral                       OBJECT IDENTIFIER ::= { enterprises 14925 }
atraiacom                         OBJECT IDENTIFIER ::= { enterprises 14926 }
disc                              OBJECT IDENTIFIER ::= { enterprises 14927 }
unipulse                          OBJECT IDENTIFIER ::= { enterprises 14928 }
onscomCo                          OBJECT IDENTIFIER ::= { enterprises 14929 }
solarTelecomTechnology            OBJECT IDENTIFIER ::= { enterprises 14930 }
victoriaUniversityOfTechnology    OBJECT IDENTIFIER ::= { enterprises 14931 }
guangzhouTopTeamSoftwareTechnologyCo OBJECT IDENTIFIER ::= { enterprises 14932 }
chungYuanChristianUniversity      OBJECT IDENTIFIER ::= { enterprises 14933 }
oksijenTeknolojiGelistirmeVeBilisimSistemleri OBJECT IDENTIFIER ::= { enterprises 14934 }
fsWalkerHughesLimited             OBJECT IDENTIFIER ::= { enterprises 14935 }
eurotuxInform                     OBJECT IDENTIFIER ::= { enterprises 14936 }
itech                             OBJECT IDENTIFIER ::= { enterprises 14937 }
exacom                            OBJECT IDENTIFIER ::= { enterprises 14938 }
styleebLLC                        OBJECT IDENTIFIER ::= { enterprises 14939 }
blueCrossBlueShieldOfNorthCarolina OBJECT IDENTIFIER ::= { enterprises 14940 }
inflectionSystems                 OBJECT IDENTIFIER ::= { enterprises 14941 }
avvioNetworks                     OBJECT IDENTIFIER ::= { enterprises 14942 }
innovationDataProcessing          OBJECT IDENTIFIER ::= { enterprises 14943 }
primalTechnologies                OBJECT IDENTIFIER ::= { enterprises 14944 }
jbxDesigns                        OBJECT IDENTIFIER ::= { enterprises 14945 }
gothenburgUniversity              OBJECT IDENTIFIER ::= { enterprises 14946 }
kyrgyzRussianSlavicUniversity     OBJECT IDENTIFIER ::= { enterprises 14947 }
hungarianForeignTradeBank         OBJECT IDENTIFIER ::= { enterprises 14948 }
northCommunications               OBJECT IDENTIFIER ::= { enterprises 14949 }
serviciosDigitalesDeCertificacion OBJECT IDENTIFIER ::= { enterprises 14950 }
efacecSISTEMASDEELECTR            OBJECT IDENTIFIER ::= { enterprises 14951 }
eyeheight                         OBJECT IDENTIFIER ::= { enterprises 14952 }
serio                             OBJECT IDENTIFIER ::= { enterprises 14953 }
cingularWireless                  OBJECT IDENTIFIER ::= { enterprises 14954 }
canam                             OBJECT IDENTIFIER ::= { enterprises 14955 }
netgateSL                         OBJECT IDENTIFIER ::= { enterprises 14956 }
nissanNorthAmerica                OBJECT IDENTIFIER ::= { enterprises 14957 }
sicItServices                     OBJECT IDENTIFIER ::= { enterprises 14958 }
cbrYaz                            OBJECT IDENTIFIER ::= { enterprises 14959 }
undernet                          OBJECT IDENTIFIER ::= { enterprises 14960 }
millenniumTechnologyLimited       OBJECT IDENTIFIER ::= { enterprises 14961 }
ingosstrakh                       OBJECT IDENTIFIER ::= { enterprises 14962 }
telemetryAndCommunicationsSystems OBJECT IDENTIFIER ::= { enterprises 14963 }
cogenit                           OBJECT IDENTIFIER ::= { enterprises 14964 }
wideinfoCorporation               OBJECT IDENTIFIER ::= { enterprises 14965 }
linosPhotonics                    OBJECT IDENTIFIER ::= { enterprises 14966 }
horsfallorg                       OBJECT IDENTIFIER ::= { enterprises 14967 }
wyniwyg                           OBJECT IDENTIFIER ::= { enterprises 14968 }
columbiaUltimate                  OBJECT IDENTIFIER ::= { enterprises 14969 }
camInternet                       OBJECT IDENTIFIER ::= { enterprises 14970 }
dlhServices                       OBJECT IDENTIFIER ::= { enterprises 14971 }
jeb                               OBJECT IDENTIFIER ::= { enterprises 14972 }
deemingnet                        OBJECT IDENTIFIER ::= { enterprises 14973 }
dataTelecomO                      OBJECT IDENTIFIER ::= { enterprises 14974 }
bryTecnologiaSA                   OBJECT IDENTIFIER ::= { enterprises 14975 }
softmillennium                    OBJECT IDENTIFIER ::= { enterprises 14976 }
wuerthElektronik                  OBJECT IDENTIFIER ::= { enterprises 14977 }
commerzbankAG                     OBJECT IDENTIFIER ::= { enterprises 14978 }
coreTecCommunications             OBJECT IDENTIFIER ::= { enterprises 14979 }
guidantCorporation                OBJECT IDENTIFIER ::= { enterprises 14980 }
cogentLogicCorporation            OBJECT IDENTIFIER ::= { enterprises 14981 }
ikuSystemhausAG                   OBJECT IDENTIFIER ::= { enterprises 14982 }
woafTech                          OBJECT IDENTIFIER ::= { enterprises 14983 }
poco                              OBJECT IDENTIFIER ::= { enterprises 14984 }
hsiHuSerionHighSchool             OBJECT IDENTIFIER ::= { enterprises 14985 }
nextreamingCorporation            OBJECT IDENTIFIER ::= { enterprises 14986 }
e3networks                        OBJECT IDENTIFIER ::= { enterprises 14987 }
mikrotik                          OBJECT IDENTIFIER ::= { enterprises 14988 }
cinesiteEurope                    OBJECT IDENTIFIER ::= { enterprises 14989 }
inmMagic                          OBJECT IDENTIFIER ::= { enterprises 14990 }
resaAirportDataSystems            OBJECT IDENTIFIER ::= { enterprises 14991 }
stagira                           OBJECT IDENTIFIER ::= { enterprises 14992 }
igd                               OBJECT IDENTIFIER ::= { enterprises 14993 }
miteq                             OBJECT IDENTIFIER ::= { enterprises 14994 }
netinary                          OBJECT IDENTIFIER ::= { enterprises 14995 }
stilleDesign                      OBJECT IDENTIFIER ::= { enterprises 14996 }
sohoware                          OBJECT IDENTIFIER ::= { enterprises 14997 }
transportationSecurityAdministration OBJECT IDENTIFIER ::= { enterprises 14998 }
codesic                           OBJECT IDENTIFIER ::= { enterprises 14999 }
kontronCanada                     OBJECT IDENTIFIER ::= { enterprises 15000 }
sewardDesigns                     OBJECT IDENTIFIER ::= { enterprises 15001 }
intentionalSoftwareCorporation    OBJECT IDENTIFIER ::= { enterprises 15002 }
iponweb                           OBJECT IDENTIFIER ::= { enterprises 15003 }
ruggedcom                         OBJECT IDENTIFIER ::= { enterprises 15004 }
fibaSoftwareSrl                   OBJECT IDENTIFIER ::= { enterprises 15005 }
pwptWaskoSpZOo                    OBJECT IDENTIFIER ::= { enterprises 15006 }
metroEthernetForum                OBJECT IDENTIFIER ::= { enterprises 15007 }
tilaria                           OBJECT IDENTIFIER ::= { enterprises 15008 }
gplicity                          OBJECT IDENTIFIER ::= { enterprises 15009 }
logitel                           OBJECT IDENTIFIER ::= { enterprises 15010 }
revivio                           OBJECT IDENTIFIER ::= { enterprises 15011 }
bernardMadoffInvestmentSecurities OBJECT IDENTIFIER ::= { enterprises 15012 }
quantec                           OBJECT IDENTIFIER ::= { enterprises 15013 }
limited                           OBJECT IDENTIFIER ::= { enterprises 15014 }
integratedModularSystems          OBJECT IDENTIFIER ::= { enterprises 15015 }
nettiporttiOY                     OBJECT IDENTIFIER ::= { enterprises 15016 }
johnsHopkinsSingapore             OBJECT IDENTIFIER ::= { enterprises 15017 }
daydaySoftwareLTD                 OBJECT IDENTIFIER ::= { enterprises 15018 }
bazyISystemyBankoweSpZOo          OBJECT IDENTIFIER ::= { enterprises 15019 }
productosProfesionalesDeTelecomunicacion OBJECT IDENTIFIER ::= { enterprises 15020 }
mobidot                           OBJECT IDENTIFIER ::= { enterprises 15021 }
goldenGateUniversity              OBJECT IDENTIFIER ::= { enterprises 15022 }
tremium                           OBJECT IDENTIFIER ::= { enterprises 15023 }
tougasnet                         OBJECT IDENTIFIER ::= { enterprises 15024 }
studentersamfundetITrondhjem      OBJECT IDENTIFIER ::= { enterprises 15025 }
centreHospitalierDeRoanne         OBJECT IDENTIFIER ::= { enterprises 15026 }
seccommerceTechnologiesAG         OBJECT IDENTIFIER ::= { enterprises 15027 }
jamesCollings                     OBJECT IDENTIFIER ::= { enterprises 15028 }
jarevaTechnologies                OBJECT IDENTIFIER ::= { enterprises 15029 }
guangzhouRCOMCommunicationCo      OBJECT IDENTIFIER ::= { enterprises 15030 }
universityOfMelbourne             OBJECT IDENTIFIER ::= { enterprises 15031 }
inqgenTechnologyCo                OBJECT IDENTIFIER ::= { enterprises 15032 }
realtimeEmbeddedAB                OBJECT IDENTIFIER ::= { enterprises 15033 }
ksolutionsSpA                     OBJECT IDENTIFIER ::= { enterprises 15034 }
partnerVoxtream                   OBJECT IDENTIFIER ::= { enterprises 15035 }
logical2                          OBJECT IDENTIFIER ::= { enterprises 15036 }
shandsHealthcareAndTeachingClinics OBJECT IDENTIFIER ::= { enterprises 15037 }
charlesStarkDraperLaboratory      OBJECT IDENTIFIER ::= { enterprises 15038 }
armedia                           OBJECT IDENTIFIER ::= { enterprises 15039 }
globalAeonPty                     OBJECT IDENTIFIER ::= { enterprises 15040 }
poznanUniversityOfTechnology      OBJECT IDENTIFIER ::= { enterprises 15041 }
vsecure                           OBJECT IDENTIFIER ::= { enterprises 15042 }
jengYeTechEnterpriseCo            OBJECT IDENTIFIER ::= { enterprises 15043 }
transatel                         OBJECT IDENTIFIER ::= { enterprises 15044 }
moneyam                           OBJECT IDENTIFIER ::= { enterprises 15045 }
clickfox                          OBJECT IDENTIFIER ::= { enterprises 15046 }
javaSoftwareFoundry               OBJECT IDENTIFIER ::= { enterprises 15047 }
startekEngineering                OBJECT IDENTIFIER ::= { enterprises 15048 }
seattleCentralCommunityCollege    OBJECT IDENTIFIER ::= { enterprises 15049 }
waycomInternational               OBJECT IDENTIFIER ::= { enterprises 15050 }
finkleEnterprises                 OBJECT IDENTIFIER ::= { enterprises 15051 }
geminiTechnologies                OBJECT IDENTIFIER ::= { enterprises 15052 }
meritekSystems                    OBJECT IDENTIFIER ::= { enterprises 15053 }
passK                             OBJECT IDENTIFIER ::= { enterprises 15054 }
ikegamiTsushinkiCo                OBJECT IDENTIFIER ::= { enterprises 15055 }
anthonyhanorg                     OBJECT IDENTIFIER ::= { enterprises 15056 }
moraviapressAs                    OBJECT IDENTIFIER ::= { enterprises 15057 }
ceisec                            OBJECT IDENTIFIER ::= { enterprises 15058 }
baptisteMalguy                    OBJECT IDENTIFIER ::= { enterprises 15059 }
zentic                            OBJECT IDENTIFIER ::= { enterprises 15060 }
servusAS                          OBJECT IDENTIFIER ::= { enterprises 15061 }
millionCorporation                OBJECT IDENTIFIER ::= { enterprises 15062 }
ekoSystems                        OBJECT IDENTIFIER ::= { enterprises 15063 }
manySa                            OBJECT IDENTIFIER ::= { enterprises 15064 }
mantas                            OBJECT IDENTIFIER ::= { enterprises 15065 }
jamesRichardsonEnterprises        OBJECT IDENTIFIER ::= { enterprises 15066 }
smtms                             OBJECT IDENTIFIER ::= { enterprises 15067 }
beijingCAPEComputerSoftwareEngineeringCorp OBJECT IDENTIFIER ::= { enterprises 15068 }
elastoCentro                      OBJECT IDENTIFIER ::= { enterprises 15069 }
yescomm                           OBJECT IDENTIFIER ::= { enterprises 15070 }
frontierSolutionCo                OBJECT IDENTIFIER ::= { enterprises 15071 }
hsbBankAB                         OBJECT IDENTIFIER ::= { enterprises 15072 }
synadTechnologies                 OBJECT IDENTIFIER ::= { enterprises 15073 }
thusPlc                           OBJECT IDENTIFIER ::= { enterprises 15074 }
icom2                             OBJECT IDENTIFIER ::= { enterprises 15075 }
freseniusAG                       OBJECT IDENTIFIER ::= { enterprises 15076 }
thermeonCorporation               OBJECT IDENTIFIER ::= { enterprises 15077 }
sysnetTelematicaSrl               OBJECT IDENTIFIER ::= { enterprises 15078 }
remark-InternetLimited            OBJECT IDENTIFIER ::= { enterprises 15079 }
xaidat                            OBJECT IDENTIFIER ::= { enterprises 15080 }
screwage                          OBJECT IDENTIFIER ::= { enterprises 15081 }
careyInternational                OBJECT IDENTIFIER ::= { enterprises 15082 }
rentpaymentcom                    OBJECT IDENTIFIER ::= { enterprises 15083 }
mobileRadiusUSA                   OBJECT IDENTIFIER ::= { enterprises 15084 }
afpaDSIS                          OBJECT IDENTIFIER ::= { enterprises 15085 }
omegaTrin                         OBJECT IDENTIFIER ::= { enterprises 15086 }
projekt13                         OBJECT IDENTIFIER ::= { enterprises 15087 }
advizexTechnologiesLLC            OBJECT IDENTIFIER ::= { enterprises 15088 }
scientificSystemsCompany          OBJECT IDENTIFIER ::= { enterprises 15089 }
teamix                            OBJECT IDENTIFIER ::= { enterprises 15090 }
boydConsultingServices            OBJECT IDENTIFIER ::= { enterprises 15091 }
perfcapCorpoation                 OBJECT IDENTIFIER ::= { enterprises 15092 }
novartisInternationalAG           OBJECT IDENTIFIER ::= { enterprises 15093 }
linetecGmbh                       OBJECT IDENTIFIER ::= { enterprises 15094 }
tdcServicesAS                     OBJECT IDENTIFIER ::= { enterprises 15095 }
ag                                OBJECT IDENTIFIER ::= { enterprises 15096 }
sevenspace                        OBJECT IDENTIFIER ::= { enterprises 15097 }
smithsonianInstitution            OBJECT IDENTIFIER ::= { enterprises 15098 }
lomaLindaUniversity               OBJECT IDENTIFIER ::= { enterprises 15099 }
grupoDeArquitecturaYConcurrencia  OBJECT IDENTIFIER ::= { enterprises 15100 }
voltDeltaResources                OBJECT IDENTIFIER ::= { enterprises 15101 }
usLEC                             OBJECT IDENTIFIER ::= { enterprises 15102 }
eivd                              OBJECT IDENTIFIER ::= { enterprises 15103 }
modlinkNetworks                   OBJECT IDENTIFIER ::= { enterprises 15104 }
intraartsNewZealandLimited        OBJECT IDENTIFIER ::= { enterprises 15105 }
wificomTechnologies               OBJECT IDENTIFIER ::= { enterprises 15106 }
siraya                            OBJECT IDENTIFIER ::= { enterprises 15107 }
macaoPostESignTrustCertificationAuthority OBJECT IDENTIFIER ::= { enterprises 15108 }
psytechnics                       OBJECT IDENTIFIER ::= { enterprises 15109 }
savantisSystems                   OBJECT IDENTIFIER ::= { enterprises 15110 }
dennisEriksson                    OBJECT IDENTIFIER ::= { enterprises 15111 }
whackProductions                  OBJECT IDENTIFIER ::= { enterprises 15112 }
magtek                            OBJECT IDENTIFIER ::= { enterprises 15113 }
stabilizerAB                      OBJECT IDENTIFIER ::= { enterprises 15114 }
obviusLLc                         OBJECT IDENTIFIER ::= { enterprises 15115 }
libertyITSolutions                OBJECT IDENTIFIER ::= { enterprises 15116 }
protectionOne                     OBJECT IDENTIFIER ::= { enterprises 15117 }
westarEnergy                      OBJECT IDENTIFIER ::= { enterprises 15118 }
fidelityNationalInformationSolutions OBJECT IDENTIFIER ::= { enterprises 15119 }
crcnetWirelessNetwork             OBJECT IDENTIFIER ::= { enterprises 15120 }
mentataSystems                    OBJECT IDENTIFIER ::= { enterprises 15121 }
interfaceWebHosting               OBJECT IDENTIFIER ::= { enterprises 15122 }
fachhochschuleOldenburgOstfrieslandWilhelmshaven OBJECT IDENTIFIER ::= { enterprises 15123 }
rodanSystemsSA                    OBJECT IDENTIFIER ::= { enterprises 15124 }
vectura                           OBJECT IDENTIFIER ::= { enterprises 15125 }
cunyCIS                           OBJECT IDENTIFIER ::= { enterprises 15127 }
vergataEDVBeratung                OBJECT IDENTIFIER ::= { enterprises 15128 }
eCARD                             OBJECT IDENTIFIER ::= { enterprises 15129 }
gensSoftware                      OBJECT IDENTIFIER ::= { enterprises 15130 }
edgeaccess                        OBJECT IDENTIFIER ::= { enterprises 15131 }
sixContinentsHotels               OBJECT IDENTIFIER ::= { enterprises 15132 }
illinoisInstituteOfTechnology     OBJECT IDENTIFIER ::= { enterprises 15133 }
christianBoesch                   OBJECT IDENTIFIER ::= { enterprises 15134 }
omatis                            OBJECT IDENTIFIER ::= { enterprises 15135 }
sukumarPatel                      OBJECT IDENTIFIER ::= { enterprises 15136 }
enovia                            OBJECT IDENTIFIER ::= { enterprises 15137 }
simFreaks                         OBJECT IDENTIFIER ::= { enterprises 15138 }
landtime                          OBJECT IDENTIFIER ::= { enterprises 15139 }
yoyoweb                           OBJECT IDENTIFIER ::= { enterprises 15140 }
infotropicAB                      OBJECT IDENTIFIER ::= { enterprises 15141 }
comunicandoSociet                 OBJECT IDENTIFIER ::= { enterprises 15142 }
synergyBusinessSolutions          OBJECT IDENTIFIER ::= { enterprises 15143 }
binaryWaveTechnologies            OBJECT IDENTIFIER ::= { enterprises 15144 }
ireasoningNetworks                OBJECT IDENTIFIER ::= { enterprises 15145 }
m444Systems                       OBJECT IDENTIFIER ::= { enterprises 15146 }
hrvatskeAutocesteDoo              OBJECT IDENTIFIER ::= { enterprises 15147 }
witteveenBos                      OBJECT IDENTIFIER ::= { enterprises 15148 }
xanturycom                        OBJECT IDENTIFIER ::= { enterprises 15149 }
exosec                            OBJECT IDENTIFIER ::= { enterprises 15150 }
spyderworks                       OBJECT IDENTIFIER ::= { enterprises 15151 }
schollEngineering                 OBJECT IDENTIFIER ::= { enterprises 15152 }
dmsfactory                        OBJECT IDENTIFIER ::= { enterprises 15153 }
activiaNetworks                   OBJECT IDENTIFIER ::= { enterprises 15154 }
ipsquare                          OBJECT IDENTIFIER ::= { enterprises 15155 }
accusys                           OBJECT IDENTIFIER ::= { enterprises 15156 }
dlS                               OBJECT IDENTIFIER ::= { enterprises 15157 }
sca                               OBJECT IDENTIFIER ::= { enterprises 15158 }
ultradyne                         OBJECT IDENTIFIER ::= { enterprises 15159 }
interactiveNorthwest              OBJECT IDENTIFIER ::= { enterprises 15160 }
idealab                           OBJECT IDENTIFIER ::= { enterprises 15161 }
movilokInteractividadMovilSL      OBJECT IDENTIFIER ::= { enterprises 15162 }
netkingcallCo                     OBJECT IDENTIFIER ::= { enterprises 15163 }
openPointNetworks                 OBJECT IDENTIFIER ::= { enterprises 15164 }
ntSYSTEMS                         OBJECT IDENTIFIER ::= { enterprises 15165 }
brianBunnell                      OBJECT IDENTIFIER ::= { enterprises 15166 }
chapcom                           OBJECT IDENTIFIER ::= { enterprises 15167 }
vosslohSystemTechnik              OBJECT IDENTIFIER ::= { enterprises 15168 }
iizukaSoftwareTechnologies        OBJECT IDENTIFIER ::= { enterprises 15169 }
crinisNetworks                    OBJECT IDENTIFIER ::= { enterprises 15170 }
landmarkGraphicsCorporation       OBJECT IDENTIFIER ::= { enterprises 15171 }
supciknet                         OBJECT IDENTIFIER ::= { enterprises 15172 }
hammerheadSystems                 OBJECT IDENTIFIER ::= { enterprises 15173 }
safescryptLimited                 OBJECT IDENTIFIER ::= { enterprises 15174 }
lonnySoftware                     OBJECT IDENTIFIER ::= { enterprises 15175 }
advancedInfoServicePLC            OBJECT IDENTIFIER ::= { enterprises 15176 }
admtek                            OBJECT IDENTIFIER ::= { enterprises 15177 }
axtionSystemsCorporation          OBJECT IDENTIFIER ::= { enterprises 15178 }
seanceSoftware                    OBJECT IDENTIFIER ::= { enterprises 15179 }
cityOfBloomington                 OBJECT IDENTIFIER ::= { enterprises 15180 }
ineoquestTechnologies             OBJECT IDENTIFIER ::= { enterprises 15181 }
adsTec                            OBJECT IDENTIFIER ::= { enterprises 15182 }
objectlab                         OBJECT IDENTIFIER ::= { enterprises 15183 }
itxc                              OBJECT IDENTIFIER ::= { enterprises 15184 }
phantasiaBroadcast                OBJECT IDENTIFIER ::= { enterprises 15185 }
solumstar                         OBJECT IDENTIFIER ::= { enterprises 15186 }
nysDepartmentOfCivilService       OBJECT IDENTIFIER ::= { enterprises 15187 }
gemforSro                         OBJECT IDENTIFIER ::= { enterprises 15188 }
objectlab2                        OBJECT IDENTIFIER ::= { enterprises 15189 }
incnetworks                       OBJECT IDENTIFIER ::= { enterprises 15190 }
voicePrintInternational           OBJECT IDENTIFIER ::= { enterprises 15191 }
evergreenAssurance                OBJECT IDENTIFIER ::= { enterprises 15192 }
tacitNetworks                     OBJECT IDENTIFIER ::= { enterprises 15193 }
alanFlett                         OBJECT IDENTIFIER ::= { enterprises 15194 }
privat                            OBJECT IDENTIFIER ::= { enterprises 15195 }
liqwidNetworks                    OBJECT IDENTIFIER ::= { enterprises 15196 }
howCO                             OBJECT IDENTIFIER ::= { enterprises 15197 }
fnetCo                            OBJECT IDENTIFIER ::= { enterprises 15198 }
infologic                         OBJECT IDENTIFIER ::= { enterprises 15199 }
flexibix                          OBJECT IDENTIFIER ::= { enterprises 15200 }
upsyncSoftwareIndiaPrivate        OBJECT IDENTIFIER ::= { enterprises 15201 }
oeConsultSoftware                 OBJECT IDENTIFIER ::= { enterprises 15202 }
tdcMobileAS                       OBJECT IDENTIFIER ::= { enterprises 15203 }
mobilethinkAS                     OBJECT IDENTIFIER ::= { enterprises 15204 }
nordsanTechnologyCo               OBJECT IDENTIFIER ::= { enterprises 15205 }
visualpixSA                       OBJECT IDENTIFIER ::= { enterprises 15206 }
modul1                            OBJECT IDENTIFIER ::= { enterprises 15207 }
ombreEtPixel                      OBJECT IDENTIFIER ::= { enterprises 15208 }
precisionTherapyInternational     OBJECT IDENTIFIER ::= { enterprises 15209 }
shinkuro                          OBJECT IDENTIFIER ::= { enterprises 15210 }
northCountryInternetAccess        OBJECT IDENTIFIER ::= { enterprises 15211 }
itau                              OBJECT IDENTIFIER ::= { enterprises 15212 }
itausa                            OBJECT IDENTIFIER ::= { enterprises 15213 }
globalNetworkOperations           OBJECT IDENTIFIER ::= { enterprises 15214 }
agilejavacom                      OBJECT IDENTIFIER ::= { enterprises 15215 }
whiteRabbit                       OBJECT IDENTIFIER ::= { enterprises 15216 }
altavista                         OBJECT IDENTIFIER ::= { enterprises 15217 }
kscCommercialInternetCo           OBJECT IDENTIFIER ::= { enterprises 15218 }
sevoiCo                           OBJECT IDENTIFIER ::= { enterprises 15219 }
nvQWENTES                         OBJECT IDENTIFIER ::= { enterprises 15220 }
lorus                             OBJECT IDENTIFIER ::= { enterprises 15221 }
rastarDigitalMarketing            OBJECT IDENTIFIER ::= { enterprises 15222 }
andago                            OBJECT IDENTIFIER ::= { enterprises 15223 }
oztech                            OBJECT IDENTIFIER ::= { enterprises 15224 }
nightstarCorporation              OBJECT IDENTIFIER ::= { enterprises 15225 }
etronics                          OBJECT IDENTIFIER ::= { enterprises 15226 }
venusInfoTech                     OBJECT IDENTIFIER ::= { enterprises 15227 }
dammCellularSystemsAS             OBJECT IDENTIFIER ::= { enterprises 15228 }
tSystemsSchweizAG                 OBJECT IDENTIFIER ::= { enterprises 15229 }
securitBV                         OBJECT IDENTIFIER ::= { enterprises 15230 }
schulzEngineering                 OBJECT IDENTIFIER ::= { enterprises 15231 }
comboxFotofinder                  OBJECT IDENTIFIER ::= { enterprises 15232 }
regenative                        OBJECT IDENTIFIER ::= { enterprises 15233 }
softswitchingTechnologies         OBJECT IDENTIFIER ::= { enterprises 15234 }
xpointTechnologies                OBJECT IDENTIFIER ::= { enterprises 15235 }
rAndKGlobalBusinessServices       OBJECT IDENTIFIER ::= { enterprises 15236 }
intellingerSoftwareCorporation    OBJECT IDENTIFIER ::= { enterprises 15237 }
collinsEnterprisesLLC             OBJECT IDENTIFIER ::= { enterprises 15238 }
applicoSecurity                   OBJECT IDENTIFIER ::= { enterprises 15239 }
ahbInternetSolutions              OBJECT IDENTIFIER ::= { enterprises 15240 }
nimel                             OBJECT IDENTIFIER ::= { enterprises 15241 }
toolcaseLLC                       OBJECT IDENTIFIER ::= { enterprises 15242 }
gavLv                             OBJECT IDENTIFIER ::= { enterprises 15243 }
essentialSystems                  OBJECT IDENTIFIER ::= { enterprises 15244 }
infnis                            OBJECT IDENTIFIER ::= { enterprises 15245 }
edvBeratungAndNetzwerktechnikDiplIngMatthiasKahle OBJECT IDENTIFIER ::= { enterprises 15246 }
rocksoftLimited                   OBJECT IDENTIFIER ::= { enterprises 15247 }
quantel                           OBJECT IDENTIFIER ::= { enterprises 15248 }
xCellentTechnologies              OBJECT IDENTIFIER ::= { enterprises 15249 }
morseGroup                        OBJECT IDENTIFIER ::= { enterprises 15250 }
deutscheTelekomTCom               OBJECT IDENTIFIER ::= { enterprises 15251 }
sbAndc                            OBJECT IDENTIFIER ::= { enterprises 15252 }
ceyba                             OBJECT IDENTIFIER ::= { enterprises 15253 }
intellipoolAB                     OBJECT IDENTIFIER ::= { enterprises 15254 }
reliableControlsCorporation       OBJECT IDENTIFIER ::= { enterprises 15255 }
unitedNations                     OBJECT IDENTIFIER ::= { enterprises 15256 }
cityComputingLimited              OBJECT IDENTIFIER ::= { enterprises 15257 }
exersTechnologies                 OBJECT IDENTIFIER ::= { enterprises 15258 }
saarl                             OBJECT IDENTIFIER ::= { enterprises 15259 }
universit8                        OBJECT IDENTIFIER ::= { enterprises 15260 }
uniconSoftware                    OBJECT IDENTIFIER ::= { enterprises 15261 }
dataDisplayLimited                OBJECT IDENTIFIER ::= { enterprises 15262 }
dlrgLandesverbandRheinlandPfalz   OBJECT IDENTIFIER ::= { enterprises 15263 }
anonymizer                        OBJECT IDENTIFIER ::= { enterprises 15264 }
telelogicAB                       OBJECT IDENTIFIER ::= { enterprises 15265 }
omnibusSystems                    OBJECT IDENTIFIER ::= { enterprises 15266 }
damagePreventionSystems           OBJECT IDENTIFIER ::= { enterprises 15267 }
oyNetItBe                         OBJECT IDENTIFIER ::= { enterprises 15268 }
craniacEntertainment              OBJECT IDENTIFIER ::= { enterprises 15269 }
printcafeSoftware                 OBJECT IDENTIFIER ::= { enterprises 15270 }
oberfinanzdirektionKoblenz        OBJECT IDENTIFIER ::= { enterprises 15271 }
maatec                            OBJECT IDENTIFIER ::= { enterprises 15272 }
thePalomaGroup                    OBJECT IDENTIFIER ::= { enterprises 15273 }
paulScherrerInstitut              OBJECT IDENTIFIER ::= { enterprises 15274 }
aaeSystems                        OBJECT IDENTIFIER ::= { enterprises 15275 }
bearasp                           OBJECT IDENTIFIER ::= { enterprises 15276 }
softtreeTechnologies              OBJECT IDENTIFIER ::= { enterprises 15277 }
oblicore                          OBJECT IDENTIFIER ::= { enterprises 15278 }
wfi                               OBJECT IDENTIFIER ::= { enterprises 15279 }
relapixity                        OBJECT IDENTIFIER ::= { enterprises 15280 }
zeomegaInfotect                   OBJECT IDENTIFIER ::= { enterprises 15281 }
gcom                              OBJECT IDENTIFIER ::= { enterprises 15282 }
mikroliittiOy                     OBJECT IDENTIFIER ::= { enterprises 15283 }
postaSLOVENIJE                    OBJECT IDENTIFIER ::= { enterprises 15284 }
isolvTechnologiesCc               OBJECT IDENTIFIER ::= { enterprises 15285 }
adpm                              OBJECT IDENTIFIER ::= { enterprises 15286 }
fobTeam                           OBJECT IDENTIFIER ::= { enterprises 15287 }
registeritSpa                     OBJECT IDENTIFIER ::= { enterprises 15288 }
advancedBroadbandCommunicationsCenter OBJECT IDENTIFIER ::= { enterprises 15289 }
ordwayCenterForThePerformingArts  OBJECT IDENTIFIER ::= { enterprises 15290 }
machTechnology                    OBJECT IDENTIFIER ::= { enterprises 15291 }
americanCityBusinessJournals      OBJECT IDENTIFIER ::= { enterprises 15292 }
coderanger                        OBJECT IDENTIFIER ::= { enterprises 15293 }
epImagingConcepts                 OBJECT IDENTIFIER ::= { enterprises 15294 }
metrima                           OBJECT IDENTIFIER ::= { enterprises 15295 }
plumFinancialServicePty           OBJECT IDENTIFIER ::= { enterprises 15296 }
soneraSolutionsOy                 OBJECT IDENTIFIER ::= { enterprises 15297 }
volkswagenBank                    OBJECT IDENTIFIER ::= { enterprises 15298 }
elcoteqNetworkCorporation         OBJECT IDENTIFIER ::= { enterprises 15299 }
wirelessIndependentProviderAB     OBJECT IDENTIFIER ::= { enterprises 15300 }
kfkiRMKISzHK                      OBJECT IDENTIFIER ::= { enterprises 15301 }
galaxesolutions                   OBJECT IDENTIFIER ::= { enterprises 15302 }
accelerateITServices              OBJECT IDENTIFIER ::= { enterprises 15303 }
takeit                            OBJECT IDENTIFIER ::= { enterprises 15304 }
mbuf                              OBJECT IDENTIFIER ::= { enterprises 15305 }
mountRoyalCollege                 OBJECT IDENTIFIER ::= { enterprises 15306 }
esphion                           OBJECT IDENTIFIER ::= { enterprises 15307 }
peaceSoftware                     OBJECT IDENTIFIER ::= { enterprises 15308 }
eDynastyLimited                   OBJECT IDENTIFIER ::= { enterprises 15309 }
exodusCommunicaitons              OBJECT IDENTIFIER ::= { enterprises 15310 }
mistrustCertificationAuthority    OBJECT IDENTIFIER ::= { enterprises 15311 }
jozefStefanInstitute              OBJECT IDENTIFIER ::= { enterprises 15312 }
redlinkMediendienste              OBJECT IDENTIFIER ::= { enterprises 15313 }
itAS                              OBJECT IDENTIFIER ::= { enterprises 15314 }
internetBusinessNews              OBJECT IDENTIFIER ::= { enterprises 15315 }
hubHillSoftware                   OBJECT IDENTIFIER ::= { enterprises 15316 }
wellsFargo                        OBJECT IDENTIFIER ::= { enterprises 15317 }
edu4FranceSA                      OBJECT IDENTIFIER ::= { enterprises 15318 }
skypilotNetwork                   OBJECT IDENTIFIER ::= { enterprises 15319 }
custom7                           OBJECT IDENTIFIER ::= { enterprises 15320 }
transcor                          OBJECT IDENTIFIER ::= { enterprises 15321 }
echopassCorporation               OBJECT IDENTIFIER ::= { enterprises 15322 }
inpNet                            OBJECT IDENTIFIER ::= { enterprises 15323 }
walterEHelmkeLibrary              OBJECT IDENTIFIER ::= { enterprises 15324 }
stva                              OBJECT IDENTIFIER ::= { enterprises 15325 }
mobicusOy                         OBJECT IDENTIFIER ::= { enterprises 15326 }
haldenDataserviceAS               OBJECT IDENTIFIER ::= { enterprises 15327 }
svanbergConsulting                OBJECT IDENTIFIER ::= { enterprises 15328 }
dalianUniversityOfTechnology      OBJECT IDENTIFIER ::= { enterprises 15329 }
kleegroup                         OBJECT IDENTIFIER ::= { enterprises 15330 }
indagonOy                         OBJECT IDENTIFIER ::= { enterprises 15331 }
logicaUK                          OBJECT IDENTIFIER ::= { enterprises 15332 }
globalCommunicationTechnologies   OBJECT IDENTIFIER ::= { enterprises 15333 }
mwvcaa                            OBJECT IDENTIFIER ::= { enterprises 15334 }
itxc2                             OBJECT IDENTIFIER ::= { enterprises 15335 }
telemetAmerica                    OBJECT IDENTIFIER ::= { enterprises 15336 }
photronics                        OBJECT IDENTIFIER ::= { enterprises 15337 }
palmsource                        OBJECT IDENTIFIER ::= { enterprises 15338 }
ilseMediaGroepBv                  OBJECT IDENTIFIER ::= { enterprises 15339 }
georgeFurniture                   OBJECT IDENTIFIER ::= { enterprises 15340 }
wuhanYangtzeCommunicationsIndustryGroupCo OBJECT IDENTIFIER ::= { enterprises 15341 }
vitalectTechnologiesIndiaPvt      OBJECT IDENTIFIER ::= { enterprises 15342 }
fundacionINASMET                  OBJECT IDENTIFIER ::= { enterprises 15343 }
yomiPLC                           OBJECT IDENTIFIER ::= { enterprises 15344 }
danskR                            OBJECT IDENTIFIER ::= { enterprises 15345 }
vikingSystems                     OBJECT IDENTIFIER ::= { enterprises 15346 }
ighIngenieurgesellschaftH         OBJECT IDENTIFIER ::= { enterprises 15347 }
precisionInterop                  OBJECT IDENTIFIER ::= { enterprises 15348 }
andreasBartschITSolutions         OBJECT IDENTIFIER ::= { enterprises 15349 }
jatosoftLLC                       OBJECT IDENTIFIER ::= { enterprises 15350 }
foreverlivingcom                  OBJECT IDENTIFIER ::= { enterprises 15351 }
universityOfArkansasAtFortSmith   OBJECT IDENTIFIER ::= { enterprises 15352 }
integratedDigitalSolutions        OBJECT IDENTIFIER ::= { enterprises 15353 }
number1Customer                   OBJECT IDENTIFIER ::= { enterprises 15354 }
integan                           OBJECT IDENTIFIER ::= { enterprises 15355 }
bartnet                           OBJECT IDENTIFIER ::= { enterprises 15356 }
diversifiedSystemsResources       OBJECT IDENTIFIER ::= { enterprises 15357 }
cygnetron                         OBJECT IDENTIFIER ::= { enterprises 15358 }
multidasTechnologies              OBJECT IDENTIFIER ::= { enterprises 15359 }
centreDESANTEMENTALE              OBJECT IDENTIFIER ::= { enterprises 15360 }
rpaResearchCo                     OBJECT IDENTIFIER ::= { enterprises 15361 }
digitalOnNetCo                    OBJECT IDENTIFIER ::= { enterprises 15362 }
hotelInterski                     OBJECT IDENTIFIER ::= { enterprises 15363 }
sibsnetTechnologies               OBJECT IDENTIFIER ::= { enterprises 15364 }
infostep                          OBJECT IDENTIFIER ::= { enterprises 15365 }
dunhuangAcademy                   OBJECT IDENTIFIER ::= { enterprises 15366 }
zlantec                           OBJECT IDENTIFIER ::= { enterprises 15367 }
unixagSiegen                      OBJECT IDENTIFIER ::= { enterprises 15368 }
cititechAustralia                 OBJECT IDENTIFIER ::= { enterprises 15369 }
gigaBYTETECHNOLOGYCO              OBJECT IDENTIFIER ::= { enterprises 15370 }
horryTelephoneCooperative         OBJECT IDENTIFIER ::= { enterprises 15371 }
maxPlanckInstituteForEvolutionaryAnthropology OBJECT IDENTIFIER ::= { enterprises 15372 }
nask                              OBJECT IDENTIFIER ::= { enterprises 15373 }
enfoOy                            OBJECT IDENTIFIER ::= { enterprises 15374 }
hsbSystemhaus                     OBJECT IDENTIFIER ::= { enterprises 15375 }
deNayer                           OBJECT IDENTIFIER ::= { enterprises 15376 }
chilimoonFoundation               OBJECT IDENTIFIER ::= { enterprises 15377 }
csiPiemonte                       OBJECT IDENTIFIER ::= { enterprises 15378 }
allocity                          OBJECT IDENTIFIER ::= { enterprises 15379 }
alterpoint                        OBJECT IDENTIFIER ::= { enterprises 15380 }
wilkesUniversity                  OBJECT IDENTIFIER ::= { enterprises 15381 }
bitHosting                        OBJECT IDENTIFIER ::= { enterprises 15382 }
bluejavelin                       OBJECT IDENTIFIER ::= { enterprises 15383 }
ncarpcom                          OBJECT IDENTIFIER ::= { enterprises 15384 }
genasysIISpain                    OBJECT IDENTIFIER ::= { enterprises 15385 }
ibisTecnologiaEInformacao         OBJECT IDENTIFIER ::= { enterprises 15386 }
industriTelekomunikasiIndonesia   OBJECT IDENTIFIER ::= { enterprises 15387 }
maginetCompany                    OBJECT IDENTIFIER ::= { enterprises 15388 }
bestwayTelecom                    OBJECT IDENTIFIER ::= { enterprises 15389 }
siluCo                            OBJECT IDENTIFIER ::= { enterprises 15390 }
iei                               OBJECT IDENTIFIER ::= { enterprises 15391 }
olviko                            OBJECT IDENTIFIER ::= { enterprises 15392 }
avestapolaritAB                   OBJECT IDENTIFIER ::= { enterprises 15393 }
ptSigmaCiptaCaraka                OBJECT IDENTIFIER ::= { enterprises 15394 }
crossml                           OBJECT IDENTIFIER ::= { enterprises 15395 }
alfaAndArissBv                    OBJECT IDENTIFIER ::= { enterprises 15396 }
netintactAB                       OBJECT IDENTIFIER ::= { enterprises 15397 }
ic3sAG                            OBJECT IDENTIFIER ::= { enterprises 15398 }
universiteDePoitiers              OBJECT IDENTIFIER ::= { enterprises 15399 }
postConsultInternational          OBJECT IDENTIFIER ::= { enterprises 15400 }
eunetEDVUndInternetDienstleistungsAG OBJECT IDENTIFIER ::= { enterprises 15401 }
proximityCorp                     OBJECT IDENTIFIER ::= { enterprises 15402 }
tSystemsCSM                       OBJECT IDENTIFIER ::= { enterprises 15403 }
penteledata                       OBJECT IDENTIFIER ::= { enterprises 15404 }
comunicacionesNetPeopleCA         OBJECT IDENTIFIER ::= { enterprises 15405 }
axiomIntegration                  OBJECT IDENTIFIER ::= { enterprises 15406 }
ambicom                           OBJECT IDENTIFIER ::= { enterprises 15407 }
truecontext                       OBJECT IDENTIFIER ::= { enterprises 15408 }
customizedDatabaseSystems         OBJECT IDENTIFIER ::= { enterprises 15409 }
seawayNetworks                    OBJECT IDENTIFIER ::= { enterprises 15410 }
lasipalatsinMediakeskusOy         OBJECT IDENTIFIER ::= { enterprises 15411 }
cotagesoft                        OBJECT IDENTIFIER ::= { enterprises 15412 }
odenOdenWirelessNetworksTechnology OBJECT IDENTIFIER ::= { enterprises 15413 }
billhuslercom                     OBJECT IDENTIFIER ::= { enterprises 15414 }
openetInformationTechnology       OBJECT IDENTIFIER ::= { enterprises 15415 }
saftPowerSystems                  OBJECT IDENTIFIER ::= { enterprises 15416 }
imaInformaticaDeMunicipiosAssociados OBJECT IDENTIFIER ::= { enterprises 15417 }
forumSystems                      OBJECT IDENTIFIER ::= { enterprises 15418 }
forestSidingSupply                OBJECT IDENTIFIER ::= { enterprises 15419 }
lightsurfTechnologies             OBJECT IDENTIFIER ::= { enterprises 15420 }
chiemgauGymnasiumTraunstein       OBJECT IDENTIFIER ::= { enterprises 15421 }
artifintelligence                 OBJECT IDENTIFIER ::= { enterprises 15422 }
netspaceSolu                      OBJECT IDENTIFIER ::= { enterprises 15423 }
storeimagePrograms                OBJECT IDENTIFIER ::= { enterprises 15424 }
imagestreamInternetSolutions      OBJECT IDENTIFIER ::= { enterprises 15425 }
koreaInternetDataCenter           OBJECT IDENTIFIER ::= { enterprises 15426 }
hwaJinSeo                         OBJECT IDENTIFIER ::= { enterprises 15427 }
cybertecPty                       OBJECT IDENTIFIER ::= { enterprises 15428 }
futureComputingSolutionsIndiaPvt  OBJECT IDENTIFIER ::= { enterprises 15429 }
jinInformationSystems             OBJECT IDENTIFIER ::= { enterprises 15430 }
xionITSystemsAG                   OBJECT IDENTIFIER ::= { enterprises 15431 }
cybconIndustries                  OBJECT IDENTIFIER ::= { enterprises 15432 }
landespolizeiMecklenburgVorpommern OBJECT IDENTIFIER ::= { enterprises 15433 }
chebuctoCommunityNet              OBJECT IDENTIFIER ::= { enterprises 15434 }
worldnet21                        OBJECT IDENTIFIER ::= { enterprises 15435 }
ositools                          OBJECT IDENTIFIER ::= { enterprises 15436 }
sso                               OBJECT IDENTIFIER ::= { enterprises 15437 }
rtlTelevision                     OBJECT IDENTIFIER ::= { enterprises 15438 }
passTechnologie                   OBJECT IDENTIFIER ::= { enterprises 15439 }
zphLitex                          OBJECT IDENTIFIER ::= { enterprises 15440 }
karell                            OBJECT IDENTIFIER ::= { enterprises 15441 }
orchestelSystems                  OBJECT IDENTIFIER ::= { enterprises 15442 }
jpSync                            OBJECT IDENTIFIER ::= { enterprises 15443 }
saffronSolutions                  OBJECT IDENTIFIER ::= { enterprises 15444 }
sbs2                              OBJECT IDENTIFIER ::= { enterprises 15445 }
cyberpowerSystems                 OBJECT IDENTIFIER ::= { enterprises 15446 }
sem                               OBJECT IDENTIFIER ::= { enterprises 15447 }
damovoCeskaRepublika              OBJECT IDENTIFIER ::= { enterprises 15448 }
foursys                           OBJECT IDENTIFIER ::= { enterprises 15449 }
innominateSecurityTechnologiesAG  OBJECT IDENTIFIER ::= { enterprises 15450 }
realitateaTV                      OBJECT IDENTIFIER ::= { enterprises 15451 }
geovariances                      OBJECT IDENTIFIER ::= { enterprises 15452 }
abzNederland                      OBJECT IDENTIFIER ::= { enterprises 15453 }
arborAudioCommunications          OBJECT IDENTIFIER ::= { enterprises 15454 }
codeas                            OBJECT IDENTIFIER ::= { enterprises 15455 }
laCocina                          OBJECT IDENTIFIER ::= { enterprises 15456 }
ackernet                          OBJECT IDENTIFIER ::= { enterprises 15457 }
markMcKenzie                      OBJECT IDENTIFIER ::= { enterprises 15458 }
mSystems                          OBJECT IDENTIFIER ::= { enterprises 15459 }
orchestelSystems2                 OBJECT IDENTIFIER ::= { enterprises 15460 }
corybant                          OBJECT IDENTIFIER ::= { enterprises 15461 }
rupprechtAndPatashnickCo          OBJECT IDENTIFIER ::= { enterprises 15462 }
huronSuperiorCatholicDistrictSchoolBoard OBJECT IDENTIFIER ::= { enterprises 15463 }
muskokacom                        OBJECT IDENTIFIER ::= { enterprises 15464 }
universityOfToronto               OBJECT IDENTIFIER ::= { enterprises 15465 }
peacefulhaven                     OBJECT IDENTIFIER ::= { enterprises 15466 }
digibel                           OBJECT IDENTIFIER ::= { enterprises 15467 }
siegeorg                          OBJECT IDENTIFIER ::= { enterprises 15468 }
internetConnection                OBJECT IDENTIFIER ::= { enterprises 15469 }
digitalSystemResources            OBJECT IDENTIFIER ::= { enterprises 15470 }
nucleoDePesquisaEmRedesESistemasAbertos OBJECT IDENTIFIER ::= { enterprises 15471 }
digitalEvolution                  OBJECT IDENTIFIER ::= { enterprises 15472 }
springWorth                       OBJECT IDENTIFIER ::= { enterprises 15473 }
lighthouseSoftwareGroup           OBJECT IDENTIFIER ::= { enterprises 15474 }
zhongguangTelecommunications      OBJECT IDENTIFIER ::= { enterprises 15475 }
fareastoneTelecommunicationCorp   OBJECT IDENTIFIER ::= { enterprises 15476 }
bankForForeignTrade               OBJECT IDENTIFIER ::= { enterprises 15477 }
h3                                OBJECT IDENTIFIER ::= { enterprises 15478 }
dudleyorg                         OBJECT IDENTIFIER ::= { enterprises 15479 }
trillionDigitalCommunications     OBJECT IDENTIFIER ::= { enterprises 15480 }
capitalChannelInformationCo       OBJECT IDENTIFIER ::= { enterprises 15481 }
tianEn                            OBJECT IDENTIFIER ::= { enterprises 15482 }
ocaSA                             OBJECT IDENTIFIER ::= { enterprises 15483 }
luxTechnologies                   OBJECT IDENTIFIER ::= { enterprises 15484 }
universityOfOtago                 OBJECT IDENTIFIER ::= { enterprises 15485 }
keyon                             OBJECT IDENTIFIER ::= { enterprises 15486 }
daisyTechnologies                 OBJECT IDENTIFIER ::= { enterprises 15487 }
pureMatrix                        OBJECT IDENTIFIER ::= { enterprises 15488 }
homeSEAB                          OBJECT IDENTIFIER ::= { enterprises 15489 }
prasannaTechnologies              OBJECT IDENTIFIER ::= { enterprises 15490 }
protegrity                        OBJECT IDENTIFIER ::= { enterprises 15491 }
sichuanChanghongElectricGroupCo   OBJECT IDENTIFIER ::= { enterprises 15492 }
gollEnterprises                   OBJECT IDENTIFIER ::= { enterprises 15493 }
heliumLLC                         OBJECT IDENTIFIER ::= { enterprises 15494 }
ehouse                            OBJECT IDENTIFIER ::= { enterprises 15495 }
lascoala                          OBJECT IDENTIFIER ::= { enterprises 15496 }
ironportSystems                   OBJECT IDENTIFIER ::= { enterprises 15497 }
tesiSpA                           OBJECT IDENTIFIER ::= { enterprises 15498 }
theKing                           OBJECT IDENTIFIER ::= { enterprises 15499 }
ewingsTechnologies                OBJECT IDENTIFIER ::= { enterprises 15500 }
mAndcLaboratory                   OBJECT IDENTIFIER ::= { enterprises 15501 }
animezone                         OBJECT IDENTIFIER ::= { enterprises 15502 }
universityOfBerne                 OBJECT IDENTIFIER ::= { enterprises 15503 }
minist                            OBJECT IDENTIFIER ::= { enterprises 15504 }
eWitness                          OBJECT IDENTIFIER ::= { enterprises 15505 }
akiratechLimited                  OBJECT IDENTIFIER ::= { enterprises 15506 }
tieroneOSSTechnologies            OBJECT IDENTIFIER ::= { enterprises 15507 }
packetiqCorp                      OBJECT IDENTIFIER ::= { enterprises 15508 }
diretoorgbr                       OBJECT IDENTIFIER ::= { enterprises 15509 }
rhetoricalSystems                 OBJECT IDENTIFIER ::= { enterprises 15510 }
groupeERMEWASA                    OBJECT IDENTIFIER ::= { enterprises 15511 }
comaxINC                          OBJECT IDENTIFIER ::= { enterprises 15512 }
gendac                            OBJECT IDENTIFIER ::= { enterprises 15513 }
financijskaAgencija               OBJECT IDENTIFIER ::= { enterprises 15514 }
dget                              OBJECT IDENTIFIER ::= { enterprises 15515 }
softworksAustraliaPty             OBJECT IDENTIFIER ::= { enterprises 15516 }
entri                             OBJECT IDENTIFIER ::= { enterprises 15517 }
vocalocity                        OBJECT IDENTIFIER ::= { enterprises 15518 }
resultsComputingCorporation       OBJECT IDENTIFIER ::= { enterprises 15519 }
actiswitch                        OBJECT IDENTIFIER ::= { enterprises 15520 }
signalkontor                      OBJECT IDENTIFIER ::= { enterprises 15521 }
whitmanCollege                    OBJECT IDENTIFIER ::= { enterprises 15522 }
equinecom                         OBJECT IDENTIFIER ::= { enterprises 15523 }
accessPoint                       OBJECT IDENTIFIER ::= { enterprises 15524 }
braum                             OBJECT IDENTIFIER ::= { enterprises 15525 }
mixmobile                         OBJECT IDENTIFIER ::= { enterprises 15526 }
anienib                           OBJECT IDENTIFIER ::= { enterprises 15527 }
naviair                           OBJECT IDENTIFIER ::= { enterprises 15528 }
universidadDelValle               OBJECT IDENTIFIER ::= { enterprises 15529 }
integratedTechnologySC            OBJECT IDENTIFIER ::= { enterprises 15530 }
vpnchinaTechDevelopmentCorp       OBJECT IDENTIFIER ::= { enterprises 15531 }
hollomeyConsultantsGmbh           OBJECT IDENTIFIER ::= { enterprises 15532 }
mobileTornado                     OBJECT IDENTIFIER ::= { enterprises 15533 }
linupFront                        OBJECT IDENTIFIER ::= { enterprises 15534 }
verenigingMilieudefensie          OBJECT IDENTIFIER ::= { enterprises 15535 }
ptmcom                            OBJECT IDENTIFIER ::= { enterprises 15536 }
emkDesign                         OBJECT IDENTIFIER ::= { enterprises 15537 }
asigra                            OBJECT IDENTIFIER ::= { enterprises 15538 }
media4SpZOo                       OBJECT IDENTIFIER ::= { enterprises 15539 }
amCorporation                     OBJECT IDENTIFIER ::= { enterprises 15540 }
rhMinistarstvoGospodarstva        OBJECT IDENTIFIER ::= { enterprises 15541 }
emkDesign2                        OBJECT IDENTIFIER ::= { enterprises 15542 }
illinoisPowerCompany              OBJECT IDENTIFIER ::= { enterprises 15543 }
americanMensa                     OBJECT IDENTIFIER ::= { enterprises 15544 }
probix                            OBJECT IDENTIFIER ::= { enterprises 15545 }
elevenam                          OBJECT IDENTIFIER ::= { enterprises 15546 }
onarasAG                          OBJECT IDENTIFIER ::= { enterprises 15547 }
pillarDataSystems                 OBJECT IDENTIFIER ::= { enterprises 15548 }
xcacheTechnologies                OBJECT IDENTIFIER ::= { enterprises 15549 }
laSierraUniversity                OBJECT IDENTIFIER ::= { enterprises 15550 }
objectEngineering                 OBJECT IDENTIFIER ::= { enterprises 15551 }
statmonTechnologiesCorp           OBJECT IDENTIFIER ::= { enterprises 15552 }
snarlsnmpDynamicWebApplicationMonitorDevelopersGroup OBJECT IDENTIFIER ::= { enterprises 15553 }
democraticNationalCommittee       OBJECT IDENTIFIER ::= { enterprises 15554 }
goldCoastCityCouncil              OBJECT IDENTIFIER ::= { enterprises 15555 }
chuqYang                          OBJECT IDENTIFIER ::= { enterprises 15556 }
inflectionTechnologies            OBJECT IDENTIFIER ::= { enterprises 15557 }
instituteOfChemicalProcessFundamentals OBJECT IDENTIFIER ::= { enterprises 15558 }
orionet                           OBJECT IDENTIFIER ::= { enterprises 15559 }
yanfa                             OBJECT IDENTIFIER ::= { enterprises 15560 }
colemanFamilyCamps                OBJECT IDENTIFIER ::= { enterprises 15561 }
mbraceorg                         OBJECT IDENTIFIER ::= { enterprises 15562 }
adtron                            OBJECT IDENTIFIER ::= { enterprises 15563 }
aseliaTechnologies                OBJECT IDENTIFIER ::= { enterprises 15564 }
greatPlainsMallnet                OBJECT IDENTIFIER ::= { enterprises 15565 }
aCareSystems                      OBJECT IDENTIFIER ::= { enterprises 15566 }
neople                            OBJECT IDENTIFIER ::= { enterprises 15567 }
centerForDevelopmentOfInformationTechnologyCDIT OBJECT IDENTIFIER ::= { enterprises 15568 }
iccKrasnoyarskRailRoad            OBJECT IDENTIFIER ::= { enterprises 15569 }
bayerischeLandesbank              OBJECT IDENTIFIER ::= { enterprises 15570 }
schulerElectronics                OBJECT IDENTIFIER ::= { enterprises 15571 }
tcomAnddtvro                      OBJECT IDENTIFIER ::= { enterprises 15572 }
apertio                           OBJECT IDENTIFIER ::= { enterprises 15573 }
eMilioInternetServices            OBJECT IDENTIFIER ::= { enterprises 15574 }
chimes                            OBJECT IDENTIFIER ::= { enterprises 15575 }
pompoenBV                         OBJECT IDENTIFIER ::= { enterprises 15576 }
airprism                          OBJECT IDENTIFIER ::= { enterprises 15577 }
deeprootLinux                     OBJECT IDENTIFIER ::= { enterprises 15578 }
saesonTelecomCo                   OBJECT IDENTIFIER ::= { enterprises 15579 }
vniins                            OBJECT IDENTIFIER ::= { enterprises 15580 }
telemedCommunicationsServices     OBJECT IDENTIFIER ::= { enterprises 15581 }
xtradyneTechnologiesAG            OBJECT IDENTIFIER ::= { enterprises 15582 }
eureg                             OBJECT IDENTIFIER ::= { enterprises 15583 }
deWerknaam                        OBJECT IDENTIFIER ::= { enterprises 15584 }
northernLightTechnology           OBJECT IDENTIFIER ::= { enterprises 15585 }
responseMechanics                 OBJECT IDENTIFIER ::= { enterprises 15586 }
humboldtStateUniversity           OBJECT IDENTIFIER ::= { enterprises 15587 }
wetwebmedia                       OBJECT IDENTIFIER ::= { enterprises 15588 }
intigate                          OBJECT IDENTIFIER ::= { enterprises 15589 }
catboyTechnologies                OBJECT IDENTIFIER ::= { enterprises 15590 }
alexShepard                       OBJECT IDENTIFIER ::= { enterprises 15591 }
vikingTelecom                     OBJECT IDENTIFIER ::= { enterprises 15592 }
koreSystems                       OBJECT IDENTIFIER ::= { enterprises 15593 }
causewayTechnologies              OBJECT IDENTIFIER ::= { enterprises 15594 }
meagMUNICHERGOAssetManagement     OBJECT IDENTIFIER ::= { enterprises 15595 }
sonorkSRL                         OBJECT IDENTIFIER ::= { enterprises 15596 }
avamarTechnologies                OBJECT IDENTIFIER ::= { enterprises 15597 }
comproTechnologies                OBJECT IDENTIFIER ::= { enterprises 15598 }
groomLakeLaboratories             OBJECT IDENTIFIER ::= { enterprises 15599 }
xetaTechnologies                  OBJECT IDENTIFIER ::= { enterprises 15600 }
velocitySoftware                  OBJECT IDENTIFIER ::= { enterprises 15601 }
lottasophiede                     OBJECT IDENTIFIER ::= { enterprises 15602 }
sunhilloCorporation               OBJECT IDENTIFIER ::= { enterprises 15603 }
kuopioTelephonePLC                OBJECT IDENTIFIER ::= { enterprises 15604 }
grayLaboratories                  OBJECT IDENTIFIER ::= { enterprises 15605 }
toppioneerTechnologiesLimited     OBJECT IDENTIFIER ::= { enterprises 15606 }
encentuate                        OBJECT IDENTIFIER ::= { enterprises 15607 }
andersAndRodewyk                  OBJECT IDENTIFIER ::= { enterprises 15608 }
iskonInternetDd                   OBJECT IDENTIFIER ::= { enterprises 15609 }
herbertRetail                     OBJECT IDENTIFIER ::= { enterprises 15610 }
micElectronicsLimited             OBJECT IDENTIFIER ::= { enterprises 15611 }
softwareServices                  OBJECT IDENTIFIER ::= { enterprises 15612 }
genILimited                       OBJECT IDENTIFIER ::= { enterprises 15613 }
rickBaumanConsulting              OBJECT IDENTIFIER ::= { enterprises 15614 }
kma                               OBJECT IDENTIFIER ::= { enterprises 15615 }
dullroarEnterprises               OBJECT IDENTIFIER ::= { enterprises 15616 }
newlimits                         OBJECT IDENTIFIER ::= { enterprises 15617 }
adrenalize                        OBJECT IDENTIFIER ::= { enterprises 15618 }
deleanVision                      OBJECT IDENTIFIER ::= { enterprises 15619 }
ceivaLogic                        OBJECT IDENTIFIER ::= { enterprises 15620 }
zpTechnologies                    OBJECT IDENTIFIER ::= { enterprises 15621 }
aptare                            OBJECT IDENTIFIER ::= { enterprises 15622 }
darrylRoss                        OBJECT IDENTIFIER ::= { enterprises 15623 }
skopeoLLC                         OBJECT IDENTIFIER ::= { enterprises 15624 }
excedentTechnologies              OBJECT IDENTIFIER ::= { enterprises 15625 }
campusCrusadeAsia                 OBJECT IDENTIFIER ::= { enterprises 15626 }
spezifikum                        OBJECT IDENTIFIER ::= { enterprises 15627 }
lamarc                            OBJECT IDENTIFIER ::= { enterprises 15628 }
iqsoftRt                          OBJECT IDENTIFIER ::= { enterprises 15629 }
infoguardHB                       OBJECT IDENTIFIER ::= { enterprises 15630 }
vivistaLimited                    OBJECT IDENTIFIER ::= { enterprises 15631 }
primeFactoryGmbhAndCoKG           OBJECT IDENTIFIER ::= { enterprises 15632 }
tonisoft                          OBJECT IDENTIFIER ::= { enterprises 15633 }
d3netInternetTechnologienGmbh     OBJECT IDENTIFIER ::= { enterprises 15634 }
chinaPKI                          OBJECT IDENTIFIER ::= { enterprises 15635 }
altheaTechnical                   OBJECT IDENTIFIER ::= { enterprises 15636 }
spinlockNetworkLLC                OBJECT IDENTIFIER ::= { enterprises 15637 }
commissairenet                    OBJECT IDENTIFIER ::= { enterprises 15638 }
eSolutions                        OBJECT IDENTIFIER ::= { enterprises 15639 }
clearTechnology                   OBJECT IDENTIFIER ::= { enterprises 15640 }
masobitSRL                        OBJECT IDENTIFIER ::= { enterprises 15641 }
transplace                        OBJECT IDENTIFIER ::= { enterprises 15642 }
hallwaySoftwareDesignCorp         OBJECT IDENTIFIER ::= { enterprises 15643 }
brendaBell                        OBJECT IDENTIFIER ::= { enterprises 15644 }
pixellDatenAndDesign              OBJECT IDENTIFIER ::= { enterprises 15645 }
pjusarafelagIslands               OBJECT IDENTIFIER ::= { enterprises 15646 }
thesysadmin                       OBJECT IDENTIFIER ::= { enterprises 15647 }
atlantisServices                  OBJECT IDENTIFIER ::= { enterprises 15648 }
binaryMagic                       OBJECT IDENTIFIER ::= { enterprises 15649 }
citrenesysCorporation             OBJECT IDENTIFIER ::= { enterprises 15650 }
seventhMoonCo                     OBJECT IDENTIFIER ::= { enterprises 15651 }
sheInformationssystemeAG          OBJECT IDENTIFIER ::= { enterprises 15652 }
intesys                           OBJECT IDENTIFIER ::= { enterprises 15653 }
maxMomentum                       OBJECT IDENTIFIER ::= { enterprises 15654 }
sitadelle                         OBJECT IDENTIFIER ::= { enterprises 15655 }
computerPark                      OBJECT IDENTIFIER ::= { enterprises 15656 }
macrocall                         OBJECT IDENTIFIER ::= { enterprises 15657 }
fillmoreLabs                      OBJECT IDENTIFIER ::= { enterprises 15658 }
alaskaAirlines                    OBJECT IDENTIFIER ::= { enterprises 15659 }
tlmSoftware                       OBJECT IDENTIFIER ::= { enterprises 15660 }
x2net                             OBJECT IDENTIFIER ::= { enterprises 15661 }
fumphcom                          OBJECT IDENTIFIER ::= { enterprises 15662 }
aswanCo                           OBJECT IDENTIFIER ::= { enterprises 15663 }
aractelNetworks                   OBJECT IDENTIFIER ::= { enterprises 15664 }
easternCommunicationTechnologyDevelopmentCOLTD OBJECT IDENTIFIER ::= { enterprises 15665 }
orgatechUlrichTiemann             OBJECT IDENTIFIER ::= { enterprises 15666 }
lechnerRauHaustechnik             OBJECT IDENTIFIER ::= { enterprises 15667 }
zhongfangInformationCo            OBJECT IDENTIFIER ::= { enterprises 15668 }
lifecycleSoftware                 OBJECT IDENTIFIER ::= { enterprises 15669 }
theInternetMarketingCenter        OBJECT IDENTIFIER ::= { enterprises 15670 }
wardegaConsulting                 OBJECT IDENTIFIER ::= { enterprises 15671 }
jpPTTSaobracaja                   OBJECT IDENTIFIER ::= { enterprises 15672 }
codeangelsSolutions               OBJECT IDENTIFIER ::= { enterprises 15673 }
valenteCC                         OBJECT IDENTIFIER ::= { enterprises 15674 }
stonedonut                        OBJECT IDENTIFIER ::= { enterprises 15675 }
baede                             OBJECT IDENTIFIER ::= { enterprises 15676 }
thomsonThomson                    OBJECT IDENTIFIER ::= { enterprises 15677 }
softwareProjectsPty               OBJECT IDENTIFIER ::= { enterprises 15678 }
capeCom                           OBJECT IDENTIFIER ::= { enterprises 15679 }
digirati                          OBJECT IDENTIFIER ::= { enterprises 15680 }
roscoAssociatesTechnologyStaffing OBJECT IDENTIFIER ::= { enterprises 15681 }
pkicluecom                        OBJECT IDENTIFIER ::= { enterprises 15682 }
acrosonicCorporation              OBJECT IDENTIFIER ::= { enterprises 15683 }
macroTechnology                   OBJECT IDENTIFIER ::= { enterprises 15684 }
agalanet                          OBJECT IDENTIFIER ::= { enterprises 15685 }
meiCommunicationCo                OBJECT IDENTIFIER ::= { enterprises 15686 }
magicSoftwareEnterprises          OBJECT IDENTIFIER ::= { enterprises 15687 }
practicalLabs                     OBJECT IDENTIFIER ::= { enterprises 15688 }
heinzFamilyGermany                OBJECT IDENTIFIER ::= { enterprises 15689 }
liisp                             OBJECT IDENTIFIER ::= { enterprises 15690 }
netpowerSolutions                 OBJECT IDENTIFIER ::= { enterprises 15691 }
minnigerode                       OBJECT IDENTIFIER ::= { enterprises 15692 }
ionidea                           OBJECT IDENTIFIER ::= { enterprises 15693 }
silicom                           OBJECT IDENTIFIER ::= { enterprises 15694 }
aPomerantzAndCompany              OBJECT IDENTIFIER ::= { enterprises 15695 }
bayerAG                           OBJECT IDENTIFIER ::= { enterprises 15696 }
cellon                            OBJECT IDENTIFIER ::= { enterprises 15697 }
nloci                             OBJECT IDENTIFIER ::= { enterprises 15698 }
renesysCorporation                OBJECT IDENTIFIER ::= { enterprises 15699 }
henriciITConsulting               OBJECT IDENTIFIER ::= { enterprises 15700 }
schmut                            OBJECT IDENTIFIER ::= { enterprises 15701 }
computerImageTechnology           OBJECT IDENTIFIER ::= { enterprises 15702 }
softwareDiversifiedServices       OBJECT IDENTIFIER ::= { enterprises 15703 }
cyanWorlds                        OBJECT IDENTIFIER ::= { enterprises 15704 }
multitalents                      OBJECT IDENTIFIER ::= { enterprises 15705 }
iglooSECURITY                     OBJECT IDENTIFIER ::= { enterprises 15706 }
silvenet                          OBJECT IDENTIFIER ::= { enterprises 15707 }
beijingWestmanAutomation          OBJECT IDENTIFIER ::= { enterprises 15708 }
cboss                             OBJECT IDENTIFIER ::= { enterprises 15709 }
megasoft                          OBJECT IDENTIFIER ::= { enterprises 15710 }
euroDB                            OBJECT IDENTIFIER ::= { enterprises 15711 }
taringold                         OBJECT IDENTIFIER ::= { enterprises 15712 }
drinsama                          OBJECT IDENTIFIER ::= { enterprises 15713 }
lenelSystemsInternational         OBJECT IDENTIFIER ::= { enterprises 15714 }
blueTreeSystems                   OBJECT IDENTIFIER ::= { enterprises 15715 }
hexago                            OBJECT IDENTIFIER ::= { enterprises 15716 }
cegetelNet                        OBJECT IDENTIFIER ::= { enterprises 15717 }
loyaltyManagementGroupCanada      OBJECT IDENTIFIER ::= { enterprises 15718 }
massCollegeOfLiberalArts          OBJECT IDENTIFIER ::= { enterprises 15719 }
binarymedia                       OBJECT IDENTIFIER ::= { enterprises 15720 }
comm2                             OBJECT IDENTIFIER ::= { enterprises 15721 }
concare                           OBJECT IDENTIFIER ::= { enterprises 15722 }
holoscenescom                     OBJECT IDENTIFIER ::= { enterprises 15723 }
visionbankCorp                    OBJECT IDENTIFIER ::= { enterprises 15724 }
zyflexTechnologies                OBJECT IDENTIFIER ::= { enterprises 15725 }
klug                              OBJECT IDENTIFIER ::= { enterprises 15726 }
hofenorg                          OBJECT IDENTIFIER ::= { enterprises 15727 }
sentryInformationAndAlertSystemsCorp OBJECT IDENTIFIER ::= { enterprises 15728 }
sytrust                           OBJECT IDENTIFIER ::= { enterprises 15729 }
luluEnterprises                   OBJECT IDENTIFIER ::= { enterprises 15730 }
easypax                           OBJECT IDENTIFIER ::= { enterprises 15731 }
usyscom                           OBJECT IDENTIFIER ::= { enterprises 15732 }
washingtonStateUniversity         OBJECT IDENTIFIER ::= { enterprises 15733 }
aionSystems                       OBJECT IDENTIFIER ::= { enterprises 15734 }
secureTechnologyHawaii            OBJECT IDENTIFIER ::= { enterprises 15735 }
emergepoint                       OBJECT IDENTIFIER ::= { enterprises 15736 }
zozoa                             OBJECT IDENTIFIER ::= { enterprises 15737 }
businessNetworkCommunications     OBJECT IDENTIFIER ::= { enterprises 15738 }
ruzzTechnologyPty                 OBJECT IDENTIFIER ::= { enterprises 15739 }
digitalVisionTechnology           OBJECT IDENTIFIER ::= { enterprises 15740 }
softerra                          OBJECT IDENTIFIER ::= { enterprises 15741 }
disksites                         OBJECT IDENTIFIER ::= { enterprises 15742 }
vtl                               OBJECT IDENTIFIER ::= { enterprises 15743 }
netratings                        OBJECT IDENTIFIER ::= { enterprises 15744 }
schorenNMSSolutions               OBJECT IDENTIFIER ::= { enterprises 15745 }
zonerSoftware                     OBJECT IDENTIFIER ::= { enterprises 15746 }
locusPortalCorporation            OBJECT IDENTIFIER ::= { enterprises 15747 }
netghostCommunications            OBJECT IDENTIFIER ::= { enterprises 15748 }
ingersollRandCo                   OBJECT IDENTIFIER ::= { enterprises 15749 }
universityOfTroms                 OBJECT IDENTIFIER ::= { enterprises 15750 }
trcFiord                          OBJECT IDENTIFIER ::= { enterprises 15751 }
slamborg                          OBJECT IDENTIFIER ::= { enterprises 15752 }
appserver                         OBJECT IDENTIFIER ::= { enterprises 15753 }
vancouverCommunityNetwork         OBJECT IDENTIFIER ::= { enterprises 15754 }
pivodTechnologies                 OBJECT IDENTIFIER ::= { enterprises 15755 }
wistronNeWebCorporation           OBJECT IDENTIFIER ::= { enterprises 15756 }
mitsubishiELECTRICINFORMATIONTECHNOLOGYCORPORATION OBJECT IDENTIFIER ::= { enterprises 15757 }
suntekBeijingyanjiuyuan           OBJECT IDENTIFIER ::= { enterprises 15758 }
greenerPasturesInnovations        OBJECT IDENTIFIER ::= { enterprises 15759 }
nmsworks                          OBJECT IDENTIFIER ::= { enterprises 15760 }
atsElektronik                     OBJECT IDENTIFIER ::= { enterprises 15761 }
khety                             OBJECT IDENTIFIER ::= { enterprises 15762 }
lagan                             OBJECT IDENTIFIER ::= { enterprises 15763 }
repsolYPF                         OBJECT IDENTIFIER ::= { enterprises 15764 }
jxSolutions                       OBJECT IDENTIFIER ::= { enterprises 15765 }
matrixMailing                     OBJECT IDENTIFIER ::= { enterprises 15766 }
triblen                           OBJECT IDENTIFIER ::= { enterprises 15767 }
belairNetworks                    OBJECT IDENTIFIER ::= { enterprises 15768 }
argecyComputerCorporation         OBJECT IDENTIFIER ::= { enterprises 15769 }
zeeraNetworks                     OBJECT IDENTIFIER ::= { enterprises 15770 }
jfPossibilities                   OBJECT IDENTIFIER ::= { enterprises 15771 }
fachhochschuleLandshut            OBJECT IDENTIFIER ::= { enterprises 15772 }
eBS                               OBJECT IDENTIFIER ::= { enterprises 15773 }
designet                          OBJECT IDENTIFIER ::= { enterprises 15774 }
heidenhain                        OBJECT IDENTIFIER ::= { enterprises 15775 }
advancedDataIntegration           OBJECT IDENTIFIER ::= { enterprises 15776 }
openin                            OBJECT IDENTIFIER ::= { enterprises 15777 }
daxnetwork                        OBJECT IDENTIFIER ::= { enterprises 15778 }
novelTongFang                     OBJECT IDENTIFIER ::= { enterprises 15779 }
kiloutou                          OBJECT IDENTIFIER ::= { enterprises 15780 }
transflowInformationslogistik     OBJECT IDENTIFIER ::= { enterprises 15781 }
viaMATMANAGEMENTAG                OBJECT IDENTIFIER ::= { enterprises 15782 }
hrsmart                           OBJECT IDENTIFIER ::= { enterprises 15783 }
elbConsulting                     OBJECT IDENTIFIER ::= { enterprises 15784 }
montruscoBoltonInvestments        OBJECT IDENTIFIER ::= { enterprises 15785 }
netledger                         OBJECT IDENTIFIER ::= { enterprises 15786 }
dgnService                        OBJECT IDENTIFIER ::= { enterprises 15787 }
theEldersOfTheUniverse            OBJECT IDENTIFIER ::= { enterprises 15788 }
infineonTechnologiesAG            OBJECT IDENTIFIER ::= { enterprises 15789 }
widerayCorporation                OBJECT IDENTIFIER ::= { enterprises 15790 }
laCanadaWirelessAssociation       OBJECT IDENTIFIER ::= { enterprises 15791 }
interlinkGroup                    OBJECT IDENTIFIER ::= { enterprises 15792 }
pittigSoftwareAndInternetServices OBJECT IDENTIFIER ::= { enterprises 15793 }
degeorgeFamily                    OBJECT IDENTIFIER ::= { enterprises 15794 }
vandelayInternetServices          OBJECT IDENTIFIER ::= { enterprises 15795 }
imageoneCo                        OBJECT IDENTIFIER ::= { enterprises 15796 }
infosysTechnologiesLimited        OBJECT IDENTIFIER ::= { enterprises 15797 }
ratoInternationalCommunicationCo  OBJECT IDENTIFIER ::= { enterprises 15798 }
ceskyMobilAs                      OBJECT IDENTIFIER ::= { enterprises 15799 }
jnDataAS                          OBJECT IDENTIFIER ::= { enterprises 15800 }
huitsingEmbeddedSystems           OBJECT IDENTIFIER ::= { enterprises 15801 }
farlep                            OBJECT IDENTIFIER ::= { enterprises 15802 }
mercatisInformationSystemsGmbh    OBJECT IDENTIFIER ::= { enterprises 15803 }
dlrSISTEC                         OBJECT IDENTIFIER ::= { enterprises 15804 }
sweetheartCupCompany              OBJECT IDENTIFIER ::= { enterprises 15805 }
connectalk                        OBJECT IDENTIFIER ::= { enterprises 15806 }
dgnService2                       OBJECT IDENTIFIER ::= { enterprises 15807 }
dgnService3                       OBJECT IDENTIFIER ::= { enterprises 15808 }
wnetISP                           OBJECT IDENTIFIER ::= { enterprises 15809 }
bankSevernayaKaznaOAO             OBJECT IDENTIFIER ::= { enterprises 15810 }
digitalControl                    OBJECT IDENTIFIER ::= { enterprises 15811 }
radicalCorporation                OBJECT IDENTIFIER ::= { enterprises 15812 }
aispl                             OBJECT IDENTIFIER ::= { enterprises 15813 }
appliedConcepts                   OBJECT IDENTIFIER ::= { enterprises 15814 }
netqa                             OBJECT IDENTIFIER ::= { enterprises 15815 }
infra911                          OBJECT IDENTIFIER ::= { enterprises 15816 }
falconSystemConsulting            OBJECT IDENTIFIER ::= { enterprises 15817 }
stadtBraunschweig                 OBJECT IDENTIFIER ::= { enterprises 15818 }
cryptologInternational            OBJECT IDENTIFIER ::= { enterprises 15819 }
castorInformatique                OBJECT IDENTIFIER ::= { enterprises 15820 }
freebsdCNProject                  OBJECT IDENTIFIER ::= { enterprises 15821 }
iSTnet                            OBJECT IDENTIFIER ::= { enterprises 15822 }
linuxwithincom                    OBJECT IDENTIFIER ::= { enterprises 15823 }
inasoft                           OBJECT IDENTIFIER ::= { enterprises 15824 }
clearmetrix                       OBJECT IDENTIFIER ::= { enterprises 15825 }
cryptek                           OBJECT IDENTIFIER ::= { enterprises 15826 }
crockerCommunications             OBJECT IDENTIFIER ::= { enterprises 15827 }
h3gItaliaSpAEnterpriseCA          OBJECT IDENTIFIER ::= { enterprises 15828 }
digitalPRODUCTIONSARL             OBJECT IDENTIFIER ::= { enterprises 15829 }
robinlea                          OBJECT IDENTIFIER ::= { enterprises 15830 }
densoITLABORATORY                 OBJECT IDENTIFIER ::= { enterprises 15831 }
btIgniteSolutions                 OBJECT IDENTIFIER ::= { enterprises 15832 }
sigec                             OBJECT IDENTIFIER ::= { enterprises 15833 }
tigardTualatinSchoolDistrict      OBJECT IDENTIFIER ::= { enterprises 15834 }
mAndsSystems                      OBJECT IDENTIFIER ::= { enterprises 15835 }
marcorAssociates                  OBJECT IDENTIFIER ::= { enterprises 15836 }
investmentTechnologyGroup         OBJECT IDENTIFIER ::= { enterprises 15837 }
aka                               OBJECT IDENTIFIER ::= { enterprises 15838 }
theEWScrippsCompany               OBJECT IDENTIFIER ::= { enterprises 15839 }
geidax                            OBJECT IDENTIFIER ::= { enterprises 15840 }
danielRitter                      OBJECT IDENTIFIER ::= { enterprises 15841 }
blasbergComputerSysteme           OBJECT IDENTIFIER ::= { enterprises 15842 }
massenbach                        OBJECT IDENTIFIER ::= { enterprises 15843 }
marconiSeleniaCommunicationsSpa   OBJECT IDENTIFIER ::= { enterprises 15844 }
dixperSystems                     OBJECT IDENTIFIER ::= { enterprises 15845 }
ipFabrics                         OBJECT IDENTIFIER ::= { enterprises 15846 }
harvardLawSchool                  OBJECT IDENTIFIER ::= { enterprises 15847 }
sensorsoftCorporation             OBJECT IDENTIFIER ::= { enterprises 15848 }
evansCompanies                    OBJECT IDENTIFIER ::= { enterprises 15849 }
reshape                           OBJECT IDENTIFIER ::= { enterprises 15850 }
computerizedMedicalSystems        OBJECT IDENTIFIER ::= { enterprises 15851 }
legionInteractive                 OBJECT IDENTIFIER ::= { enterprises 15852 }
computerCenter                    OBJECT IDENTIFIER ::= { enterprises 15853 }
ripeNCC                           OBJECT IDENTIFIER ::= { enterprises 15854 }
lule                              OBJECT IDENTIFIER ::= { enterprises 15855 }
openPowerNetwork                  OBJECT IDENTIFIER ::= { enterprises 15856 }
administracionDelPrincipadoDeAsturias OBJECT IDENTIFIER ::= { enterprises 15857 }
allInGreencom                     OBJECT IDENTIFIER ::= { enterprises 15858 }
cityOfTampere                     OBJECT IDENTIFIER ::= { enterprises 15859 }
partec                            OBJECT IDENTIFIER ::= { enterprises 15860 }
kinetik                           OBJECT IDENTIFIER ::= { enterprises 15861 }
bankservicePlc                    OBJECT IDENTIFIER ::= { enterprises 15862 }
innovativeNavigation              OBJECT IDENTIFIER ::= { enterprises 15863 }
unicityPty                        OBJECT IDENTIFIER ::= { enterprises 15864 }
cabProdukttechnik                 OBJECT IDENTIFIER ::= { enterprises 15865 }
joeRhodesConsultingLLC            OBJECT IDENTIFIER ::= { enterprises 15866 }
ixiMobile                         OBJECT IDENTIFIER ::= { enterprises 15867 }
cybrisNetworkInformationSystems   OBJECT IDENTIFIER ::= { enterprises 15868 }
tijdBeursmedia                    OBJECT IDENTIFIER ::= { enterprises 15869 }
egonTechnologies                  OBJECT IDENTIFIER ::= { enterprises 15870 }
omnilux                           OBJECT IDENTIFIER ::= { enterprises 15871 }
itMerge                           OBJECT IDENTIFIER ::= { enterprises 15872 }
guardianLifeInsurance             OBJECT IDENTIFIER ::= { enterprises 15873 }
mdsProteomicsAS                   OBJECT IDENTIFIER ::= { enterprises 15874 }
mPLIFYSA                          OBJECT IDENTIFIER ::= { enterprises 15875 }
microprogramInformationLDCO       OBJECT IDENTIFIER ::= { enterprises 15876 }
apiTechnologies                   OBJECT IDENTIFIER ::= { enterprises 15877 }
aztechSYSTEMSLTD                  OBJECT IDENTIFIER ::= { enterprises 15878 }
waveip                            OBJECT IDENTIFIER ::= { enterprises 15879 }
moneylineBANKINGSYSTEMS           OBJECT IDENTIFIER ::= { enterprises 15880 }
thomasFahle                       OBJECT IDENTIFIER ::= { enterprises 15881 }
smartIp                           OBJECT IDENTIFIER ::= { enterprises 15882 }
getronicsFrance                   OBJECT IDENTIFIER ::= { enterprises 15883 }
nobleTurkeySoftware               OBJECT IDENTIFIER ::= { enterprises 15884 }
esagEnergieversorgungSachsenOstAG OBJECT IDENTIFIER ::= { enterprises 15885 }
manhattanAssociates               OBJECT IDENTIFIER ::= { enterprises 15886 }
cosiniNetworks                    OBJECT IDENTIFIER ::= { enterprises 15887 }
taiSrl                            OBJECT IDENTIFIER ::= { enterprises 15888 }
qFreeASA                          OBJECT IDENTIFIER ::= { enterprises 15889 }
prairieGroveTelephoneCo           OBJECT IDENTIFIER ::= { enterprises 15890 }
pandaRestaurantGroup              OBJECT IDENTIFIER ::= { enterprises 15891 }
openmodesTechnologyGroup          OBJECT IDENTIFIER ::= { enterprises 15892 }
computerProcessControls           OBJECT IDENTIFIER ::= { enterprises 15893 }
astrostage                        OBJECT IDENTIFIER ::= { enterprises 15894 }
linux                             OBJECT IDENTIFIER ::= { enterprises 15895 }
rostovStateUniversity             OBJECT IDENTIFIER ::= { enterprises 15896 }
guangzhouGaoUSAndTDevelopmentCo   OBJECT IDENTIFIER ::= { enterprises 15897 }
polizeiBrandenburg                OBJECT IDENTIFIER ::= { enterprises 15898 }
inubit                            OBJECT IDENTIFIER ::= { enterprises 15899 }
openweb                           OBJECT IDENTIFIER ::= { enterprises 15900 }
valsimmonTechnologyGroup          OBJECT IDENTIFIER ::= { enterprises 15901 }
men                               OBJECT IDENTIFIER ::= { enterprises 15902 }
seebekIngenier                    OBJECT IDENTIFIER ::= { enterprises 15903 }
peterEckel                        OBJECT IDENTIFIER ::= { enterprises 15904 }
deferoSystemsAB                   OBJECT IDENTIFIER ::= { enterprises 15905 }
wlanAG                            OBJECT IDENTIFIER ::= { enterprises 15906 }
canyonNetworks                    OBJECT IDENTIFIER ::= { enterprises 15907 }
businessTechnologyAssociates      OBJECT IDENTIFIER ::= { enterprises 15908 }
mrxSolutions                      OBJECT IDENTIFIER ::= { enterprises 15909 }
autotradercom                     OBJECT IDENTIFIER ::= { enterprises 15910 }
heChuan                           OBJECT IDENTIFIER ::= { enterprises 15911 }
bluecomAS                         OBJECT IDENTIFIER ::= { enterprises 15912 }
networkingSupportServices         OBJECT IDENTIFIER ::= { enterprises 15913 }
netreo                            OBJECT IDENTIFIER ::= { enterprises 15914 }
highTowerSoftware                 OBJECT IDENTIFIER ::= { enterprises 15915 }
landeskSoftware                   OBJECT IDENTIFIER ::= { enterprises 15916 }
stargatenet                       OBJECT IDENTIFIER ::= { enterprises 15917 }
theMORROWGroup                    OBJECT IDENTIFIER ::= { enterprises 15918 }
hitachiStorageSoftware            OBJECT IDENTIFIER ::= { enterprises 15919 }
switchManagement                  OBJECT IDENTIFIER ::= { enterprises 15920 }
mobileaccess                      OBJECT IDENTIFIER ::= { enterprises 15921 }
yishangINNOVATIONTECHNOLOGYCO     OBJECT IDENTIFIER ::= { enterprises 15922 }
ics                               OBJECT IDENTIFIER ::= { enterprises 15923 }
kuwaitLinuxCompany                OBJECT IDENTIFIER ::= { enterprises 15924 }
cadenceDesignSystems              OBJECT IDENTIFIER ::= { enterprises 15925 }
cartierPartnersFinancialGroup     OBJECT IDENTIFIER ::= { enterprises 15926 }
pointLomaNazareneUniversity       OBJECT IDENTIFIER ::= { enterprises 15927 }
snb                               OBJECT IDENTIFIER ::= { enterprises 15928 }
cambodiaSamartCommunication       OBJECT IDENTIFIER ::= { enterprises 15929 }
lucasfilm                         OBJECT IDENTIFIER ::= { enterprises 15930 }
centerForInternationalRehabilitation OBJECT IDENTIFIER ::= { enterprises 15931 }
wuertele                          OBJECT IDENTIFIER ::= { enterprises 15932 }
cyaneaSystemsCorp                 OBJECT IDENTIFIER ::= { enterprises 15933 }
multipKft                         OBJECT IDENTIFIER ::= { enterprises 15934 }
centerplex                        OBJECT IDENTIFIER ::= { enterprises 15935 }
koreadotcom                       OBJECT IDENTIFIER ::= { enterprises 15936 }
svyazinformOfRepublicMordoviaJointStockCompany OBJECT IDENTIFIER ::= { enterprises 15937 }
jointSTOCKCOMPANYIMPORTEXPORTBANK OBJECT IDENTIFIER ::= { enterprises 15938 }
coralTelecom                      OBJECT IDENTIFIER ::= { enterprises 15939 }
factoriaDeIniciativasInternetFi2  OBJECT IDENTIFIER ::= { enterprises 15940 }
galenaParkISD                     OBJECT IDENTIFIER ::= { enterprises 15941 }
cabildoDeGranCanaria              OBJECT IDENTIFIER ::= { enterprises 15942 }
conexusCreditUnion                OBJECT IDENTIFIER ::= { enterprises 15943 }
agenceDeLaFrancophonie            OBJECT IDENTIFIER ::= { enterprises 15944 }
ascertia                          OBJECT IDENTIFIER ::= { enterprises 15945 }
calypsoNetworks                   OBJECT IDENTIFIER ::= { enterprises 15946 }
newJerseyInstituteOfTechnology    OBJECT IDENTIFIER ::= { enterprises 15947 }
trevsplacecom                     OBJECT IDENTIFIER ::= { enterprises 15948 }
f2                                OBJECT IDENTIFIER ::= { enterprises 15949 }
amMedia                           OBJECT IDENTIFIER ::= { enterprises 15950 }
axentGlobal                       OBJECT IDENTIFIER ::= { enterprises 15951 }
advancedComputerResources         OBJECT IDENTIFIER ::= { enterprises 15952 }
aaronSpangler                     OBJECT IDENTIFIER ::= { enterprises 15953 }
filesurePte                       OBJECT IDENTIFIER ::= { enterprises 15954 }
omnicompTechnologyServices        OBJECT IDENTIFIER ::= { enterprises 15955 }
incoreTechnology                  OBJECT IDENTIFIER ::= { enterprises 15956 }
muonics                           OBJECT IDENTIFIER ::= { enterprises 15957 }
trevsplacecom2                    OBJECT IDENTIFIER ::= { enterprises 15958 }
sue                               OBJECT IDENTIFIER ::= { enterprises 15959 }
eairports                         OBJECT IDENTIFIER ::= { enterprises 15960 }
cockingAndCo                      OBJECT IDENTIFIER ::= { enterprises 15961 }
asml                              OBJECT IDENTIFIER ::= { enterprises 15962 }
informaCOLOMBIA                   OBJECT IDENTIFIER ::= { enterprises 15963 }
institutoNacionalDeAstrof         OBJECT IDENTIFIER ::= { enterprises 15964 }
publicResourcesManagementGroup    OBJECT IDENTIFIER ::= { enterprises 15965 }
visa                              OBJECT IDENTIFIER ::= { enterprises 15966 }
ncastCorporation                  OBJECT IDENTIFIER ::= { enterprises 15967 }
emicoVero                         OBJECT IDENTIFIER ::= { enterprises 15968 }
vindigo                           OBJECT IDENTIFIER ::= { enterprises 15969 }
aspenNetworks                     OBJECT IDENTIFIER ::= { enterprises 15970 }
advancedBiometricControls         OBJECT IDENTIFIER ::= { enterprises 15971 }
disasterKleenupInternational      OBJECT IDENTIFIER ::= { enterprises 15972 }
jcorporate                        OBJECT IDENTIFIER ::= { enterprises 15973 }
skywaveCorporation                OBJECT IDENTIFIER ::= { enterprises 15974 }
meikyoELECTRICCO                  OBJECT IDENTIFIER ::= { enterprises 15975 }
adacomSA                          OBJECT IDENTIFIER ::= { enterprises 15976 }
compolII                          OBJECT IDENTIFIER ::= { enterprises 15977 }
it                                OBJECT IDENTIFIER ::= { enterprises 15978 }
tomsoft                           OBJECT IDENTIFIER ::= { enterprises 15979 }
trackwellSoftwareHf               OBJECT IDENTIFIER ::= { enterprises 15980 }
anilloNetworks                    OBJECT IDENTIFIER ::= { enterprises 15981 }
hubbubITServices                  OBJECT IDENTIFIER ::= { enterprises 15982 }
meruNetworks                      OBJECT IDENTIFIER ::= { enterprises 15983 }
authenex                          OBJECT IDENTIFIER ::= { enterprises 15984 }
theUniversityOfLethbridge         OBJECT IDENTIFIER ::= { enterprises 15985 }
binara                            OBJECT IDENTIFIER ::= { enterprises 15986 }
topozPty                          OBJECT IDENTIFIER ::= { enterprises 15987 }
cymes                             OBJECT IDENTIFIER ::= { enterprises 15988 }
torstenSchneider                  OBJECT IDENTIFIER ::= { enterprises 15989 }
mikrobitti                        OBJECT IDENTIFIER ::= { enterprises 15990 }
raso                              OBJECT IDENTIFIER ::= { enterprises 15991 }
tracerdigital                     OBJECT IDENTIFIER ::= { enterprises 15992 }
netScaleTechnologies              OBJECT IDENTIFIER ::= { enterprises 15993 }
xcomComunicacaoSegura             OBJECT IDENTIFIER ::= { enterprises 15994 }
itConsultantHenningFollmann       OBJECT IDENTIFIER ::= { enterprises 15995 }
ncRJRNP                           OBJECT IDENTIFIER ::= { enterprises 15996 }
waveSystemsCorp                   OBJECT IDENTIFIER ::= { enterprises 15997 }
universityOfGlamorgan             OBJECT IDENTIFIER ::= { enterprises 15998 }
cpsTechnologyGroup                OBJECT IDENTIFIER ::= { enterprises 15999 }
syreaSrl                          OBJECT IDENTIFIER ::= { enterprises 16000 }
ministryOfFinance                 OBJECT IDENTIFIER ::= { enterprises 16001 }
glyphix                           OBJECT IDENTIFIER ::= { enterprises 16002 }
zschimmer                         OBJECT IDENTIFIER ::= { enterprises 16003 }
intrusec                          OBJECT IDENTIFIER ::= { enterprises 16004 }
universityOfDurham                OBJECT IDENTIFIER ::= { enterprises 16005 }
codefab                           OBJECT IDENTIFIER ::= { enterprises 16006 }
nativeInstruments                 OBJECT IDENTIFIER ::= { enterprises 16007 }
consolidatedCommunications        OBJECT IDENTIFIER ::= { enterprises 16008 }
telemaxxTelekommunikation         OBJECT IDENTIFIER ::= { enterprises 16009 }
kapschBusinessComAG               OBJECT IDENTIFIER ::= { enterprises 16010 }
stateOfUtahDASITS                 OBJECT IDENTIFIER ::= { enterprises 16011 }
memscap                           OBJECT IDENTIFIER ::= { enterprises 16012 }
bytecentric                       OBJECT IDENTIFIER ::= { enterprises 16013 }
appliedMaterials                  OBJECT IDENTIFIER ::= { enterprises 16014 }
primaryObjective                  OBJECT IDENTIFIER ::= { enterprises 16015 }
simmeyLimited                     OBJECT IDENTIFIER ::= { enterprises 16016 }
cewCo                             OBJECT IDENTIFIER ::= { enterprises 16017 }
punkerorg                         OBJECT IDENTIFIER ::= { enterprises 16018 }
reitek                            OBJECT IDENTIFIER ::= { enterprises 16019 }
wasadataSystemAB                  OBJECT IDENTIFIER ::= { enterprises 16020 }
cassavaEnterprises                OBJECT IDENTIFIER ::= { enterprises 16021 }
minicomAdvancedSystems            OBJECT IDENTIFIER ::= { enterprises 16022 }
inetadmin                         OBJECT IDENTIFIER ::= { enterprises 16023 }
netzwertAktiengesellschaft        OBJECT IDENTIFIER ::= { enterprises 16024 }
ciblisEngenhariaSC                OBJECT IDENTIFIER ::= { enterprises 16025 }
softaplicSC                       OBJECT IDENTIFIER ::= { enterprises 16026 }
shahUSA                           OBJECT IDENTIFIER ::= { enterprises 16027 }
xaosSystems                       OBJECT IDENTIFIER ::= { enterprises 16028 }
westleaderInternational           OBJECT IDENTIFIER ::= { enterprises 16029 }
hongkongPost                      OBJECT IDENTIFIER ::= { enterprises 16030 }
atmarkTechno                      OBJECT IDENTIFIER ::= { enterprises 16031 }
uraltransbank                     OBJECT IDENTIFIER ::= { enterprises 16032 }
telemicOy                         OBJECT IDENTIFIER ::= { enterprises 16033 }
opusHadsel                        OBJECT IDENTIFIER ::= { enterprises 16034 }
icomMobile                        OBJECT IDENTIFIER ::= { enterprises 16035 }
infocentre                        OBJECT IDENTIFIER ::= { enterprises 16036 }
emmotion                         OBJECT IDENTIFIER ::= { enterprises 16037 }
oraylis                           OBJECT IDENTIFIER ::= { enterprises 16038 }
automatedSystemsEngineering       OBJECT IDENTIFIER ::= { enterprises 16039 }
datapartynet                      OBJECT IDENTIFIER ::= { enterprises 16040 }
hogeschoolBrabant                 OBJECT IDENTIFIER ::= { enterprises 16041 }
jmpSYSTEMS                        OBJECT IDENTIFIER ::= { enterprises 16042 }
viasec                            OBJECT IDENTIFIER ::= { enterprises 16043 }
todoGesellschaftFuerInformationstechnikMbH OBJECT IDENTIFIER ::= { enterprises 16044 }
ocacoFinlandOy                    OBJECT IDENTIFIER ::= { enterprises 16045 }
dsdSA                             OBJECT IDENTIFIER ::= { enterprises 16046 }
itPractice                        OBJECT IDENTIFIER ::= { enterprises 16047 }
bofriis                           OBJECT IDENTIFIER ::= { enterprises 16048 }
flamencoNetworks                  OBJECT IDENTIFIER ::= { enterprises 16049 }
krupczakOrg                       OBJECT IDENTIFIER ::= { enterprises 16050 }
coreteamAB                        OBJECT IDENTIFIER ::= { enterprises 16051 }
chrisRauschuber                   OBJECT IDENTIFIER ::= { enterprises 16052 }
burgerKingCorporation             OBJECT IDENTIFIER ::= { enterprises 16053 }
resourceDataManagement            OBJECT IDENTIFIER ::= { enterprises 16054 }
blandsite                         OBJECT IDENTIFIER ::= { enterprises 16055 }
okazakiCityOffice                 OBJECT IDENTIFIER ::= { enterprises 16056 }
eventgnosis                       OBJECT IDENTIFIER ::= { enterprises 16057 }
genkey                            OBJECT IDENTIFIER ::= { enterprises 16058 }
tsinghuaTongFangSoftwareCo        OBJECT IDENTIFIER ::= { enterprises 16059 }
lighthouseInformationSystems      OBJECT IDENTIFIER ::= { enterprises 16060 }
adhersisNorthAmerica              OBJECT IDENTIFIER ::= { enterprises 16061 }
zincnetworks                      OBJECT IDENTIFIER ::= { enterprises 16062 }
dcTechnologies                    OBJECT IDENTIFIER ::= { enterprises 16063 }
perspectixAG                      OBJECT IDENTIFIER ::= { enterprises 16064 }
arkSystems                        OBJECT IDENTIFIER ::= { enterprises 16065 }
necTelenetworx                    OBJECT IDENTIFIER ::= { enterprises 16066 }
barcointelligentdisplays          OBJECT IDENTIFIER ::= { enterprises 16067 }
repeatitAB                        OBJECT IDENTIFIER ::= { enterprises 16068 }
minefiSP                          OBJECT IDENTIFIER ::= { enterprises 16069 }
bundesamtF                        OBJECT IDENTIFIER ::= { enterprises 16070 }
pictetAndCie                      OBJECT IDENTIFIER ::= { enterprises 16071 }
linkeocom                         OBJECT IDENTIFIER ::= { enterprises 16072 }
edithCowanUniversity              OBJECT IDENTIFIER ::= { enterprises 16073 }
vblKarlsruhe                      OBJECT IDENTIFIER ::= { enterprises 16074 }
uninet                            OBJECT IDENTIFIER ::= { enterprises 16075 }
dominionDiagnostics               OBJECT IDENTIFIER ::= { enterprises 16076 }
witbe                             OBJECT IDENTIFIER ::= { enterprises 16077 }
mouvementR                        OBJECT IDENTIFIER ::= { enterprises 16078 }
bitmaster                         OBJECT IDENTIFIER ::= { enterprises 16079 }
softwareLogistics                 OBJECT IDENTIFIER ::= { enterprises 16080 }
ktaland                           OBJECT IDENTIFIER ::= { enterprises 16081 }
bechtelCorporation                OBJECT IDENTIFIER ::= { enterprises 16082 }
mainebase                         OBJECT IDENTIFIER ::= { enterprises 16083 }
houseOfNoise                      OBJECT IDENTIFIER ::= { enterprises 16084 }
telexpertiseDeMexicoSADeCV        OBJECT IDENTIFIER ::= { enterprises 16085 }
mitsumiELECTRICCO                 OBJECT IDENTIFIER ::= { enterprises 16086 }
zayedUniversity                   OBJECT IDENTIFIER ::= { enterprises 16087 }
groatsLaboratories                OBJECT IDENTIFIER ::= { enterprises 16088 }
exwavecomCo                       OBJECT IDENTIFIER ::= { enterprises 16089 }
estweb                            OBJECT IDENTIFIER ::= { enterprises 16090 }
ecr                               OBJECT IDENTIFIER ::= { enterprises 16091 }
airwalkCommunications             OBJECT IDENTIFIER ::= { enterprises 16092 }
awSoftware                        OBJECT IDENTIFIER ::= { enterprises 16093 }
stacken                           OBJECT IDENTIFIER ::= { enterprises 16094 }
fluencyVoiceTechnology            OBJECT IDENTIFIER ::= { enterprises 16095 }
rcsTECHNOLOGY                     OBJECT IDENTIFIER ::= { enterprises 16096 }
voiceRobots                       OBJECT IDENTIFIER ::= { enterprises 16097 }
scaGraphicSundsvallAB             OBJECT IDENTIFIER ::= { enterprises 16098 }
pinionGroup                       OBJECT IDENTIFIER ::= { enterprises 16099 }
ironMountain                      OBJECT IDENTIFIER ::= { enterprises 16100 }
cadero                            OBJECT IDENTIFIER ::= { enterprises 16101 }
miharuCommunications              OBJECT IDENTIFIER ::= { enterprises 16102 }
nilgiriNetworks                   OBJECT IDENTIFIER ::= { enterprises 16103 }
keycomInformationTechnologyCO     OBJECT IDENTIFIER ::= { enterprises 16104 }
standardInformationDataCentreOfMinistryOfEducationPRC OBJECT IDENTIFIER ::= { enterprises 16105 }
iccs                              OBJECT IDENTIFIER ::= { enterprises 16106 }
eneaDataAB                        OBJECT IDENTIFIER ::= { enterprises 16107 }
garderosSoftwareInnovations       OBJECT IDENTIFIER ::= { enterprises 16108 }
pfannenberg                       OBJECT IDENTIFIER ::= { enterprises 16109 }
infocentre2                       OBJECT IDENTIFIER ::= { enterprises 16110 }
beaumontHospital                  OBJECT IDENTIFIER ::= { enterprises 16111 }
valentineKOUTCHERBAEV             OBJECT IDENTIFIER ::= { enterprises 16112 }
networkDweebsCorporation          OBJECT IDENTIFIER ::= { enterprises 16113 }
qualstarCorporation               OBJECT IDENTIFIER ::= { enterprises 16114 }
cybersarge                        OBJECT IDENTIFIER ::= { enterprises 16115 }
enforcerGroup                     OBJECT IDENTIFIER ::= { enterprises 16116 }
revDNetworks                      OBJECT IDENTIFIER ::= { enterprises 16117 }
threeGfp                          OBJECT IDENTIFIER ::= { enterprises 16118 }
catalogcom                        OBJECT IDENTIFIER ::= { enterprises 16119 }
simcon                            OBJECT IDENTIFIER ::= { enterprises 16120 }
caliberTechnoloigiesAndConsultancy OBJECT IDENTIFIER ::= { enterprises 16121 }
netguild                          OBJECT IDENTIFIER ::= { enterprises 16122 }
universityOfFlorence              OBJECT IDENTIFIER ::= { enterprises 16123 }
x32Pty                            OBJECT IDENTIFIER ::= { enterprises 16124 }
netSPACE                          OBJECT IDENTIFIER ::= { enterprises 16125 }
parliamentOfFinland               OBJECT IDENTIFIER ::= { enterprises 16126 }
fathomTechnologyKFT               OBJECT IDENTIFIER ::= { enterprises 16127 }
aLAWRENCERIEDEL                   OBJECT IDENTIFIER ::= { enterprises 16128 }
lighthouseTrainingAndConsultingSrl OBJECT IDENTIFIER ::= { enterprises 16129 }
necAustraliaPL                    OBJECT IDENTIFIER ::= { enterprises 16130 }
humaxCo                           OBJECT IDENTIFIER ::= { enterprises 16131 }
phamKimBinhNguyen                 OBJECT IDENTIFIER ::= { enterprises 16132 }
arturSabik                        OBJECT IDENTIFIER ::= { enterprises 16133 }
cirtiDeNantes                     OBJECT IDENTIFIER ::= { enterprises 16134 }
coherentLight                     OBJECT IDENTIFIER ::= { enterprises 16135 }
ftInteractiveData                 OBJECT IDENTIFIER ::= { enterprises 16136 }
drHuggleAndPartner                OBJECT IDENTIFIER ::= { enterprises 16137 }
eTradeFinancial                   OBJECT IDENTIFIER ::= { enterprises 16138 }
compellentTechnologies            OBJECT IDENTIFIER ::= { enterprises 16139 }
mozappsorg                        OBJECT IDENTIFIER ::= { enterprises 16140 }
aNeTInternetServicesBv            OBJECT IDENTIFIER ::= { enterprises 16141 }
networkTechnologyAndEngineeringInstituteOfXi OBJECT IDENTIFIER ::= { enterprises 16142 }
ginaAndJonathanOberg              OBJECT IDENTIFIER ::= { enterprises 16143 }
kerberos                          OBJECT IDENTIFIER ::= { enterprises 16144 }
dresearchDigitalMediaSystems      OBJECT IDENTIFIER ::= { enterprises 16145 }
unitedBulgarianBank               OBJECT IDENTIFIER ::= { enterprises 16146 }
inty                              OBJECT IDENTIFIER ::= { enterprises 16147 }
javarealmSoftwareDevelopmentTeam  OBJECT IDENTIFIER ::= { enterprises 16148 }
delMarAnalytical                  OBJECT IDENTIFIER ::= { enterprises 16149 }
whiteWolfCamarilla                OBJECT IDENTIFIER ::= { enterprises 16150 }
pimaCommunityCollege              OBJECT IDENTIFIER ::= { enterprises 16151 }
theCincinnatiInsuranceCompanies   OBJECT IDENTIFIER ::= { enterprises 16152 }
snert                             OBJECT IDENTIFIER ::= { enterprises 16153 }
networkResourceTechnologiesCorp   OBJECT IDENTIFIER ::= { enterprises 16154 }
halcyonflame                      OBJECT IDENTIFIER ::= { enterprises 16155 }
feralNerdsEnterprises             OBJECT IDENTIFIER ::= { enterprises 16156 }
rdi                               OBJECT IDENTIFIER ::= { enterprises 16157 }
citrPty                           OBJECT IDENTIFIER ::= { enterprises 16158 }
uqBusinessSchool                  OBJECT IDENTIFIER ::= { enterprises 16159 }
sphereSystems                     OBJECT IDENTIFIER ::= { enterprises 16160 }
cscScientificComputing            OBJECT IDENTIFIER ::= { enterprises 16161 }
rmSystemHolding                   OBJECT IDENTIFIER ::= { enterprises 16162 }
elettronikaSrl                    OBJECT IDENTIFIER ::= { enterprises 16163 }
zylk                              OBJECT IDENTIFIER ::= { enterprises 16164 }
crescendoNetworks                 OBJECT IDENTIFIER ::= { enterprises 16165 }
universityOfSheffield             OBJECT IDENTIFIER ::= { enterprises 16166 }
repsolQuimica                     OBJECT IDENTIFIER ::= { enterprises 16167 }
medisyncMidwestLimited            OBJECT IDENTIFIER ::= { enterprises 16168 }
teleredes                         OBJECT IDENTIFIER ::= { enterprises 16169 }
totaleasy                         OBJECT IDENTIFIER ::= { enterprises 16170 }
zucchetticomSrl                   OBJECT IDENTIFIER ::= { enterprises 16171 }
danger                            OBJECT IDENTIFIER ::= { enterprises 16172 }
arizonaWesternCollege             OBJECT IDENTIFIER ::= { enterprises 16173 }
sensatronicsLLC                   OBJECT IDENTIFIER ::= { enterprises 16174 }
triadeBeratungsgesellschaftF      OBJECT IDENTIFIER ::= { enterprises 16175 }
zephraCorp                        OBJECT IDENTIFIER ::= { enterprises 16176 }
ontimeNetworksAS                  OBJECT IDENTIFIER ::= { enterprises 16177 }
wellpointHealthNetworks           OBJECT IDENTIFIER ::= { enterprises 16178 }
wanNorway                         OBJECT IDENTIFIER ::= { enterprises 16179 }
blueDataNetworks                  OBJECT IDENTIFIER ::= { enterprises 16180 }
tadArtis                          OBJECT IDENTIFIER ::= { enterprises 16181 }
whitesmithsAustraliaPty           OBJECT IDENTIFIER ::= { enterprises 16182 }
hanaroTelecom                     OBJECT IDENTIFIER ::= { enterprises 16183 }
ptIndoramaSyntheticsTbk           OBJECT IDENTIFIER ::= { enterprises 16184 }
nmSystemsCo                       OBJECT IDENTIFIER ::= { enterprises 16185 }
peterSchneiderEDV                 OBJECT IDENTIFIER ::= { enterprises 16186 }
unassigned8                       OBJECT IDENTIFIER ::= { enterprises 16187 }
materialsScienceAndTechnologyDeptUnivOfCreteGREECE OBJECT IDENTIFIER ::= { enterprises 16188 }
assuredCommunicationsGroupLimited OBJECT IDENTIFIER ::= { enterprises 16189 }
colegioOficialDeArquitectosDeMadrid OBJECT IDENTIFIER ::= { enterprises 16190 }
nightfireSoftware                 OBJECT IDENTIFIER ::= { enterprises 16191 }
bcnAssociates                     OBJECT IDENTIFIER ::= { enterprises 16192 }
eagleMountainInternationalChurch  OBJECT IDENTIFIER ::= { enterprises 16193 }
ranchoMorado                      OBJECT IDENTIFIER ::= { enterprises 16194 }
thomsonCorpSwitzerlandAG          OBJECT IDENTIFIER ::= { enterprises 16195 }
washingtonMutual                  OBJECT IDENTIFIER ::= { enterprises 16196 }
scoobtec                          OBJECT IDENTIFIER ::= { enterprises 16197 }
investmentCompanyInstitute        OBJECT IDENTIFIER ::= { enterprises 16198 }
openforceInformationTechnologyGesmbH OBJECT IDENTIFIER ::= { enterprises 16199 }
casero                            OBJECT IDENTIFIER ::= { enterprises 16200 }
tiTelecomunicazioniAndInformatica OBJECT IDENTIFIER ::= { enterprises 16201 }
oaklandUniversity                 OBJECT IDENTIFIER ::= { enterprises 16202 }
sysdataKft                        OBJECT IDENTIFIER ::= { enterprises 16203 }
westinghouseElectricCompany       OBJECT IDENTIFIER ::= { enterprises 16204 }
tSystemsGCFMSY                    OBJECT IDENTIFIER ::= { enterprises 16205 }
mobileTeleSystemsLimitedLibilityCompany OBJECT IDENTIFIER ::= { enterprises 16206 }
splicecom                         OBJECT IDENTIFIER ::= { enterprises 16207 }
universidadeLusiada               OBJECT IDENTIFIER ::= { enterprises 16208 }
collaborativeNetworkTechnologies  OBJECT IDENTIFIER ::= { enterprises 16209 }
deltaPiktoriOy                    OBJECT IDENTIFIER ::= { enterprises 16210 }
certifiedSecuritySolutions        OBJECT IDENTIFIER ::= { enterprises 16211 }
wang                              OBJECT IDENTIFIER ::= { enterprises 16212 }
cenISSSXFSWorkshop                OBJECT IDENTIFIER ::= { enterprises 16213 }
pehkonenFamily                    OBJECT IDENTIFIER ::= { enterprises 16214 }
elbitSystems                      OBJECT IDENTIFIER ::= { enterprises 16215 }
trinityCCConsulting               OBJECT IDENTIFIER ::= { enterprises 16216 }
kddiMediaWillCorporation          OBJECT IDENTIFIER ::= { enterprises 16217 }
talkline                          OBJECT IDENTIFIER ::= { enterprises 16218 }
dbTelematik                       OBJECT IDENTIFIER ::= { enterprises 16219 }
landmat                           OBJECT IDENTIFIER ::= { enterprises 16220 }
strodl                            OBJECT IDENTIFIER ::= { enterprises 16221 }
donobi                            OBJECT IDENTIFIER ::= { enterprises 16222 }
globalMessagingSolutions          OBJECT IDENTIFIER ::= { enterprises 16223 }
htbluvaWienerNeustadt             OBJECT IDENTIFIER ::= { enterprises 16224 }
paetecCommunications              OBJECT IDENTIFIER ::= { enterprises 16225 }
publicServiceEnterpriseGroup      OBJECT IDENTIFIER ::= { enterprises 16226 }
vitalstream                       OBJECT IDENTIFIER ::= { enterprises 16227 }
auriqSystems                      OBJECT IDENTIFIER ::= { enterprises 16228 }
nuInformationssysteme             OBJECT IDENTIFIER ::= { enterprises 16229 }
ecornell                          OBJECT IDENTIFIER ::= { enterprises 16230 }
introspectConsulting              OBJECT IDENTIFIER ::= { enterprises 16231 }
netmanjProject                    OBJECT IDENTIFIER ::= { enterprises 16232 }
tukcedoServices                   OBJECT IDENTIFIER ::= { enterprises 16233 }
dogico                            OBJECT IDENTIFIER ::= { enterprises 16234 }
insigniaFinancialGroup            OBJECT IDENTIFIER ::= { enterprises 16235 }
andrewMaldonadoConsulting         OBJECT IDENTIFIER ::= { enterprises 16236 }
mantisTechnologyLLC               OBJECT IDENTIFIER ::= { enterprises 16237 }
thecartcompanycom                 OBJECT IDENTIFIER ::= { enterprises 16238 }
corbettSystemsDevelopment         OBJECT IDENTIFIER ::= { enterprises 16239 }
skinoskeTech                      OBJECT IDENTIFIER ::= { enterprises 16240 }
butlernetworksAS                  OBJECT IDENTIFIER ::= { enterprises 16241 }
thamesValleyUniversity            OBJECT IDENTIFIER ::= { enterprises 16242 }
avsConsulting                     OBJECT IDENTIFIER ::= { enterprises 16243 }
ecoleDesMinesD                    OBJECT IDENTIFIER ::= { enterprises 16244 }
humanor                           OBJECT IDENTIFIER ::= { enterprises 16245 }
hertzComunicaciones               OBJECT IDENTIFIER ::= { enterprises 16246 }
eservglobal                       OBJECT IDENTIFIER ::= { enterprises 16247 }
litusat                           OBJECT IDENTIFIER ::= { enterprises 16248 }
italtelSpA                        OBJECT IDENTIFIER ::= { enterprises 16249 }
catchfireSystems                  OBJECT IDENTIFIER ::= { enterprises 16250 }
bonusoIndustries                  OBJECT IDENTIFIER ::= { enterprises 16251 }
m                                 OBJECT IDENTIFIER ::= { enterprises 16252 }
m2                                OBJECT IDENTIFIER ::= { enterprises 16253 }
holmenPaperAB                     OBJECT IDENTIFIER ::= { enterprises 16254 }
actionEngineCorp                  OBJECT IDENTIFIER ::= { enterprises 16255 }
develtech                         OBJECT IDENTIFIER ::= { enterprises 16256 }
theHongKongPolytechnicUniversity  OBJECT IDENTIFIER ::= { enterprises 16257 }
feelingk                          OBJECT IDENTIFIER ::= { enterprises 16258 }
kowaCOMPANY                       OBJECT IDENTIFIER ::= { enterprises 16259 }
theFreeBSDChinaCommunity          OBJECT IDENTIFIER ::= { enterprises 16260 }
kopintDatorgRt                    OBJECT IDENTIFIER ::= { enterprises 16261 }
repsolPetroleo                    OBJECT IDENTIFIER ::= { enterprises 16262 }
swisswebgroupGmbh                 OBJECT IDENTIFIER ::= { enterprises 16263 }
itheon                            OBJECT IDENTIFIER ::= { enterprises 16264 }
openMethods                       OBJECT IDENTIFIER ::= { enterprises 16265 }
theOptymGroup                     OBJECT IDENTIFIER ::= { enterprises 16266 }
americanNetworkCommunications     OBJECT IDENTIFIER ::= { enterprises 16267 }
usLinuxNetworks                   OBJECT IDENTIFIER ::= { enterprises 16268 }
iomart                            OBJECT IDENTIFIER ::= { enterprises 16269 }
gravityrockcom                    OBJECT IDENTIFIER ::= { enterprises 16270 }
newSouthWalesFireBrigades         OBJECT IDENTIFIER ::= { enterprises 16271 }
legend                            OBJECT IDENTIFIER ::= { enterprises 16272 }
nexgeTechnologyP                  OBJECT IDENTIFIER ::= { enterprises 16273 }
telmatIndustrie                   OBJECT IDENTIFIER ::= { enterprises 16274 }
universityOfKuopio                OBJECT IDENTIFIER ::= { enterprises 16275 }
communicationsRegulationCommission OBJECT IDENTIFIER ::= { enterprises 16276 }
mobileInternetLimited             OBJECT IDENTIFIER ::= { enterprises 16277 }
slabInformationssysteme           OBJECT IDENTIFIER ::= { enterprises 16278 }
stFrancisBorgiaRHS                OBJECT IDENTIFIER ::= { enterprises 16279 }
oltpcorp                          OBJECT IDENTIFIER ::= { enterprises 16280 }
syslogGmbh                        OBJECT IDENTIFIER ::= { enterprises 16281 }
h5Technologies                    OBJECT IDENTIFIER ::= { enterprises 16282 }
om                                OBJECT IDENTIFIER ::= { enterprises 16283 }
quadforeCorporation               OBJECT IDENTIFIER ::= { enterprises 16284 }
ibpsearch                         OBJECT IDENTIFIER ::= { enterprises 16285 }
hungarocom                        OBJECT IDENTIFIER ::= { enterprises 16286 }
swissFederalInstituteOfTechnology OBJECT IDENTIFIER ::= { enterprises 16287 }
edvBeratung                       OBJECT IDENTIFIER ::= { enterprises 16288 }
mediva                            OBJECT IDENTIFIER ::= { enterprises 16289 }
siat                              OBJECT IDENTIFIER ::= { enterprises 16290 }
meetingMaker                      OBJECT IDENTIFIER ::= { enterprises 16291 }
susurro                           OBJECT IDENTIFIER ::= { enterprises 16292 }
brvlTechnology                    OBJECT IDENTIFIER ::= { enterprises 16293 }
appliedInstruments                OBJECT IDENTIFIER ::= { enterprises 16294 }
ormondCollege                     OBJECT IDENTIFIER ::= { enterprises 16295 }
vindicia                          OBJECT IDENTIFIER ::= { enterprises 16296 }
semnode                           OBJECT IDENTIFIER ::= { enterprises 16297 }
hanbangSoftTechnologyCo           OBJECT IDENTIFIER ::= { enterprises 16298 }
coregaKK                          OBJECT IDENTIFIER ::= { enterprises 16299 }
penguinIndiaLinuxSolutionsPvt     OBJECT IDENTIFIER ::= { enterprises 16300 }
silesianUniversityInOpava         OBJECT IDENTIFIER ::= { enterprises 16301 }
intrae                            OBJECT IDENTIFIER ::= { enterprises 16302 }
sansSerif                         OBJECT IDENTIFIER ::= { enterprises 16303 }
eads                              OBJECT IDENTIFIER ::= { enterprises 16304 }
kibsADSkopje                      OBJECT IDENTIFIER ::= { enterprises 16305 }
repsolDistribucion                OBJECT IDENTIFIER ::= { enterprises 16306 }
braddahead                        OBJECT IDENTIFIER ::= { enterprises 16307 }
rhoenKLINIKUMAG                   OBJECT IDENTIFIER ::= { enterprises 16308 }
nttSoftwareCorporation            OBJECT IDENTIFIER ::= { enterprises 16309 }
marketlineRt                      OBJECT IDENTIFIER ::= { enterprises 16310 }
alatec                            OBJECT IDENTIFIER ::= { enterprises 16311 }
registercom                       OBJECT IDENTIFIER ::= { enterprises 16312 }
valemountNetworksCorp             OBJECT IDENTIFIER ::= { enterprises 16313 }
bureautiqueServicesDeveloppement  OBJECT IDENTIFIER ::= { enterprises 16314 }
xsupport                         OBJECT IDENTIFIER ::= { enterprises 16315 }
hsbccom                           OBJECT IDENTIFIER ::= { enterprises 16316 }
quebecorWorldNorthAmerica         OBJECT IDENTIFIER ::= { enterprises 16317 }
empuron                           OBJECT IDENTIFIER ::= { enterprises 16318 }
viavisMobileSolutions             OBJECT IDENTIFIER ::= { enterprises 16319 }
theBrainRoom                      OBJECT IDENTIFIER ::= { enterprises 16320 }
zoomInternational                 OBJECT IDENTIFIER ::= { enterprises 16321 }
leadingEdgeTelemetry              OBJECT IDENTIFIER ::= { enterprises 16322 }
traxHoldings                      OBJECT IDENTIFIER ::= { enterprises 16323 }
itelsys                           OBJECT IDENTIFIER ::= { enterprises 16324 }
nescoCO                           OBJECT IDENTIFIER ::= { enterprises 16325 }
iyaburocom                        OBJECT IDENTIFIER ::= { enterprises 16326 }
markChesney                       OBJECT IDENTIFIER ::= { enterprises 16327 }
nariCorp                          OBJECT IDENTIFIER ::= { enterprises 16328 }
adisysOy                          OBJECT IDENTIFIER ::= { enterprises 16329 }
reutechRadarSystem                OBJECT IDENTIFIER ::= { enterprises 16330 }
cosmocode                         OBJECT IDENTIFIER ::= { enterprises 16331 }
longshineTechnologieEurope        OBJECT IDENTIFIER ::= { enterprises 16332 }
bitmineAB                         OBJECT IDENTIFIER ::= { enterprises 16333 }
northropGrumman                   OBJECT IDENTIFIER ::= { enterprises 16334 }
seoulElectricPowerSystemCo        OBJECT IDENTIFIER ::= { enterprises 16335 }
alatec2                           OBJECT IDENTIFIER ::= { enterprises 16336 }
canadianNationalRailwayCompany    OBJECT IDENTIFIER ::= { enterprises 16337 }
ipone                             OBJECT IDENTIFIER ::= { enterprises 16338 }
globeopFinancialServices          OBJECT IDENTIFIER ::= { enterprises 16339 }
whiteRockNetworks                 OBJECT IDENTIFIER ::= { enterprises 16340 }
biomedicalInformaticsResearchNetwork OBJECT IDENTIFIER ::= { enterprises 16341 }
mentaGroup                        OBJECT IDENTIFIER ::= { enterprises 16342 }
uttcUnitedTriTechCorporation      OBJECT IDENTIFIER ::= { enterprises 16343 }
perfigo                           OBJECT IDENTIFIER ::= { enterprises 16344 }
theAnvilOrganisation              OBJECT IDENTIFIER ::= { enterprises 16345 }
farabiTechnology                  OBJECT IDENTIFIER ::= { enterprises 16346 }
ipcast                            OBJECT IDENTIFIER ::= { enterprises 16347 }
shanghaiTransfiberScienceAndTechnologyCo OBJECT IDENTIFIER ::= { enterprises 16348 }
comgear                           OBJECT IDENTIFIER ::= { enterprises 16349 }
totCorporationPublicCompanyLimited OBJECT IDENTIFIER ::= { enterprises 16350 }
caixaBankSA                       OBJECT IDENTIFIER ::= { enterprises 16351 }
newmanCollegeOfHE                 OBJECT IDENTIFIER ::= { enterprises 16352 }
howaldtswerkeDeutscheWerftAG      OBJECT IDENTIFIER ::= { enterprises 16353 }
gruppennest                       OBJECT IDENTIFIER ::= { enterprises 16354 }
midray                            OBJECT IDENTIFIER ::= { enterprises 16355 }
transferLimited                   OBJECT IDENTIFIER ::= { enterprises 16356 }
hainCelestialGroup                OBJECT IDENTIFIER ::= { enterprises 16357 }
unitedCarrierNetworks             OBJECT IDENTIFIER ::= { enterprises 16358 }
millerSamuel                      OBJECT IDENTIFIER ::= { enterprises 16359 }
contralor                         OBJECT IDENTIFIER ::= { enterprises 16360 }
progressiveLinuxConsultantsLLC    OBJECT IDENTIFIER ::= { enterprises 16361 }
watersNetworkSystems              OBJECT IDENTIFIER ::= { enterprises 16362 }
scholzAndVOLKMERIntermedialesDesign OBJECT IDENTIFIER ::= { enterprises 16363 }
smartdata                         OBJECT IDENTIFIER ::= { enterprises 16364 }
cskSoftwareAG                     OBJECT IDENTIFIER ::= { enterprises 16365 }
informaDELPERU                    OBJECT IDENTIFIER ::= { enterprises 16366 }
saarstahl                         OBJECT IDENTIFIER ::= { enterprises 16367 }
sysapexCommunications             OBJECT IDENTIFIER ::= { enterprises 16368 }
clarkUniversity                   OBJECT IDENTIFIER ::= { enterprises 16369 }
dassConsultingGroup               OBJECT IDENTIFIER ::= { enterprises 16370 }
tygrysekcom                       OBJECT IDENTIFIER ::= { enterprises 16371 }
tMobileCzechRepublicAs            OBJECT IDENTIFIER ::= { enterprises 16372 }
federalPublicServiceTransportAndMobility OBJECT IDENTIFIER ::= { enterprises 16373 }
nvMultikabel                      OBJECT IDENTIFIER ::= { enterprises 16374 }
universityOfAthens                OBJECT IDENTIFIER ::= { enterprises 16375 }
acoss                             OBJECT IDENTIFIER ::= { enterprises 16376 }
imctech                           OBJECT IDENTIFIER ::= { enterprises 16377 }
sarianSystemsLimited              OBJECT IDENTIFIER ::= { enterprises 16378 }
riverCitiesReader                 OBJECT IDENTIFIER ::= { enterprises 16379 }
nexvuTechnologies                 OBJECT IDENTIFIER ::= { enterprises 16380 }
verifiber                         OBJECT IDENTIFIER ::= { enterprises 16381 }
interboxInternet                  OBJECT IDENTIFIER ::= { enterprises 16382 }
hpGSESecurity                     OBJECT IDENTIFIER ::= { enterprises 16383 }
californiaStatePolytechnicUniversity OBJECT IDENTIFIER ::= { enterprises 16384 }
hudli                             OBJECT IDENTIFIER ::= { enterprises 16385 }
daxiongmao                        OBJECT IDENTIFIER ::= { enterprises 16386 }
oeoneCorporation                  OBJECT IDENTIFIER ::= { enterprises 16387 }
j                                 OBJECT IDENTIFIER ::= { enterprises 16388 }
pegasusEDVBetreuungs              OBJECT IDENTIFIER ::= { enterprises 16389 }
vinesysTechnology                 OBJECT IDENTIFIER ::= { enterprises 16390 }
routeone                          OBJECT IDENTIFIER ::= { enterprises 16391 }
cortlandCommunications            OBJECT IDENTIFIER ::= { enterprises 16392 }
seanChampEnterprises              OBJECT IDENTIFIER ::= { enterprises 16393 }
pigeonPointSystems                OBJECT IDENTIFIER ::= { enterprises 16394 }
williamRSowerbutts                OBJECT IDENTIFIER ::= { enterprises 16395 }
justinknashcom                    OBJECT IDENTIFIER ::= { enterprises 16396 }
usArmyALTESS                      OBJECT IDENTIFIER ::= { enterprises 16397 }
metallectCorp                     OBJECT IDENTIFIER ::= { enterprises 16398 }
greyhavens                        OBJECT IDENTIFIER ::= { enterprises 16399 }
singaporeTelecommunicationLimited OBJECT IDENTIFIER ::= { enterprises 16400 }
hewlettPackardSlovakia            OBJECT IDENTIFIER ::= { enterprises 16401 }
teleformix                        OBJECT IDENTIFIER ::= { enterprises 16402 }
brobusInternational               OBJECT IDENTIFIER ::= { enterprises 16403 }
neuralworx                        OBJECT IDENTIFIER ::= { enterprises 16404 }
cpegnet                           OBJECT IDENTIFIER ::= { enterprises 16405 }
adwin                             OBJECT IDENTIFIER ::= { enterprises 16406 }
lanuxLimited                      OBJECT IDENTIFIER ::= { enterprises 16407 }
leoConsulting                     OBJECT IDENTIFIER ::= { enterprises 16408 }
futuri                            OBJECT IDENTIFIER ::= { enterprises 16409 }
necCOMPUTERSINTERNATIONALBV       OBJECT IDENTIFIER ::= { enterprises 16410 }
indiciaNederlandBv                OBJECT IDENTIFIER ::= { enterprises 16411 }
homeHealthCorporationOfAmerica    OBJECT IDENTIFIER ::= { enterprises 16412 }
rahbanycom                        OBJECT IDENTIFIER ::= { enterprises 16413 }
itsanaddictionorg                 OBJECT IDENTIFIER ::= { enterprises 16414 }
bbradenahlAndHEggers              OBJECT IDENTIFIER ::= { enterprises 16415 }
realDATASC                        OBJECT IDENTIFIER ::= { enterprises 16416 }
tmcHealthCare                     OBJECT IDENTIFIER ::= { enterprises 16417 }
ulyssis                           OBJECT IDENTIFIER ::= { enterprises 16418 }
pinboard                          OBJECT IDENTIFIER ::= { enterprises 16419 }
sraInternational                  OBJECT IDENTIFIER ::= { enterprises 16420 }
christianAlbrechtsUniversitaet    OBJECT IDENTIFIER ::= { enterprises 16421 }
mumpkLimitedPartnership           OBJECT IDENTIFIER ::= { enterprises 16422 }
abacusResearchAG                  OBJECT IDENTIFIER ::= { enterprises 16423 }
alanta                            OBJECT IDENTIFIER ::= { enterprises 16424 }
cityUtilitiesOfSpringfieldMO      OBJECT IDENTIFIER ::= { enterprises 16425 }
lawrenceTechnologicalUniversity   OBJECT IDENTIFIER ::= { enterprises 16426 }
internetAccessFacilitiesBV        OBJECT IDENTIFIER ::= { enterprises 16427 }
dialAssurance                     OBJECT IDENTIFIER ::= { enterprises 16428 }
lindorffHoldingAS                 OBJECT IDENTIFIER ::= { enterprises 16429 }
mutinyLimited                     OBJECT IDENTIFIER ::= { enterprises 16430 }
tSystemsItaliaSpA                 OBJECT IDENTIFIER ::= { enterprises 16431 }
pkiInnovations                    OBJECT IDENTIFIER ::= { enterprises 16432 }
mooreheadCommunications           OBJECT IDENTIFIER ::= { enterprises 16433 }
jenzabar                          OBJECT IDENTIFIER ::= { enterprises 16434 }
clearswiftCorporation             OBJECT IDENTIFIER ::= { enterprises 16435 }
bookhamTechnologyPlc              OBJECT IDENTIFIER ::= { enterprises 16436 }
bart                              OBJECT IDENTIFIER ::= { enterprises 16437 }
kansasInformationConsortium       OBJECT IDENTIFIER ::= { enterprises 16438 }
pnxPty                            OBJECT IDENTIFIER ::= { enterprises 16439 }
netins                            OBJECT IDENTIFIER ::= { enterprises 16440 }
enst                              OBJECT IDENTIFIER ::= { enterprises 16441 }
proactiveAS                       OBJECT IDENTIFIER ::= { enterprises 16442 }
pAndoNedlloydLimited              OBJECT IDENTIFIER ::= { enterprises 16443 }
upti                              OBJECT IDENTIFIER ::= { enterprises 16444 }
kinetoWireless                    OBJECT IDENTIFIER ::= { enterprises 16445 }
adlink                            OBJECT IDENTIFIER ::= { enterprises 16446 }
epixInternetServices              OBJECT IDENTIFIER ::= { enterprises 16447 }
neogateCo                         OBJECT IDENTIFIER ::= { enterprises 16448 }
charcoalGenerationLimited         OBJECT IDENTIFIER ::= { enterprises 16449 }
itConcepts                        OBJECT IDENTIFIER ::= { enterprises 16450 }
smcPneumatics                     OBJECT IDENTIFIER ::= { enterprises 16451 }
infocompPty                       OBJECT IDENTIFIER ::= { enterprises 16452 }
beijingMunicipalLocalTaxationBureau OBJECT IDENTIFIER ::= { enterprises 16453 }
axway                             OBJECT IDENTIFIER ::= { enterprises 16454 }
dfsDeutscheFlugsicherung          OBJECT IDENTIFIER ::= { enterprises 16455 }
gplEletroEletronicaSA             OBJECT IDENTIFIER ::= { enterprises 16456 }
operaLogic                        OBJECT IDENTIFIER ::= { enterprises 16457 }
geminiMobileTechnology            OBJECT IDENTIFIER ::= { enterprises 16458 }
epygiTechnologies                 OBJECT IDENTIFIER ::= { enterprises 16459 }
convertronic                      OBJECT IDENTIFIER ::= { enterprises 16460 }
eurofluxoSuporteANovasTecnologias OBJECT IDENTIFIER ::= { enterprises 16461 }
javcoConsulting                   OBJECT IDENTIFIER ::= { enterprises 16462 }
metavanteCorporation              OBJECT IDENTIFIER ::= { enterprises 16463 }
pangolinSoftwareIndustries        OBJECT IDENTIFIER ::= { enterprises 16464 }
stateCollegeAreaSchoolDistrict    OBJECT IDENTIFIER ::= { enterprises 16465 }
sonartechAtlasPty                 OBJECT IDENTIFIER ::= { enterprises 16466 }
gigaworks                         OBJECT IDENTIFIER ::= { enterprises 16467 }
deriva                            OBJECT IDENTIFIER ::= { enterprises 16468 }
coastalWaveInternet               OBJECT IDENTIFIER ::= { enterprises 16469 }
kebaAG                            OBJECT IDENTIFIER ::= { enterprises 16470 }
scanASSOCIATESSDNBHD              OBJECT IDENTIFIER ::= { enterprises 16471 }
qmedit                            OBJECT IDENTIFIER ::= { enterprises 16472 }
terranet                          OBJECT IDENTIFIER ::= { enterprises 16473 }
mencial                           OBJECT IDENTIFIER ::= { enterprises 16474 }
haysIMS                           OBJECT IDENTIFIER ::= { enterprises 16475 }
awsysGmbh                         OBJECT IDENTIFIER ::= { enterprises 16476 }
syslineSpA                        OBJECT IDENTIFIER ::= { enterprises 16477 }
eiweiTrainingAndConsulting        OBJECT IDENTIFIER ::= { enterprises 16478 }
p4Tecnologia                      OBJECT IDENTIFIER ::= { enterprises 16479 }
ministryOfTransportationOfOntario OBJECT IDENTIFIER ::= { enterprises 16480 }
joutfittersLLC                    OBJECT IDENTIFIER ::= { enterprises 16481 }
oldDominionUniversity             OBJECT IDENTIFIER ::= { enterprises 16482 }
pureNetworks                      OBJECT IDENTIFIER ::= { enterprises 16483 }
gavinNewman                       OBJECT IDENTIFIER ::= { enterprises 16484 }
advancedMultifakeSystems          OBJECT IDENTIFIER ::= { enterprises 16485 }
dauphinMultiMedia                 OBJECT IDENTIFIER ::= { enterprises 16486 }
thalesNL                          OBJECT IDENTIFIER ::= { enterprises 16487 }
electralink                       OBJECT IDENTIFIER ::= { enterprises 16488 }
theHanoverCompany                 OBJECT IDENTIFIER ::= { enterprises 16489 }
sentryware                        OBJECT IDENTIFIER ::= { enterprises 16490 }
inmetricsLTDAEPP                  OBJECT IDENTIFIER ::= { enterprises 16491 }
scitorCorporation                 OBJECT IDENTIFIER ::= { enterprises 16492 }
propagateNetworks                 OBJECT IDENTIFIER ::= { enterprises 16493 }
massmutual                        OBJECT IDENTIFIER ::= { enterprises 16494 }
iafricacom                        OBJECT IDENTIFIER ::= { enterprises 16495 }
acuRITECOMPANIESINC               OBJECT IDENTIFIER ::= { enterprises 16496 }
repsolExploracion                 OBJECT IDENTIFIER ::= { enterprises 16497 }
mediumSOFTAs                      OBJECT IDENTIFIER ::= { enterprises 16498 }
graburnTechnology                 OBJECT IDENTIFIER ::= { enterprises 16499 }
swac                              OBJECT IDENTIFIER ::= { enterprises 16500 }
sAndhGreenpoints                  OBJECT IDENTIFIER ::= { enterprises 16501 }
lgbPhOeNiX                        OBJECT IDENTIFIER ::= { enterprises 16502 }
prairieFireInternetTechnologies   OBJECT IDENTIFIER ::= { enterprises 16503 }
sindhsoft                         OBJECT IDENTIFIER ::= { enterprises 16504 }
teamstaff                         OBJECT IDENTIFIER ::= { enterprises 16505 }
nextorage                         OBJECT IDENTIFIER ::= { enterprises 16506 }
evanzEnterprises                  OBJECT IDENTIFIER ::= { enterprises 16507 }
progelSrl                         OBJECT IDENTIFIER ::= { enterprises 16508 }
associationDesMedecinsDeSaintHilaire OBJECT IDENTIFIER ::= { enterprises 16509 }
thePepsiBottlingGroup             OBJECT IDENTIFIER ::= { enterprises 16510 }
sentorManagedSecurityServicesAB   OBJECT IDENTIFIER ::= { enterprises 16511 }
medienzentrumOsnabrueck           OBJECT IDENTIFIER ::= { enterprises 16512 }
monacoInteractive                 OBJECT IDENTIFIER ::= { enterprises 16513 }
uunetSA                           OBJECT IDENTIFIER ::= { enterprises 16514 }
grnetSA                           OBJECT IDENTIFIER ::= { enterprises 16515 }
elipsan                           OBJECT IDENTIFIER ::= { enterprises 16516 }
partnersHealthCareSystem          OBJECT IDENTIFIER ::= { enterprises 16517 }
newParticlesCorporation           OBJECT IDENTIFIER ::= { enterprises 16518 }
microdasys                        OBJECT IDENTIFIER ::= { enterprises 16519 }
pgCs                              OBJECT IDENTIFIER ::= { enterprises 16520 }
prontoNetworks                    OBJECT IDENTIFIER ::= { enterprises 16521 }
telefonicaPublicidadEInformacionSA OBJECT IDENTIFIER ::= { enterprises 16522 }
ericYeo                           OBJECT IDENTIFIER ::= { enterprises 16523 }
mortyAbzug                        OBJECT IDENTIFIER ::= { enterprises 16524 }
unicorn                           OBJECT IDENTIFIER ::= { enterprises 16525 }
kyaGroup                          OBJECT IDENTIFIER ::= { enterprises 16526 }
internetPicturesCorporation       OBJECT IDENTIFIER ::= { enterprises 16527 }
leadtekResearch                   OBJECT IDENTIFIER ::= { enterprises 16528 }
hclInfosystemsLimited             OBJECT IDENTIFIER ::= { enterprises 16529 }
exaltTechnologies                 OBJECT IDENTIFIER ::= { enterprises 16530 }
bricoD                            OBJECT IDENTIFIER ::= { enterprises 16531 }
spardaDatenverarbeitungEG         OBJECT IDENTIFIER ::= { enterprises 16532 }
consejoGeneralDeLaAbogaciaEspa    OBJECT IDENTIFIER ::= { enterprises 16533 }
mycomInternational                OBJECT IDENTIFIER ::= { enterprises 16534 }
bitbandTechnologies               OBJECT IDENTIFIER ::= { enterprises 16535 }
tiscaliUK                         OBJECT IDENTIFIER ::= { enterprises 16536 }
wirelessDataServices              OBJECT IDENTIFIER ::= { enterprises 16537 }
progressiveElectricalServices     OBJECT IDENTIFIER ::= { enterprises 16538 }
graberEnterprises                 OBJECT IDENTIFIER ::= { enterprises 16539 }
edsPubblicaAmministrazioneSpA     OBJECT IDENTIFIER ::= { enterprises 16540 }
wapitiRegionalLibrary             OBJECT IDENTIFIER ::= { enterprises 16541 }
harleySystems                     OBJECT IDENTIFIER ::= { enterprises 16542 }
standardBankOfSouthAfrica         OBJECT IDENTIFIER ::= { enterprises 16543 }
leasfinanzAG                      OBJECT IDENTIFIER ::= { enterprises 16544 }
cardserviceInternational          OBJECT IDENTIFIER ::= { enterprises 16545 }
bbhk                              OBJECT IDENTIFIER ::= { enterprises 16546 }
alixen                            OBJECT IDENTIFIER ::= { enterprises 16547 }
fachschaftElektrotechnikUndInformationstechnik OBJECT IDENTIFIER ::= { enterprises 16548 }
giddensIndustries                 OBJECT IDENTIFIER ::= { enterprises 16549 }
mastersOfBranding                 OBJECT IDENTIFIER ::= { enterprises 16550 }
comquestTecnologia                OBJECT IDENTIFIER ::= { enterprises 16551 }
clearCommunicationsCorporation    OBJECT IDENTIFIER ::= { enterprises 16552 }
mediaworlds                       OBJECT IDENTIFIER ::= { enterprises 16553 }
mdsReprocessing                   OBJECT IDENTIFIER ::= { enterprises 16554 }
vassarCollege                     OBJECT IDENTIFIER ::= { enterprises 16555 }
wwwschenkmancom                   OBJECT IDENTIFIER ::= { enterprises 16556 }
irtElectronicsPty                 OBJECT IDENTIFIER ::= { enterprises 16557 }
jiangsuYitongHighTechCo           OBJECT IDENTIFIER ::= { enterprises 16558 }
alocBonnierAS                     OBJECT IDENTIFIER ::= { enterprises 16559 }
drT                               OBJECT IDENTIFIER ::= { enterprises 16560 }
ftgSandarTeleCastAS               OBJECT IDENTIFIER ::= { enterprises 16561 }
depaulUniversity                  OBJECT IDENTIFIER ::= { enterprises 16562 }
intersystems                      OBJECT IDENTIFIER ::= { enterprises 16563 }
everstream                        OBJECT IDENTIFIER ::= { enterprises 16564 }
pineDigitalSecurity               OBJECT IDENTIFIER ::= { enterprises 16565 }
rtShinAndAssociates               OBJECT IDENTIFIER ::= { enterprises 16566 }
universityOfBelize                OBJECT IDENTIFIER ::= { enterprises 16567 }
fukkenCO                          OBJECT IDENTIFIER ::= { enterprises 16568 }
realvision                        OBJECT IDENTIFIER ::= { enterprises 16569 }
linuxAtWorkde                     OBJECT IDENTIFIER ::= { enterprises 16570 }
westelMobileTelecommunicationsCompany OBJECT IDENTIFIER ::= { enterprises 16571 }
centroTecnicoPerLaReteUnitariaDellaPubblicaAmministrazione OBJECT IDENTIFIER ::= { enterprises 16572 }
icpEuropePLC                      OBJECT IDENTIFIER ::= { enterprises 16573 }
ontarioSystems                    OBJECT IDENTIFIER ::= { enterprises 16574 }
oopsOrg                           OBJECT IDENTIFIER ::= { enterprises 16575 }
ndsoftware                        OBJECT IDENTIFIER ::= { enterprises 16576 }
virtualTargetsCenter              OBJECT IDENTIFIER ::= { enterprises 16577 }
geos                              OBJECT IDENTIFIER ::= { enterprises 16578 }
meurisse                          OBJECT IDENTIFIER ::= { enterprises 16579 }
swiftelCommunications             OBJECT IDENTIFIER ::= { enterprises 16580 }
siig                              OBJECT IDENTIFIER ::= { enterprises 16581 }
bocONCOLOGYCENTER                 OBJECT IDENTIFIER ::= { enterprises 16582 }
net6a                             OBJECT IDENTIFIER ::= { enterprises 16583 }
evpuAs                            OBJECT IDENTIFIER ::= { enterprises 16584 }
isolutionSC                       OBJECT IDENTIFIER ::= { enterprises 16585 }
pallasAthenaBV                    OBJECT IDENTIFIER ::= { enterprises 16586 }
globalLocate                      OBJECT IDENTIFIER ::= { enterprises 16587 }
ssiMicro                          OBJECT IDENTIFIER ::= { enterprises 16588 }
cnmpNetworks                      OBJECT IDENTIFIER ::= { enterprises 16589 }
scytlOnlineWorldSecuritySA        OBJECT IDENTIFIER ::= { enterprises 16590 }
avtec                             OBJECT IDENTIFIER ::= { enterprises 16591 }
laboratoryAutomation              OBJECT IDENTIFIER ::= { enterprises 16592 }
stixo                             OBJECT IDENTIFIER ::= { enterprises 16593 }
embtek                            OBJECT IDENTIFIER ::= { enterprises 16594 }
reDesign                          OBJECT IDENTIFIER ::= { enterprises 16595 }
trenddiscoveryCorporation         OBJECT IDENTIFIER ::= { enterprises 16596 }
landalaN                          OBJECT IDENTIFIER ::= { enterprises 16597 }
tonUndStudiotechnik               OBJECT IDENTIFIER ::= { enterprises 16598 }
vassol                            OBJECT IDENTIFIER ::= { enterprises 16599 }
marketingResources                OBJECT IDENTIFIER ::= { enterprises 16600 }
intrex                            OBJECT IDENTIFIER ::= { enterprises 16601 }
itVisionAG                        OBJECT IDENTIFIER ::= { enterprises 16602 }
airmagnet                         OBJECT IDENTIFIER ::= { enterprises 16603 }
theOpenSSLGroup                   OBJECT IDENTIFIER ::= { enterprises 16604 }
radianceBBS                       OBJECT IDENTIFIER ::= { enterprises 16605 }
delfi                             OBJECT IDENTIFIER ::= { enterprises 16606 }
distraPty                         OBJECT IDENTIFIER ::= { enterprises 16607 }
sanyoMultimediaTottoriCo          OBJECT IDENTIFIER ::= { enterprises 16608 }
phalanyx                          OBJECT IDENTIFIER ::= { enterprises 16609 }
telemediaSoftwareCorp             OBJECT IDENTIFIER ::= { enterprises 16610 }
qnet                              OBJECT IDENTIFIER ::= { enterprises 16611 }
zenon                             OBJECT IDENTIFIER ::= { enterprises 16612 }
cross                             OBJECT IDENTIFIER ::= { enterprises 16613 }
genomeSequencingCenter            OBJECT IDENTIFIER ::= { enterprises 16614 }
entradaSoftware                   OBJECT IDENTIFIER ::= { enterprises 16615 }
disciplemakers                    OBJECT IDENTIFIER ::= { enterprises 16616 }
merlinAviationSystems             OBJECT IDENTIFIER ::= { enterprises 16617 }
saitc                             OBJECT IDENTIFIER ::= { enterprises 16618 }
bandspeed                         OBJECT IDENTIFIER ::= { enterprises 16619 }
bugaluxDenmarkAS                  OBJECT IDENTIFIER ::= { enterprises 16620 }
computerCare                      OBJECT IDENTIFIER ::= { enterprises 16621 }
intelligentagents                 OBJECT IDENTIFIER ::= { enterprises 16622 }
mobileBroadcastingCorporation     OBJECT IDENTIFIER ::= { enterprises 16623 }
planetactive                      OBJECT IDENTIFIER ::= { enterprises 16624 }
ocadoLimited                      OBJECT IDENTIFIER ::= { enterprises 16625 }
norkomTechnologies                OBJECT IDENTIFIER ::= { enterprises 16626 }
changIndustry                     OBJECT IDENTIFIER ::= { enterprises 16627 }
pdxcolonet                        OBJECT IDENTIFIER ::= { enterprises 16628 }
certeon                           OBJECT IDENTIFIER ::= { enterprises 16629 }
intellagent                       OBJECT IDENTIFIER ::= { enterprises 16630 }
bermudaHolding                    OBJECT IDENTIFIER ::= { enterprises 16631 }
setonHallUniversity               OBJECT IDENTIFIER ::= { enterprises 16632 }
danamisAssociates                 OBJECT IDENTIFIER ::= { enterprises 16633 }
voxageTeleinformatica             OBJECT IDENTIFIER ::= { enterprises 16634 }
sFRiENdS                          OBJECT IDENTIFIER ::= { enterprises 16635 }
ktroad                            OBJECT IDENTIFIER ::= { enterprises 16636 }
sanycomTechnologyCo               OBJECT IDENTIFIER ::= { enterprises 16637 }
avlList                           OBJECT IDENTIFIER ::= { enterprises 16638 }
softsolutions                     OBJECT IDENTIFIER ::= { enterprises 16639 }
xnet2000                          OBJECT IDENTIFIER ::= { enterprises 16640 }
internationalSolarEnergySociety   OBJECT IDENTIFIER ::= { enterprises 16641 }
theAmuletGroup                    OBJECT IDENTIFIER ::= { enterprises 16642 }
exago                             OBJECT IDENTIFIER ::= { enterprises 16643 }
xtensive                          OBJECT IDENTIFIER ::= { enterprises 16644 }
sanJoaquinValleyCollege           OBJECT IDENTIFIER ::= { enterprises 16645 }
rFSystems                         OBJECT IDENTIFIER ::= { enterprises 16646 }
regalCineMedia                    OBJECT IDENTIFIER ::= { enterprises 16647 }
centosPrime                       OBJECT IDENTIFIER ::= { enterprises 16648 }
softelSystemsPty                  OBJECT IDENTIFIER ::= { enterprises 16649 }
jscDalcombank                     OBJECT IDENTIFIER ::= { enterprises 16650 }
giftOfTheGiversFoundation         OBJECT IDENTIFIER ::= { enterprises 16651 }
thundergeek                       OBJECT IDENTIFIER ::= { enterprises 16652 }
eltron                            OBJECT IDENTIFIER ::= { enterprises 16653 }
electralink2                      OBJECT IDENTIFIER ::= { enterprises 16654 }
lunarGravityNetworks              OBJECT IDENTIFIER ::= { enterprises 16655 }
m3production                      OBJECT IDENTIFIER ::= { enterprises 16656 }
ingDirect                         OBJECT IDENTIFIER ::= { enterprises 16657 }
itaSoftware                       OBJECT IDENTIFIER ::= { enterprises 16658 }
computerScienceHouse              OBJECT IDENTIFIER ::= { enterprises 16659 }
dmxTechnologies                   OBJECT IDENTIFIER ::= { enterprises 16660 }
tacteam                           OBJECT IDENTIFIER ::= { enterprises 16661 }
cfsGlobalServices                 OBJECT IDENTIFIER ::= { enterprises 16662 }
westecHoldingCompany              OBJECT IDENTIFIER ::= { enterprises 16663 }
aciEurope                         OBJECT IDENTIFIER ::= { enterprises 16664 }
estonianBusinessSchoolGroup       OBJECT IDENTIFIER ::= { enterprises 16665 }
pecProducts                       OBJECT IDENTIFIER ::= { enterprises 16666 }
freaxSistemas                     OBJECT IDENTIFIER ::= { enterprises 16667 }
pciTechnologies                   OBJECT IDENTIFIER ::= { enterprises 16668 }
freelandHaynesLimited             OBJECT IDENTIFIER ::= { enterprises 16669 }
actionTechnologies                OBJECT IDENTIFIER ::= { enterprises 16670 }
americanPhysicalSociety           OBJECT IDENTIFIER ::= { enterprises 16671 }
airflowNetworks                   OBJECT IDENTIFIER ::= { enterprises 16672 }
chrisMitchell                     OBJECT IDENTIFIER ::= { enterprises 16673 }
voyageData                        OBJECT IDENTIFIER ::= { enterprises 16674 }
chaceCommunitySchool              OBJECT IDENTIFIER ::= { enterprises 16675 }
servibancaGrupoBCP                OBJECT IDENTIFIER ::= { enterprises 16676 }
centreOfMedicalTechnology         OBJECT IDENTIFIER ::= { enterprises 16677 }
inxServices                       OBJECT IDENTIFIER ::= { enterprises 16678 }
staTrackEnterpriseLimited         OBJECT IDENTIFIER ::= { enterprises 16679 }
axiaSuperNet                      OBJECT IDENTIFIER ::= { enterprises 16680 }
validSolutions                    OBJECT IDENTIFIER ::= { enterprises 16681 }
xtrac                             OBJECT IDENTIFIER ::= { enterprises 16682 }
iit                               OBJECT IDENTIFIER ::= { enterprises 16683 }
europeanHumanitiesUniversity      OBJECT IDENTIFIER ::= { enterprises 16684 }
optinelSystems                    OBJECT IDENTIFIER ::= { enterprises 16685 }
protegoNetworks                   OBJECT IDENTIFIER ::= { enterprises 16686 }
cyantel                           OBJECT IDENTIFIER ::= { enterprises 16687 }
infrasecSwedenAB                  OBJECT IDENTIFIER ::= { enterprises 16688 }
retalix                           OBJECT IDENTIFIER ::= { enterprises 16689 }
smallElectricMotors               OBJECT IDENTIFIER ::= { enterprises 16690 }
tekronCommunicationSystems        OBJECT IDENTIFIER ::= { enterprises 16691 }
optimalTechnologies               OBJECT IDENTIFIER ::= { enterprises 16692 }
longreachTelecommunicationsPty    OBJECT IDENTIFIER ::= { enterprises 16693 }
purpleSun                         OBJECT IDENTIFIER ::= { enterprises 16694 }
cygnusMICROSYSTEMSPRIVATELIMITED  OBJECT IDENTIFIER ::= { enterprises 16695 }
decisiv                           OBJECT IDENTIFIER ::= { enterprises 16696 }
theFreeSoftwareInitiativeOfJapan  OBJECT IDENTIFIER ::= { enterprises 16697 }
scsEntripriseSystems              OBJECT IDENTIFIER ::= { enterprises 16698 }
gyl                               OBJECT IDENTIFIER ::= { enterprises 16699 }
southwestAirlinesCo               OBJECT IDENTIFIER ::= { enterprises 16700 }
carlsonHospitalityWorldwide       OBJECT IDENTIFIER ::= { enterprises 16701 }
navalResearchLaboratory           OBJECT IDENTIFIER ::= { enterprises 16702 }
universityOfWestminster           OBJECT IDENTIFIER ::= { enterprises 16703 }
yaga                              OBJECT IDENTIFIER ::= { enterprises 16704 }
loyolaMarymountUniversity         OBJECT IDENTIFIER ::= { enterprises 16705 }
navinmailServices                 OBJECT IDENTIFIER ::= { enterprises 16706 }
exelixisDeutschland               OBJECT IDENTIFIER ::= { enterprises 16707 }
wuhanWearnesTechnologyCO          OBJECT IDENTIFIER ::= { enterprises 16708 }
bankOne                           OBJECT IDENTIFIER ::= { enterprises 16709 }
screamingGeniusMetaLabs           OBJECT IDENTIFIER ::= { enterprises 16710 }
basis0net                         OBJECT IDENTIFIER ::= { enterprises 16711 }
ilb                               OBJECT IDENTIFIER ::= { enterprises 16712 }
fhRosenheim                       OBJECT IDENTIFIER ::= { enterprises 16713 }
gossamerGroup                     OBJECT IDENTIFIER ::= { enterprises 16714 }
trlabsRegina                      OBJECT IDENTIFIER ::= { enterprises 16715 }
unisynSoftware                    OBJECT IDENTIFIER ::= { enterprises 16716 }
universityOfVictoria              OBJECT IDENTIFIER ::= { enterprises 16717 }
gmvSA                             OBJECT IDENTIFIER ::= { enterprises 16718 }
sasIRISTechnologies               OBJECT IDENTIFIER ::= { enterprises 16719 }
ossService                        OBJECT IDENTIFIER ::= { enterprises 16720 }
chronosTechnology                 OBJECT IDENTIFIER ::= { enterprises 16721 }
methicsOy                         OBJECT IDENTIFIER ::= { enterprises 16722 }
lawbaseTechnologies               OBJECT IDENTIFIER ::= { enterprises 16723 }
fitzgeraldAssociates              OBJECT IDENTIFIER ::= { enterprises 16724 }
itech2                            OBJECT IDENTIFIER ::= { enterprises 16725 }
dowslakeMicrosystemsCorporation   OBJECT IDENTIFIER ::= { enterprises 16726 }
thalesAVIONICS                    OBJECT IDENTIFIER ::= { enterprises 16727 }
wolcottSystemsGroup               OBJECT IDENTIFIER ::= { enterprises 16728 }
midlingAndAssociates              OBJECT IDENTIFIER ::= { enterprises 16729 }
higherGroundNetworksLLC           OBJECT IDENTIFIER ::= { enterprises 16730 }
industrialMedium                  OBJECT IDENTIFIER ::= { enterprises 16731 }
guardent                          OBJECT IDENTIFIER ::= { enterprises 16732 }
activelife                        OBJECT IDENTIFIER ::= { enterprises 16733 }
orbitalDataCorporation            OBJECT IDENTIFIER ::= { enterprises 16734 }
technocomCorporation              OBJECT IDENTIFIER ::= { enterprises 16735 }
javali                            OBJECT IDENTIFIER ::= { enterprises 16736 }
neotoolDevelopment                OBJECT IDENTIFIER ::= { enterprises 16737 }
intervideo                        OBJECT IDENTIFIER ::= { enterprises 16738 }
companyname                       OBJECT IDENTIFIER ::= { enterprises 16739 }
threeCLimited                     OBJECT IDENTIFIER ::= { enterprises 16740 }
alexanderM                        OBJECT IDENTIFIER ::= { enterprises 16741 }
topteamServices                   OBJECT IDENTIFIER ::= { enterprises 16742 }
hessischeZentraleFuerDatenverarbeitung OBJECT IDENTIFIER ::= { enterprises 16743 }
blankom                           OBJECT IDENTIFIER ::= { enterprises 16744 }
alfaBankOJSC                      OBJECT IDENTIFIER ::= { enterprises 16745 }
norbu09org                        OBJECT IDENTIFIER ::= { enterprises 16746 }
intercommitBv                     OBJECT IDENTIFIER ::= { enterprises 16747 }
studentskaUnieCVUT                OBJECT IDENTIFIER ::= { enterprises 16748 }
extensibleSystems                 OBJECT IDENTIFIER ::= { enterprises 16749 }
geeBroadcastSystems               OBJECT IDENTIFIER ::= { enterprises 16750 }
insa                              OBJECT IDENTIFIER ::= { enterprises 16751 }
gConsulting                       OBJECT IDENTIFIER ::= { enterprises 16752 }
dbnetPty                          OBJECT IDENTIFIER ::= { enterprises 16753 }
merlin                            OBJECT IDENTIFIER ::= { enterprises 16754 }
danusys                           OBJECT IDENTIFIER ::= { enterprises 16755 }
juasunnet                         OBJECT IDENTIFIER ::= { enterprises 16756 }
itSOFTWARE                        OBJECT IDENTIFIER ::= { enterprises 16757 }
lakeridgeHealthCorporation        OBJECT IDENTIFIER ::= { enterprises 16758 }
centralMissouriStateUniversity    OBJECT IDENTIFIER ::= { enterprises 16759 }
internetDirect                    OBJECT IDENTIFIER ::= { enterprises 16760 }
newMexicoTech                     OBJECT IDENTIFIER ::= { enterprises 16761 }
olsonTechnology                   OBJECT IDENTIFIER ::= { enterprises 16762 }
ezWebTech                         OBJECT IDENTIFIER ::= { enterprises 16763 }
iddWorks                          OBJECT IDENTIFIER ::= { enterprises 16764 }
schmitzIT                         OBJECT IDENTIFIER ::= { enterprises 16765 }
svSystems                         OBJECT IDENTIFIER ::= { enterprises 16766 }
wonderlineRt                      OBJECT IDENTIFIER ::= { enterprises 16767 }
marineInterface                   OBJECT IDENTIFIER ::= { enterprises 16768 }
svSystems2                        OBJECT IDENTIFIER ::= { enterprises 16769 }
daveDodge                         OBJECT IDENTIFIER ::= { enterprises 16770 }
seasSolutions                     OBJECT IDENTIFIER ::= { enterprises 16771 }
universityOfCalifornia3           OBJECT IDENTIFIER ::= { enterprises 16772 }
sourwoodResearch                  OBJECT IDENTIFIER ::= { enterprises 16773 }
uSrl                              OBJECT IDENTIFIER ::= { enterprises 16774 }
gipMDS                            OBJECT IDENTIFIER ::= { enterprises 16775 }
mmitOfECNU                        OBJECT IDENTIFIER ::= { enterprises 16776 }
oxance                            OBJECT IDENTIFIER ::= { enterprises 16777 }
uniteamInit                       OBJECT IDENTIFIER ::= { enterprises 16778 }
moreSecureBV                      OBJECT IDENTIFIER ::= { enterprises 16779 }
pathwayComputing                  OBJECT IDENTIFIER ::= { enterprises 16780 }
waspSystems                       OBJECT IDENTIFIER ::= { enterprises 16781 }
clickcadence                      OBJECT IDENTIFIER ::= { enterprises 16782 }
abacusTechnicalTrainingCompany    OBJECT IDENTIFIER ::= { enterprises 16783 }
olsonTechnology2                  OBJECT IDENTIFIER ::= { enterprises 16784 }
medizinischeUniversit             OBJECT IDENTIFIER ::= { enterprises 16785 }
eosysSrl                          OBJECT IDENTIFIER ::= { enterprises 16786 }
tSystemsNovaInternational         OBJECT IDENTIFIER ::= { enterprises 16787 }
informationTechnologyCenter       OBJECT IDENTIFIER ::= { enterprises 16788 }
berkleeCollegeOfMusic             OBJECT IDENTIFIER ::= { enterprises 16789 }
myrioCorporation                  OBJECT IDENTIFIER ::= { enterprises 16790 }
brascon                           OBJECT IDENTIFIER ::= { enterprises 16791 }
zapataEngineering                 OBJECT IDENTIFIER ::= { enterprises 16792 }
universityOfNewEngland            OBJECT IDENTIFIER ::= { enterprises 16793 }
savantTechnologiesPrivate         OBJECT IDENTIFIER ::= { enterprises 16794 }
mroTEKLTD                         OBJECT IDENTIFIER ::= { enterprises 16795 }
instituteOfHighEnergyPhysics      OBJECT IDENTIFIER ::= { enterprises 16796 }
infothuisNieuweMediaBV            OBJECT IDENTIFIER ::= { enterprises 16797 }
digitalTechnical                  OBJECT IDENTIFIER ::= { enterprises 16798 }
xlGlobalServices                  OBJECT IDENTIFIER ::= { enterprises 16799 }
idylic                            OBJECT IDENTIFIER ::= { enterprises 16800 }
openPricer                        OBJECT IDENTIFIER ::= { enterprises 16801 }
i2q                               OBJECT IDENTIFIER ::= { enterprises 16802 }
tetraPakInformationManagementAB   OBJECT IDENTIFIER ::= { enterprises 16803 }
netcadabra                        OBJECT IDENTIFIER ::= { enterprises 16804 }
validusMedicalSystems             OBJECT IDENTIFIER ::= { enterprises 16805 }
dotNewMedia                       OBJECT IDENTIFIER ::= { enterprises 16806 }
millenniumDigitalMedia            OBJECT IDENTIFIER ::= { enterprises 16807 }
hambrechtorg                      OBJECT IDENTIFIER ::= { enterprises 16808 }
paylessShoesource                 OBJECT IDENTIFIER ::= { enterprises 16809 }
alongSoftwareDeveloperWorkShop    OBJECT IDENTIFIER ::= { enterprises 16810 }
bluetie                           OBJECT IDENTIFIER ::= { enterprises 16811 }
unixiron                          OBJECT IDENTIFIER ::= { enterprises 16812 }
micronetCommunications            OBJECT IDENTIFIER ::= { enterprises 16813 }
quinsyBV                          OBJECT IDENTIFIER ::= { enterprises 16814 }
glidepathBV                       OBJECT IDENTIFIER ::= { enterprises 16815 }
computerPlus                      OBJECT IDENTIFIER ::= { enterprises 16816 }
deLaRueInternational              OBJECT IDENTIFIER ::= { enterprises 16817 }
unitedMediaCompany                OBJECT IDENTIFIER ::= { enterprises 16818 }
priocomCorp                       OBJECT IDENTIFIER ::= { enterprises 16819 }
soc                               OBJECT IDENTIFIER ::= { enterprises 16820 }
instituteForAdvancedStudy         OBJECT IDENTIFIER ::= { enterprises 16821 }
scottLHYuan                       OBJECT IDENTIFIER ::= { enterprises 16822 }
abelingITDesign                   OBJECT IDENTIFIER ::= { enterprises 16823 }
otagaki                           OBJECT IDENTIFIER ::= { enterprises 16824 }
networkTechnology                 OBJECT IDENTIFIER ::= { enterprises 16825 }
innomediaTechnologiesPrivateLimited OBJECT IDENTIFIER ::= { enterprises 16826 }
secureSystems                     OBJECT IDENTIFIER ::= { enterprises 16827 }
intelsoft                         OBJECT IDENTIFIER ::= { enterprises 16828 }
duckcorp                          OBJECT IDENTIFIER ::= { enterprises 16829 }
fidelityInformationServices       OBJECT IDENTIFIER ::= { enterprises 16830 }
benhallca                         OBJECT IDENTIFIER ::= { enterprises 16831 }
auchan                            OBJECT IDENTIFIER ::= { enterprises 16832 }
logicworks                        OBJECT IDENTIFIER ::= { enterprises 16833 }
hospitalBillingCollectionService  OBJECT IDENTIFIER ::= { enterprises 16834 }
dahleConsulting                   OBJECT IDENTIFIER ::= { enterprises 16835 }
m2studio                          OBJECT IDENTIFIER ::= { enterprises 16836 }
washingtonCounty                  OBJECT IDENTIFIER ::= { enterprises 16837 }
omronCorporation                  OBJECT IDENTIFIER ::= { enterprises 16838 }
rodionSoftware                    OBJECT IDENTIFIER ::= { enterprises 16839 }
shanghaiERomCommunicationTechnologyCo OBJECT IDENTIFIER ::= { enterprises 16840 }
ifeelnet                          OBJECT IDENTIFIER ::= { enterprises 16841 }
inPhaseConsulting                 OBJECT IDENTIFIER ::= { enterprises 16842 }
barcovision                       OBJECT IDENTIFIER ::= { enterprises 16843 }
creacare                          OBJECT IDENTIFIER ::= { enterprises 16844 }
electricit                        OBJECT IDENTIFIER ::= { enterprises 16845 }
mpecWroclawSA                     OBJECT IDENTIFIER ::= { enterprises 16846 }
sakuraNetworkJapan                OBJECT IDENTIFIER ::= { enterprises 16847 }
independentConsultingSolutions    OBJECT IDENTIFIER ::= { enterprises 16848 }
beyonddatanetITS                  OBJECT IDENTIFIER ::= { enterprises 16849 }
threeColoniesSoftware             OBJECT IDENTIFIER ::= { enterprises 16850 }
rheingoldInstitutFRQualitativeMarktUndMedienanalysenGesellschaft OBJECT IDENTIFIER ::= { enterprises 16851 }
telinfos                          OBJECT IDENTIFIER ::= { enterprises 16852 }
barracudaDigitaleAgentur          OBJECT IDENTIFIER ::= { enterprises 16853 }
stiHealthcare                     OBJECT IDENTIFIER ::= { enterprises 16854 }
metromorphSoftworksRuhriListGbR   OBJECT IDENTIFIER ::= { enterprises 16855 }
bradfordSoftware                  OBJECT IDENTIFIER ::= { enterprises 16856 }
threeBean                         OBJECT IDENTIFIER ::= { enterprises 16857 }
tallMapleSystems                  OBJECT IDENTIFIER ::= { enterprises 16858 }
multimediaGames                   OBJECT IDENTIFIER ::= { enterprises 16859 }
thomasEndo                        OBJECT IDENTIFIER ::= { enterprises 16860 }
wefinetITConsulting               OBJECT IDENTIFIER ::= { enterprises 16861 }
iconz                             OBJECT IDENTIFIER ::= { enterprises 16862 }
jsrcom                            OBJECT IDENTIFIER ::= { enterprises 16863 }
zimTechnologiesInternational      OBJECT IDENTIFIER ::= { enterprises 16865 }
softwareNorth                     OBJECT IDENTIFIER ::= { enterprises 16866 }
datasynapse                       OBJECT IDENTIFIER ::= { enterprises 16867 }
conseilInternetAndLogicielsLibres OBJECT IDENTIFIER ::= { enterprises 16868 }
rommon                            OBJECT IDENTIFIER ::= { enterprises 16869 }
bancoDoEstadoDoRioGrandeDoSul     OBJECT IDENTIFIER ::= { enterprises 16870 }
tchiboFrischR                     OBJECT IDENTIFIER ::= { enterprises 16871 }
collaborativeCommerceEngines      OBJECT IDENTIFIER ::= { enterprises 16872 }
futureGateGroup                   OBJECT IDENTIFIER ::= { enterprises 16873 }
hitrust                           OBJECT IDENTIFIER ::= { enterprises 16874 }
computerPlus2                     OBJECT IDENTIFIER ::= { enterprises 16875 }
kungfooCoders                     OBJECT IDENTIFIER ::= { enterprises 16876 }
allMediaBankingBV                 OBJECT IDENTIFIER ::= { enterprises 16877 }
oldhamMetropolitanBoroughCouncil  OBJECT IDENTIFIER ::= { enterprises 16878 }
scaTransforestAB                  OBJECT IDENTIFIER ::= { enterprises 16879 }
zehomecom                         OBJECT IDENTIFIER ::= { enterprises 16880 }
emni                              OBJECT IDENTIFIER ::= { enterprises 16881 }
openeaiSoftwareFoundation         OBJECT IDENTIFIER ::= { enterprises 16882 }
gkbTechnologyCo                   OBJECT IDENTIFIER ::= { enterprises 16883 }
nortelNetworks                    OBJECT IDENTIFIER ::= { enterprises 16885 }
revelstoneTechnology              OBJECT IDENTIFIER ::= { enterprises 16886 }
iplocks                           OBJECT IDENTIFIER ::= { enterprises 16887 }
neutelligentcom                   OBJECT IDENTIFIER ::= { enterprises 16888 }
myitbiz                           OBJECT IDENTIFIER ::= { enterprises 16889 }
technisys                         OBJECT IDENTIFIER ::= { enterprises 16890 }
meta                              OBJECT IDENTIFIER ::= { enterprises 16891 }
signalisationVerMac               OBJECT IDENTIFIER ::= { enterprises 16892 }
enterpriseRentACar                OBJECT IDENTIFIER ::= { enterprises 16893 }
cotelligent                       OBJECT IDENTIFIER ::= { enterprises 16894 }
jpEvans                           OBJECT IDENTIFIER ::= { enterprises 16895 }
sungardFrontOfficeSolutions       OBJECT IDENTIFIER ::= { enterprises 16896 }
sdataCSplittgerberDatentechnik    OBJECT IDENTIFIER ::= { enterprises 16897 }
ventureIndustryInternationalCorp  OBJECT IDENTIFIER ::= { enterprises 16898 }
corvigo                           OBJECT IDENTIFIER ::= { enterprises 16899 }
aMetarealMaterial                 OBJECT IDENTIFIER ::= { enterprises 16900 }
wibhuTechnologiesPvt              OBJECT IDENTIFIER ::= { enterprises 16901 }
appletzCO                         OBJECT IDENTIFIER ::= { enterprises 16902 }
telecatsBV                        OBJECT IDENTIFIER ::= { enterprises 16903 }
aylesfordNewsprintLimited         OBJECT IDENTIFIER ::= { enterprises 16904 }
gingerAlliance                    OBJECT IDENTIFIER ::= { enterprises 16905 }
enertronLLC                       OBJECT IDENTIFIER ::= { enterprises 16906 }
trumanStateUniversity             OBJECT IDENTIFIER ::= { enterprises 16907 }
binaryApe                         OBJECT IDENTIFIER ::= { enterprises 16908 }
newbergPublicSchools              OBJECT IDENTIFIER ::= { enterprises 16909 }
chinaunionpay                     OBJECT IDENTIFIER ::= { enterprises 16910 }
generalWirelessScandinaviaAB      OBJECT IDENTIFIER ::= { enterprises 16911 }
bundesanstaltStatistikOesterreich OBJECT IDENTIFIER ::= { enterprises 16912 }
openNetworkSolutions2             OBJECT IDENTIFIER ::= { enterprises 16913 }
nuitca                            OBJECT IDENTIFIER ::= { enterprises 16914 }
theHalLewisGroup                  OBJECT IDENTIFIER ::= { enterprises 16915 }
maPlanete                         OBJECT IDENTIFIER ::= { enterprises 16916 }
seecago                           OBJECT IDENTIFIER ::= { enterprises 16917 }
aeiieARISE                        OBJECT IDENTIFIER ::= { enterprises 16918 }
augsburgerComputerForumEV         OBJECT IDENTIFIER ::= { enterprises 16919 }
arteGEIE                          OBJECT IDENTIFIER ::= { enterprises 16920 }
hwacomSYSTEMSINC                  OBJECT IDENTIFIER ::= { enterprises 16921 }
villeD                            OBJECT IDENTIFIER ::= { enterprises 16922 }
rtvSlovenija                      OBJECT IDENTIFIER ::= { enterprises 16923 }
britishSkyBroadcasting            OBJECT IDENTIFIER ::= { enterprises 16924 }
igaPEGASE                         OBJECT IDENTIFIER ::= { enterprises 16925 }
systemberatungAxelDunkel          OBJECT IDENTIFIER ::= { enterprises 16926 }
mlbAssociates                     OBJECT IDENTIFIER ::= { enterprises 16927 }
markSouthWest                     OBJECT IDENTIFIER ::= { enterprises 16928 }
universityOfCalifornia4           OBJECT IDENTIFIER ::= { enterprises 16929 }
camSecurityAndConnectionsBV       OBJECT IDENTIFIER ::= { enterprises 16930 }
sandwellTechnologies              OBJECT IDENTIFIER ::= { enterprises 16931 }
dicomGroup                        OBJECT IDENTIFIER ::= { enterprises 16932 }
alcComputertechnik                OBJECT IDENTIFIER ::= { enterprises 16933 }
marianBracinik                    OBJECT IDENTIFIER ::= { enterprises 16934 }
espooVantaaInstituteOfTechnology  OBJECT IDENTIFIER ::= { enterprises 16935 }
databayAG                         OBJECT IDENTIFIER ::= { enterprises 16936 }
eWriedt                           OBJECT IDENTIFIER ::= { enterprises 16937 }
sensationalAG                     OBJECT IDENTIFIER ::= { enterprises 16938 }
addixInternetServices             OBJECT IDENTIFIER ::= { enterprises 16939 }
cryptogramSA                      OBJECT IDENTIFIER ::= { enterprises 16940 }
oakley                            OBJECT IDENTIFIER ::= { enterprises 16941 }
trx                               OBJECT IDENTIFIER ::= { enterprises 16942 }
ceterusNetworks                   OBJECT IDENTIFIER ::= { enterprises 16943 }
sevenBlades                       OBJECT IDENTIFIER ::= { enterprises 16944 }
grupoDeUsuariosDeLinuxDeCanarias  OBJECT IDENTIFIER ::= { enterprises 16945 }
litchfieldCommunications          OBJECT IDENTIFIER ::= { enterprises 16946 }
programLine                       OBJECT IDENTIFIER ::= { enterprises 16947 }
rhoditech                         OBJECT IDENTIFIER ::= { enterprises 16948 }
mobifonSA                         OBJECT IDENTIFIER ::= { enterprises 16949 }
aomActiveOnlineMarketing          OBJECT IDENTIFIER ::= { enterprises 16950 }
cogemaLAHAGUE                     OBJECT IDENTIFIER ::= { enterprises 16951 }
eisodusNetworksPvt                OBJECT IDENTIFIER ::= { enterprises 16952 }
teccoSoftwareEntwicklungAG        OBJECT IDENTIFIER ::= { enterprises 16953 }
softwarePoetry                    OBJECT IDENTIFIER ::= { enterprises 16954 }
modulusSystems                    OBJECT IDENTIFIER ::= { enterprises 16955 }
inboxcop                          OBJECT IDENTIFIER ::= { enterprises 16956 }
fionetInternetServices            OBJECT IDENTIFIER ::= { enterprises 16957 }
institutoTecnol                   OBJECT IDENTIFIER ::= { enterprises 16958 }
cipherSecurityServices            OBJECT IDENTIFIER ::= { enterprises 16959 }
darronNesbitt                     OBJECT IDENTIFIER ::= { enterprises 16960 }
vaisala                           OBJECT IDENTIFIER ::= { enterprises 16961 }
sevenLevelsConsultantsAB          OBJECT IDENTIFIER ::= { enterprises 16962 }
intuwave                          OBJECT IDENTIFIER ::= { enterprises 16963 }
nonap                             OBJECT IDENTIFIER ::= { enterprises 16964 }
aunaTLC                           OBJECT IDENTIFIER ::= { enterprises 16965 }
kiffAnalytical                    OBJECT IDENTIFIER ::= { enterprises 16966 }
universityTexasMedicalBranchGalveston OBJECT IDENTIFIER ::= { enterprises 16967 }
magnifire                         OBJECT IDENTIFIER ::= { enterprises 16968 }
eyebitsStudios                    OBJECT IDENTIFIER ::= { enterprises 16969 }
coublis                           OBJECT IDENTIFIER ::= { enterprises 16970 }
lemcheNet                         OBJECT IDENTIFIER ::= { enterprises 16971 }
dslTerminalRemoteManagementAlliance OBJECT IDENTIFIER ::= { enterprises 16972 }
citsGroup                         OBJECT IDENTIFIER ::= { enterprises 16973 }
worldmingo                        OBJECT IDENTIFIER ::= { enterprises 16974 }
horstThieleMaschinenbauHydraulischeGeraete OBJECT IDENTIFIER ::= { enterprises 16975 }
sideResourcesAndDevelopment       OBJECT IDENTIFIER ::= { enterprises 16976 }
zwi1zekBankowPolskich             OBJECT IDENTIFIER ::= { enterprises 16977 }
medicalInsightAS                  OBJECT IDENTIFIER ::= { enterprises 16978 }
m2IngenierieEtConseilSARL         OBJECT IDENTIFIER ::= { enterprises 16979 }
jacobAndSundstrom                 OBJECT IDENTIFIER ::= { enterprises 16980 }
itg                               OBJECT IDENTIFIER ::= { enterprises 16981 }
masarykUniversityBrno             OBJECT IDENTIFIER ::= { enterprises 16982 }
cineca                            OBJECT IDENTIFIER ::= { enterprises 16983 }
exacoreConsolidatedSystems        OBJECT IDENTIFIER ::= { enterprises 16984 }
globalTechnologyCo                OBJECT IDENTIFIER ::= { enterprises 16985 }
factorSPE                         OBJECT IDENTIFIER ::= { enterprises 16986 }
eskerSA                           OBJECT IDENTIFIER ::= { enterprises 16987 }
theManufacturersLifeInsuranceCompany OBJECT IDENTIFIER ::= { enterprises 16988 }
kisp                              OBJECT IDENTIFIER ::= { enterprises 16989 }
print                             OBJECT IDENTIFIER ::= { enterprises 16990 }
starsoft                          OBJECT IDENTIFIER ::= { enterprises 16991 }
theHalifaxHeraldLimited           OBJECT IDENTIFIER ::= { enterprises 16992 }
norsec                            OBJECT IDENTIFIER ::= { enterprises 16993 }
keyCircle                         OBJECT IDENTIFIER ::= { enterprises 16994 }
elegoSoftwareSolutions            OBJECT IDENTIFIER ::= { enterprises 16995 }
aboriginalSportsAndRecreationAssociationOfBC OBJECT IDENTIFIER ::= { enterprises 16996 }
innovativeConsultants             OBJECT IDENTIFIER ::= { enterprises 16997 }
intoto                            OBJECT IDENTIFIER ::= { enterprises 16998 }
cortinovisSA                      OBJECT IDENTIFIER ::= { enterprises 16999 }
centreDeTelecomunicacionsITIDeLaGeneralitatDeCatalunya OBJECT IDENTIFIER ::= { enterprises 17000 }
actTechnologyCo                   OBJECT IDENTIFIER ::= { enterprises 17001 }
copseyCommunicationsProjects      OBJECT IDENTIFIER ::= { enterprises 17002 }
universityOfDundee                OBJECT IDENTIFIER ::= { enterprises 17003 }
israelInterUniversityComputationCenter OBJECT IDENTIFIER ::= { enterprises 17004 }
mangroveSystems                   OBJECT IDENTIFIER ::= { enterprises 17005 }
spherion                          OBJECT IDENTIFIER ::= { enterprises 17006 }
coolIT                            OBJECT IDENTIFIER ::= { enterprises 17007 }
cleverAgeSARL                     OBJECT IDENTIFIER ::= { enterprises 17008 }
imove                             OBJECT IDENTIFIER ::= { enterprises 17009 }
hopecomOpticCommunication         OBJECT IDENTIFIER ::= { enterprises 17010 }
metadataSystems                   OBJECT IDENTIFIER ::= { enterprises 17011 }
ecaremeTechnologies               OBJECT IDENTIFIER ::= { enterprises 17012 }
guarantyTechnologyCorp            OBJECT IDENTIFIER ::= { enterprises 17013 }
izumiCyberNetworks                OBJECT IDENTIFIER ::= { enterprises 17014 }
manageit                          OBJECT IDENTIFIER ::= { enterprises 17015 }
infoJureKnowledge                 OBJECT IDENTIFIER ::= { enterprises 17016 }
cybertechDeColombia               OBJECT IDENTIFIER ::= { enterprises 17017 }
silikonecom                       OBJECT IDENTIFIER ::= { enterprises 17018 }
heinrichBerndesHaushaltstechnik   OBJECT IDENTIFIER ::= { enterprises 17019 }
irsn                              OBJECT IDENTIFIER ::= { enterprises 17020 }
universityOfCentralFlorida        OBJECT IDENTIFIER ::= { enterprises 17021 }
avistaLabs                        OBJECT IDENTIFIER ::= { enterprises 17022 }
apptera                           OBJECT IDENTIFIER ::= { enterprises 17023 }
jacksonLocalSchoolDistrict        OBJECT IDENTIFIER ::= { enterprises 17024 }
retherNetworks                    OBJECT IDENTIFIER ::= { enterprises 17025 }
dotnsf                            OBJECT IDENTIFIER ::= { enterprises 17026 }
yaao                              OBJECT IDENTIFIER ::= { enterprises 17027 }
marketxscomBV                     OBJECT IDENTIFIER ::= { enterprises 17028 }
mode                              OBJECT IDENTIFIER ::= { enterprises 17029 }
velveo                            OBJECT IDENTIFIER ::= { enterprises 17030 }
clusterLabs                       OBJECT IDENTIFIER ::= { enterprises 17031 }
cityOfHelsinki                    OBJECT IDENTIFIER ::= { enterprises 17032 }
medicalUniversityOfSouthCarolina  OBJECT IDENTIFIER ::= { enterprises 17033 }
nhnCorp                           OBJECT IDENTIFIER ::= { enterprises 17034 }
cerberian                         OBJECT IDENTIFIER ::= { enterprises 17035 }
alisysSoftwareSL                  OBJECT IDENTIFIER ::= { enterprises 17036 }
brannstromsElektronikAB           OBJECT IDENTIFIER ::= { enterprises 17037 }
federalStateUnitaryEnterprise     OBJECT IDENTIFIER ::= { enterprises 17038 }
vontu                             OBJECT IDENTIFIER ::= { enterprises 17039 }
integritsCorporation              OBJECT IDENTIFIER ::= { enterprises 17040 }
teledomani                        OBJECT IDENTIFIER ::= { enterprises 17041 }
consultoresGlobalesOnlineSL       OBJECT IDENTIFIER ::= { enterprises 17042 }
pcRepairAalestrup                 OBJECT IDENTIFIER ::= { enterprises 17043 }
redFig                            OBJECT IDENTIFIER ::= { enterprises 17044 }
networkTechnologiesGroup          OBJECT IDENTIFIER ::= { enterprises 17045 }
errornet                          OBJECT IDENTIFIER ::= { enterprises 17046 }
eurofreshinc                      OBJECT IDENTIFIER ::= { enterprises 17047 }
ashland                           OBJECT IDENTIFIER ::= { enterprises 17048 }
eurospiderInformationTechnologyAG OBJECT IDENTIFIER ::= { enterprises 17049 }
mediasonic                        OBJECT IDENTIFIER ::= { enterprises 17050 }
lastMinuteNetworkLimited          OBJECT IDENTIFIER ::= { enterprises 17051 }
aPlusMarketing                    OBJECT IDENTIFIER ::= { enterprises 17052 }
wwwslavelru                       OBJECT IDENTIFIER ::= { enterprises 17053 }
severoceskaPlynarenska            OBJECT IDENTIFIER ::= { enterprises 17054 }
moshjahan                         OBJECT IDENTIFIER ::= { enterprises 17055 }
fusionNetworkServicesCorp         OBJECT IDENTIFIER ::= { enterprises 17056 }
victorSierra                      OBJECT IDENTIFIER ::= { enterprises 17057 }
nationalRadioAstronomyObservatory OBJECT IDENTIFIER ::= { enterprises 17058 }
cookingwise                       OBJECT IDENTIFIER ::= { enterprises 17059 }
zeteinnet                         OBJECT IDENTIFIER ::= { enterprises 17060 }
shanghai4UNetworkTechCo           OBJECT IDENTIFIER ::= { enterprises 17061 }
arielservices                     OBJECT IDENTIFIER ::= { enterprises 17062 }
lightshipTelecom                  OBJECT IDENTIFIER ::= { enterprises 17063 }
csxTechnologies                   OBJECT IDENTIFIER ::= { enterprises 17064 }
zionsBancorporation               OBJECT IDENTIFIER ::= { enterprises 17065 }
collaboratech                     OBJECT IDENTIFIER ::= { enterprises 17066 }
padimaxLimited                    OBJECT IDENTIFIER ::= { enterprises 17067 }
jcastNetworksCorp                 OBJECT IDENTIFIER ::= { enterprises 17068 }
leucotronEquipamentos             OBJECT IDENTIFIER ::= { enterprises 17069 }
hiDeHo                            OBJECT IDENTIFIER ::= { enterprises 17070 }
primeElectronicsAndSatellitics    OBJECT IDENTIFIER ::= { enterprises 17071 }
transgate                         OBJECT IDENTIFIER ::= { enterprises 17072 }
universitaetsklinikumFreiburg     OBJECT IDENTIFIER ::= { enterprises 17073 }
senatsverwaltungFuerGesundheit    OBJECT IDENTIFIER ::= { enterprises 17074 }
edwinLCoxSchoolOfBusiness         OBJECT IDENTIFIER ::= { enterprises 17075 }
excellenceHighTechGeorgiaLTD      OBJECT IDENTIFIER ::= { enterprises 17076 }
giritProjects                     OBJECT IDENTIFIER ::= { enterprises 17077 }
innovationSoftwareGroup           OBJECT IDENTIFIER ::= { enterprises 17078 }
appiq                             OBJECT IDENTIFIER ::= { enterprises 17079 }
betrained                         OBJECT IDENTIFIER ::= { enterprises 17080 }
mfVanLoon                         OBJECT IDENTIFIER ::= { enterprises 17081 }
oregonUniversitySystem            OBJECT IDENTIFIER ::= { enterprises 17082 }
compartMEDICALSYSTEMS             OBJECT IDENTIFIER ::= { enterprises 17083 }
honHAIPRECISIONINDCO              OBJECT IDENTIFIER ::= { enterprises 17084 }
beijingBUTelecomTechCo            OBJECT IDENTIFIER ::= { enterprises 17085 }
bikAschpurwisBehrens              OBJECT IDENTIFIER ::= { enterprises 17086 }
grecoInternationalAG              OBJECT IDENTIFIER ::= { enterprises 17087 }
sichuanWisesoft                   OBJECT IDENTIFIER ::= { enterprises 17088 }
universit9                        OBJECT IDENTIFIER ::= { enterprises 17089 }
packetizer                        OBJECT IDENTIFIER ::= { enterprises 17090 }
leogic                            OBJECT IDENTIFIER ::= { enterprises 17091 }
mediaringLimited                  OBJECT IDENTIFIER ::= { enterprises 17092 }
ellemediaTechnologies             OBJECT IDENTIFIER ::= { enterprises 17093 }
bluesliceNetworks                 OBJECT IDENTIFIER ::= { enterprises 17094 }
microchipTechnology               OBJECT IDENTIFIER ::= { enterprises 17095 }
invescoInstitutional              OBJECT IDENTIFIER ::= { enterprises 17096 }
weltekTechnologiesCo              OBJECT IDENTIFIER ::= { enterprises 17097 }
innomenta                         OBJECT IDENTIFIER ::= { enterprises 17098 }
tellustech                        OBJECT IDENTIFIER ::= { enterprises 17099 }
fabasoftRAndDSoftware             OBJECT IDENTIFIER ::= { enterprises 17100 }
internetnu                        OBJECT IDENTIFIER ::= { enterprises 17101 }
bororos                           OBJECT IDENTIFIER ::= { enterprises 17102 }
biznetInformationSystemsAndConsultancy OBJECT IDENTIFIER ::= { enterprises 17103 }
communications                    OBJECT IDENTIFIER ::= { enterprises 17104 }
insigniaSolutions                 OBJECT IDENTIFIER ::= { enterprises 17105 }
globnix                           OBJECT IDENTIFIER ::= { enterprises 17106 }
theKonopkaCorporation             OBJECT IDENTIFIER ::= { enterprises 17107 }
vinciSystems                      OBJECT IDENTIFIER ::= { enterprises 17108 }
chotaroCo                         OBJECT IDENTIFIER ::= { enterprises 17109 }
institutDeRecherchePourLeD        OBJECT IDENTIFIER ::= { enterprises 17110 }
jmse                              OBJECT IDENTIFIER ::= { enterprises 17111 }
axstoneCo                         OBJECT IDENTIFIER ::= { enterprises 17112 }
evonetComputerNetworkEvolution    OBJECT IDENTIFIER ::= { enterprises 17113 }
keyrusSA                          OBJECT IDENTIFIER ::= { enterprises 17114 }
dAPPXCorporation                  OBJECT IDENTIFIER ::= { enterprises 17115 }
gmaCOMMUNICATIONMANUFACTURINGAndMARKETING1991LTD OBJECT IDENTIFIER ::= { enterprises 17116 }
advantageSalesAndMarketing        OBJECT IDENTIFIER ::= { enterprises 17117 }
byramHealthcareCenters            OBJECT IDENTIFIER ::= { enterprises 17118 }
octetstring                       OBJECT IDENTIFIER ::= { enterprises 17119 }
teamCoolNetworks                  OBJECT IDENTIFIER ::= { enterprises 17120 }
geronimoGroup                     OBJECT IDENTIFIER ::= { enterprises 17121 }
apogentTechnologies               OBJECT IDENTIFIER ::= { enterprises 17122 }
tavataSoftwareCorporation         OBJECT IDENTIFIER ::= { enterprises 17123 }
psycatGroup                       OBJECT IDENTIFIER ::= { enterprises 17124 }
ezeCastleIntegration              OBJECT IDENTIFIER ::= { enterprises 17125 }
novaEngineering                   OBJECT IDENTIFIER ::= { enterprises 17126 }
kilowattNetworking                OBJECT IDENTIFIER ::= { enterprises 17127 }
mg2org                            OBJECT IDENTIFIER ::= { enterprises 17128 }
zaclickCo                         OBJECT IDENTIFIER ::= { enterprises 17129 }
antiquityBooks                    OBJECT IDENTIFIER ::= { enterprises 17130 }
rectifierTechnologiesPacificPty   OBJECT IDENTIFIER ::= { enterprises 17131 }
shanghaiDareOptoElectronicCommunicationCo OBJECT IDENTIFIER ::= { enterprises 17132 }
ilwooDATAAndTECHNOLOGYCo          OBJECT IDENTIFIER ::= { enterprises 17133 }
goodHealthNetwork                 OBJECT IDENTIFIER ::= { enterprises 17134 }
raaijmakers                       OBJECT IDENTIFIER ::= { enterprises 17135 }
plgAG                             OBJECT IDENTIFIER ::= { enterprises 17136 }
gradsoft                          OBJECT IDENTIFIER ::= { enterprises 17137 }
inhollandUniversities             OBJECT IDENTIFIER ::= { enterprises 17138 }
internetGold                      OBJECT IDENTIFIER ::= { enterprises 17139 }
versatelNederlandBV               OBJECT IDENTIFIER ::= { enterprises 17140 }
incentiSA                         OBJECT IDENTIFIER ::= { enterprises 17141 }
staticBytes                       OBJECT IDENTIFIER ::= { enterprises 17142 }
georgHeweghOberschule             OBJECT IDENTIFIER ::= { enterprises 17143 }
stateUniversityOfNewYorkAtStonyBrook OBJECT IDENTIFIER ::= { enterprises 17144 }
ruschConsultancyBV                OBJECT IDENTIFIER ::= { enterprises 17145 }
uvhc                              OBJECT IDENTIFIER ::= { enterprises 17146 }
easternIllinoisUniversity         OBJECT IDENTIFIER ::= { enterprises 17147 }
iburstForum                       OBJECT IDENTIFIER ::= { enterprises 17148 }
lodestarTechnology                OBJECT IDENTIFIER ::= { enterprises 17149 }
simatika                          OBJECT IDENTIFIER ::= { enterprises 17150 }
cognica                           OBJECT IDENTIFIER ::= { enterprises 17151 }
creamen                           OBJECT IDENTIFIER ::= { enterprises 17152 }
universityOfConnecticut           OBJECT IDENTIFIER ::= { enterprises 17153 }
kittredgeArcheryCo                OBJECT IDENTIFIER ::= { enterprises 17154 }
voiceageCorporation               OBJECT IDENTIFIER ::= { enterprises 17155 }
zoneLabs                          OBJECT IDENTIFIER ::= { enterprises 17156 }
chengduRunwangTchnologyCoLTD      OBJECT IDENTIFIER ::= { enterprises 17157 }
laurasiaComputing                 OBJECT IDENTIFIER ::= { enterprises 17158 }
henriMaireSA                      OBJECT IDENTIFIER ::= { enterprises 17159 }
lundUniversityHospital            OBJECT IDENTIFIER ::= { enterprises 17160 }
covisintLLC                       OBJECT IDENTIFIER ::= { enterprises 17161 }
airversalTechnology               OBJECT IDENTIFIER ::= { enterprises 17162 }
nbtTechnology                     OBJECT IDENTIFIER ::= { enterprises 17163 }
callcast                          OBJECT IDENTIFIER ::= { enterprises 17164 }
advantestRAndDCenter              OBJECT IDENTIFIER ::= { enterprises 17165 }
louisianaStateUniversityAndAAndMCollege OBJECT IDENTIFIER ::= { enterprises 17166 }
daotec                            OBJECT IDENTIFIER ::= { enterprises 17167 }
century21MikeBowman               OBJECT IDENTIFIER ::= { enterprises 17168 }
diablotin                         OBJECT IDENTIFIER ::= { enterprises 17169 }
qindel                            OBJECT IDENTIFIER ::= { enterprises 17171 }
melcoInternationalDevelopment     OBJECT IDENTIFIER ::= { enterprises 17172 }
squeekyClean                      OBJECT IDENTIFIER ::= { enterprises 17173 }
iridiumSystems                    OBJECT IDENTIFIER ::= { enterprises 17174 }
shanghaiLetelCommunicationsCo     OBJECT IDENTIFIER ::= { enterprises 17175 }
permStatePedagogicalUniversity    OBJECT IDENTIFIER ::= { enterprises 17176 }
tis                               OBJECT IDENTIFIER ::= { enterprises 17177 }
veraAutonoomProvinciebedrijf      OBJECT IDENTIFIER ::= { enterprises 17178 }
diaz                              OBJECT IDENTIFIER ::= { enterprises 17179 }
altibase                          OBJECT IDENTIFIER ::= { enterprises 17180 }
dantekComputerSystems             OBJECT IDENTIFIER ::= { enterprises 17181 }
cccDataOy                         OBJECT IDENTIFIER ::= { enterprises 17182 }
yangMeiTechnologyCo               OBJECT IDENTIFIER ::= { enterprises 17183 }
prolan                            OBJECT IDENTIFIER ::= { enterprises 17184 }
richemontGroup                    OBJECT IDENTIFIER ::= { enterprises 17185 }
mediaLINKSCo                      OBJECT IDENTIFIER ::= { enterprises 17186 }
onaro                             OBJECT IDENTIFIER ::= { enterprises 17187 }
gigaclue                          OBJECT IDENTIFIER ::= { enterprises 17188 }
ingraftedSoftware                 OBJECT IDENTIFIER ::= { enterprises 17189 }
fulcrumMicrosystems               OBJECT IDENTIFIER ::= { enterprises 17190 }
facultadDeF                       OBJECT IDENTIFIER ::= { enterprises 17191 }
emprisaNetworks                   OBJECT IDENTIFIER ::= { enterprises 17192 }
dbcDigitalBroadcastConsulting     OBJECT IDENTIFIER ::= { enterprises 17193 }
whoopyEngineering                 OBJECT IDENTIFIER ::= { enterprises 17194 }
securesoftSystems                 OBJECT IDENTIFIER ::= { enterprises 17195 }
cachelogic                        OBJECT IDENTIFIER ::= { enterprises 17196 }
relicore                          OBJECT IDENTIFIER ::= { enterprises 17197 }
martinskaftedk                    OBJECT IDENTIFIER ::= { enterprises 17198 }
ministryOfFisheriesNZ             OBJECT IDENTIFIER ::= { enterprises 17199 }
optusInternetEngineering          OBJECT IDENTIFIER ::= { enterprises 17200 }
digitalItem                       OBJECT IDENTIFIER ::= { enterprises 17201 }
necInformatecSystems              OBJECT IDENTIFIER ::= { enterprises 17202 }
pekarekHandelsgesmbH              OBJECT IDENTIFIER ::= { enterprises 17203 }
iimCORPORATION                    OBJECT IDENTIFIER ::= { enterprises 17204 }
arpentENTERPRISES                 OBJECT IDENTIFIER ::= { enterprises 17205 }
openStockCompanyiOskolElectrometallurgicalKombinat OBJECT IDENTIFIER ::= { enterprises 17206 }
cloverleafCommunications          OBJECT IDENTIFIER ::= { enterprises 17207 }
faNeaSj                           OBJECT IDENTIFIER ::= { enterprises 17208 }
strategicSystemsConsultants       OBJECT IDENTIFIER ::= { enterprises 17209 }
gzsGesellschaftFuerZahlungssystemeMbH OBJECT IDENTIFIER ::= { enterprises 17210 }
potronicsSpZOo                    OBJECT IDENTIFIER ::= { enterprises 17211 }
awetaBv                           OBJECT IDENTIFIER ::= { enterprises 17212 }
daySCOM                           OBJECT IDENTIFIER ::= { enterprises 17213 }
networkDesigners                  OBJECT IDENTIFIER ::= { enterprises 17214 }
instituteOfLinguisticStudies      OBJECT IDENTIFIER ::= { enterprises 17215 }
triplanetPartnersLLC              OBJECT IDENTIFIER ::= { enterprises 17216 }
universityOfRichmond              OBJECT IDENTIFIER ::= { enterprises 17217 }
unionInternationaleDesCheminsDeFer OBJECT IDENTIFIER ::= { enterprises 17218 }
nstel                             OBJECT IDENTIFIER ::= { enterprises 17219 }
ebenx                             OBJECT IDENTIFIER ::= { enterprises 17220 }
chbeUBC                           OBJECT IDENTIFIER ::= { enterprises 17221 }
sierhuisDigitaleDiensten          OBJECT IDENTIFIER ::= { enterprises 17222 }
cenaSalvatore                     OBJECT IDENTIFIER ::= { enterprises 17223 }
newburyNetworks                   OBJECT IDENTIFIER ::= { enterprises 17224 }
ispiOfLincoln                     OBJECT IDENTIFIER ::= { enterprises 17225 }
bc5Technologies                   OBJECT IDENTIFIER ::= { enterprises 17226 }
dmpInitiatives                    OBJECT IDENTIFIER ::= { enterprises 17227 }
kommando                          OBJECT IDENTIFIER ::= { enterprises 17228 }
miracleGroup                      OBJECT IDENTIFIER ::= { enterprises 17229 }
uniqminds                         OBJECT IDENTIFIER ::= { enterprises 17230 }
ottoUK                            OBJECT IDENTIFIER ::= { enterprises 17231 }
pannocom                          OBJECT IDENTIFIER ::= { enterprises 17232 }
icodexSoftwareAG                  OBJECT IDENTIFIER ::= { enterprises 17233 }
etEnterpriseTechnologiesSrl       OBJECT IDENTIFIER ::= { enterprises 17234 }
eSystems                          OBJECT IDENTIFIER ::= { enterprises 17235 }
shoutTelecomsLimited              OBJECT IDENTIFIER ::= { enterprises 17236 }
spesistemiEProgettiElettroniciSasDiPPrandiniAndC OBJECT IDENTIFIER ::= { enterprises 17237 }
nstel2                            OBJECT IDENTIFIER ::= { enterprises 17238 }
planBEmailServices                OBJECT IDENTIFIER ::= { enterprises 17239 }
spreadTeleinform                  OBJECT IDENTIFIER ::= { enterprises 17240 }
federalTradeCommission            OBJECT IDENTIFIER ::= { enterprises 17241 }
missionVi                         OBJECT IDENTIFIER ::= { enterprises 17242 }
worldAccessCanada                 OBJECT IDENTIFIER ::= { enterprises 17243 }
briteaceEnterprisePte             OBJECT IDENTIFIER ::= { enterprises 17244 }
genentech                         OBJECT IDENTIFIER ::= { enterprises 17245 }
freesnmp                          OBJECT IDENTIFIER ::= { enterprises 17246 }
sbcInternetServices               OBJECT IDENTIFIER ::= { enterprises 17247 }
gemstoneCommunications            OBJECT IDENTIFIER ::= { enterprises 17248 }
vanCompany                        OBJECT IDENTIFIER ::= { enterprises 17249 }
yoreElektronikYayimcilikAS        OBJECT IDENTIFIER ::= { enterprises 17250 }
wermspowke                        OBJECT IDENTIFIER ::= { enterprises 17251 }
msGlobalConsulting                OBJECT IDENTIFIER ::= { enterprises 17252 }
arcadaPolytechnic                 OBJECT IDENTIFIER ::= { enterprises 17253 }
goadus                            OBJECT IDENTIFIER ::= { enterprises 17254 }
vidyatel                          OBJECT IDENTIFIER ::= { enterprises 17255 }
clNETSro                          OBJECT IDENTIFIER ::= { enterprises 17256 }
initialSecurityLimited            OBJECT IDENTIFIER ::= { enterprises 17257 }
drqSpZOo                          OBJECT IDENTIFIER ::= { enterprises 17258 }
manex                             OBJECT IDENTIFIER ::= { enterprises 17259 }
numinatekCo                       OBJECT IDENTIFIER ::= { enterprises 17260 }
rjware                            OBJECT IDENTIFIER ::= { enterprises 17261 }
devonshireGroup                   OBJECT IDENTIFIER ::= { enterprises 17262 }
alpesTeam                         OBJECT IDENTIFIER ::= { enterprises 17263 }
mountClemensGeneralHospital       OBJECT IDENTIFIER ::= { enterprises 17264 }
escapeOE                          OBJECT IDENTIFIER ::= { enterprises 17265 }
californiaInternet                OBJECT IDENTIFIER ::= { enterprises 17266 }
hitachiComputerProducts           OBJECT IDENTIFIER ::= { enterprises 17267 }
abbProcessAnalytics               OBJECT IDENTIFIER ::= { enterprises 17268 }
hansaJSC                          OBJECT IDENTIFIER ::= { enterprises 17269 }
comcastCorporation                OBJECT IDENTIFIER ::= { enterprises 17270 }
sunshineVillageSkiAndSnowboardResort OBJECT IDENTIFIER ::= { enterprises 17271 }
akashic                           OBJECT IDENTIFIER ::= { enterprises 17272 }
theRabbitholeOrg                  OBJECT IDENTIFIER ::= { enterprises 17273 }
nevisNetworks                     OBJECT IDENTIFIER ::= { enterprises 17274 }
microbit                          OBJECT IDENTIFIER ::= { enterprises 17275 }
colegioDeRegistradoresDeLaPropiedadYMercantilesDeEspa OBJECT IDENTIFIER ::= { enterprises 17276 }
tuiNederlandNV                    OBJECT IDENTIFIER ::= { enterprises 17277 }
izbSoft                           OBJECT IDENTIFIER ::= { enterprises 17278 }
stoweHoldings                     OBJECT IDENTIFIER ::= { enterprises 17279 }
fadesaInmobiliaria                OBJECT IDENTIFIER ::= { enterprises 17280 }
lutherCollege                     OBJECT IDENTIFIER ::= { enterprises 17281 }
abhai                             OBJECT IDENTIFIER ::= { enterprises 17282 }
yacmeSrl                          OBJECT IDENTIFIER ::= { enterprises 17283 }
unicomUNIversalComputerCOMmunication OBJECT IDENTIFIER ::= { enterprises 17284 }
dobs                              OBJECT IDENTIFIER ::= { enterprises 17285 }
steuerungsAndNetzwerktechnik      OBJECT IDENTIFIER ::= { enterprises 17286 }
pacificLife                       OBJECT IDENTIFIER ::= { enterprises 17287 }
vicsuper                          OBJECT IDENTIFIER ::= { enterprises 17288 }
linuxhq                           OBJECT IDENTIFIER ::= { enterprises 17289 }
keyDigitalSolutions               OBJECT IDENTIFIER ::= { enterprises 17290 }
mithraBiodindustryCo              OBJECT IDENTIFIER ::= { enterprises 17291 }
nxnSoftwareAG                     OBJECT IDENTIFIER ::= { enterprises 17292 }
davidrlee                         OBJECT IDENTIFIER ::= { enterprises 17293 }
agileTeamwork                     OBJECT IDENTIFIER ::= { enterprises 17294 }
westnoble                         OBJECT IDENTIFIER ::= { enterprises 17295 }
fourthCornerSystems               OBJECT IDENTIFIER ::= { enterprises 17296 }
sineNomineAssociates              OBJECT IDENTIFIER ::= { enterprises 17297 }
bluewaterTechnologies             OBJECT IDENTIFIER ::= { enterprises 17298 }
vmokshaTechnologiesPrivateLimited OBJECT IDENTIFIER ::= { enterprises 17299 }
axxiusBv                          OBJECT IDENTIFIER ::= { enterprises 17300 }
allserveAutomatiseringBV          OBJECT IDENTIFIER ::= { enterprises 17301 }
iconology                         OBJECT IDENTIFIER ::= { enterprises 17302 }
paramountPictures                 OBJECT IDENTIFIER ::= { enterprises 17303 }
layer7Technologies                OBJECT IDENTIFIER ::= { enterprises 17304 }
aerasNetworks                     OBJECT IDENTIFIER ::= { enterprises 17305 }
armenianEScienceFoundation        OBJECT IDENTIFIER ::= { enterprises 17306 }
tribunalRegionalDoTrabalhoDa15    OBJECT IDENTIFIER ::= { enterprises 17307 }
digimedworx                       OBJECT IDENTIFIER ::= { enterprises 17308 }
saudiArabianMonetaryAgency        OBJECT IDENTIFIER ::= { enterprises 17309 }
vanquishInternational             OBJECT IDENTIFIER ::= { enterprises 17310 }
myllykoskiCorp                    OBJECT IDENTIFIER ::= { enterprises 17311 }
shizuokaSystemTechnology          OBJECT IDENTIFIER ::= { enterprises 17312 }
ratiodata                         OBJECT IDENTIFIER ::= { enterprises 17313 }
soltim                            OBJECT IDENTIFIER ::= { enterprises 17314 }
etheraddresscom                   OBJECT IDENTIFIER ::= { enterprises 17315 }
peoriaChristianSchool             OBJECT IDENTIFIER ::= { enterprises 17316 }
massiveego                        OBJECT IDENTIFIER ::= { enterprises 17317 }
m5tCentreD                        OBJECT IDENTIFIER ::= { enterprises 17318 }
jcComputing                       OBJECT IDENTIFIER ::= { enterprises 17319 }
jAndmCrowther                     OBJECT IDENTIFIER ::= { enterprises 17320 }
calpine                           OBJECT IDENTIFIER ::= { enterprises 17321 }
softland                          OBJECT IDENTIFIER ::= { enterprises 17322 }
datatekniskaByr                   OBJECT IDENTIFIER ::= { enterprises 17323 }
ydiWireless                       OBJECT IDENTIFIER ::= { enterprises 17324 }
babastik                          OBJECT IDENTIFIER ::= { enterprises 17325 }
acCamerfirma                      OBJECT IDENTIFIER ::= { enterprises 17326 }
cityOfNorthglenn                  OBJECT IDENTIFIER ::= { enterprises 17327 }
imentaSwedenAB                    OBJECT IDENTIFIER ::= { enterprises 17328 }
schoolOfInformationTechnologyUniversitiUtaraMalaysia OBJECT IDENTIFIER ::= { enterprises 17329 }
zettaSystems                      OBJECT IDENTIFIER ::= { enterprises 17330 }
three0SanInformationSystemCo      OBJECT IDENTIFIER ::= { enterprises 17331 }
peteAttkinsEngineering            OBJECT IDENTIFIER ::= { enterprises 17332 }
criticalNetworks                  OBJECT IDENTIFIER ::= { enterprises 17333 }
dnSolutions                       OBJECT IDENTIFIER ::= { enterprises 17334 }
upmKymmeneCorporation             OBJECT IDENTIFIER ::= { enterprises 17335 }
bankOfRussia                      OBJECT IDENTIFIER ::= { enterprises 17336 }
solaceSystems                     OBJECT IDENTIFIER ::= { enterprises 17337 }
ibsTechnologyAndServices          OBJECT IDENTIFIER ::= { enterprises 17338 }
safaGALENICA                      OBJECT IDENTIFIER ::= { enterprises 17339 }
microtest2                        OBJECT IDENTIFIER ::= { enterprises 17340 }
fonnerConsulting                  OBJECT IDENTIFIER ::= { enterprises 17341 }
danskeGymnasieeleversSammenslutning OBJECT IDENTIFIER ::= { enterprises 17342 }
edula                             OBJECT IDENTIFIER ::= { enterprises 17343 }
ofset                             OBJECT IDENTIFIER ::= { enterprises 17344 }
fusionone                         OBJECT IDENTIFIER ::= { enterprises 17345 }
alienforceit                      OBJECT IDENTIFIER ::= { enterprises 17346 }
hiltiCorporation                  OBJECT IDENTIFIER ::= { enterprises 17347 }
ustcEBusinessTechnologyCompany    OBJECT IDENTIFIER ::= { enterprises 17348 }
deltaNV                           OBJECT IDENTIFIER ::= { enterprises 17349 }
onrelay                           OBJECT IDENTIFIER ::= { enterprises 17350 }
simmonsCollege                    OBJECT IDENTIFIER ::= { enterprises 17351 }
francisscottCommunicationsLLC     OBJECT IDENTIFIER ::= { enterprises 17352 }
vissimAS                          OBJECT IDENTIFIER ::= { enterprises 17353 }
zoneTradingPartners               OBJECT IDENTIFIER ::= { enterprises 17354 }
cirrusMultimediaLimited           OBJECT IDENTIFIER ::= { enterprises 17355 }
riskmetricsGroup                  OBJECT IDENTIFIER ::= { enterprises 17356 }
derksit                           OBJECT IDENTIFIER ::= { enterprises 17357 }
fulfordConsulting                 OBJECT IDENTIFIER ::= { enterprises 17358 }
net9                              OBJECT IDENTIFIER ::= { enterprises 17359 }
tAndjComputerSystems              OBJECT IDENTIFIER ::= { enterprises 17360 }
infoscienceCorporation            OBJECT IDENTIFIER ::= { enterprises 17361 }
asiaPacificBioinformaticsNetwork  OBJECT IDENTIFIER ::= { enterprises 17362 }
sanyoDDPBU                        OBJECT IDENTIFIER ::= { enterprises 17363 }
siteli                            OBJECT IDENTIFIER ::= { enterprises 17364 }
sissaISASScuolaInternazionaleSuperioreDiStudiAvanzati OBJECT IDENTIFIER ::= { enterprises 17365 }
torbayCouncil                     OBJECT IDENTIFIER ::= { enterprises 17366 }
grepAS                            OBJECT IDENTIFIER ::= { enterprises 17367 }
pifaut                            OBJECT IDENTIFIER ::= { enterprises 17368 }
sustainableDevelopmentNetworkingProgramme OBJECT IDENTIFIER ::= { enterprises 17369 }
onrelay2                          OBJECT IDENTIFIER ::= { enterprises 17370 }
dotnetOHG                         OBJECT IDENTIFIER ::= { enterprises 17371 }
ifoniCellularServices             OBJECT IDENTIFIER ::= { enterprises 17372 }
itWatchdogs                       OBJECT IDENTIFIER ::= { enterprises 17373 }
clearfieldKnowledgeSolutions      OBJECT IDENTIFIER ::= { enterprises 17374 }
imageAnalysis                     OBJECT IDENTIFIER ::= { enterprises 17375 }
intelcomSanMarinoSpA              OBJECT IDENTIFIER ::= { enterprises 17376 }
aesysSpa                          OBJECT IDENTIFIER ::= { enterprises 17377 }
interlinkSoftwareServices         OBJECT IDENTIFIER ::= { enterprises 17378 }
universityOfAppliedSciencesWolfenbuettel OBJECT IDENTIFIER ::= { enterprises 17379 }
spazioZeroUnoSpA                  OBJECT IDENTIFIER ::= { enterprises 17380 }
theKinkaidSchool                  OBJECT IDENTIFIER ::= { enterprises 17381 }
vaiBv                             OBJECT IDENTIFIER ::= { enterprises 17382 }
easySOFTWARE                      OBJECT IDENTIFIER ::= { enterprises 17383 }
contemporaryControlSystems        OBJECT IDENTIFIER ::= { enterprises 17384 }
appriss                           OBJECT IDENTIFIER ::= { enterprises 17385 }
icansp                            OBJECT IDENTIFIER ::= { enterprises 17386 }
frontierFinancial                 OBJECT IDENTIFIER ::= { enterprises 17387 }
allenSystemsGroupINC              OBJECT IDENTIFIER ::= { enterprises 17388 }
coreNAP                           OBJECT IDENTIFIER ::= { enterprises 17389 }
familyVideo                       OBJECT IDENTIFIER ::= { enterprises 17390 }
noseAppliedIntelligenceAG         OBJECT IDENTIFIER ::= { enterprises 17391 }
abuccoTechnologies                OBJECT IDENTIFIER ::= { enterprises 17392 }
allenSystemsGroupINC2             OBJECT IDENTIFIER ::= { enterprises 17393 }
brainbowEDVBeratung               OBJECT IDENTIFIER ::= { enterprises 17394 }
beijingFounderElectronicCo        OBJECT IDENTIFIER ::= { enterprises 17395 }
sapuraAdvanceSystemsSdnBhd        OBJECT IDENTIFIER ::= { enterprises 17396 }
bveDesKantonsBern                 OBJECT IDENTIFIER ::= { enterprises 17397 }
hbhard                            OBJECT IDENTIFIER ::= { enterprises 17398 }
akit                              OBJECT IDENTIFIER ::= { enterprises 17399 }
tourislineAG                      OBJECT IDENTIFIER ::= { enterprises 17400 }
lands                             OBJECT IDENTIFIER ::= { enterprises 17401 }
sevisSystems                      OBJECT IDENTIFIER ::= { enterprises 17402 }
oklahomaDepartmentOfCareerAndTechnologyEducation OBJECT IDENTIFIER ::= { enterprises 17403 }
webundco                          OBJECT IDENTIFIER ::= { enterprises 17404 }
telecommunicationsIndustryAssociationTR8dot5 OBJECT IDENTIFIER ::= { enterprises 17405 }
hits                              OBJECT IDENTIFIER ::= { enterprises 17406 }
omegawareSystems                  OBJECT IDENTIFIER ::= { enterprises 17407 }
hicomCOMUNICA                     OBJECT IDENTIFIER ::= { enterprises 17408 }
nationalStandardizationCommitteeOfRadioAndTelevision OBJECT IDENTIFIER ::= { enterprises 17409 }
sopraGROUP                        OBJECT IDENTIFIER ::= { enterprises 17410 }
newskySoftware                    OBJECT IDENTIFIER ::= { enterprises 17411 }
gateconnectTechnologies           OBJECT IDENTIFIER ::= { enterprises 17412 }
ministerioDelInteriorEspa         OBJECT IDENTIFIER ::= { enterprises 17413 }
vzwCDS                            OBJECT IDENTIFIER ::= { enterprises 17414 }
pucrs                             OBJECT IDENTIFIER ::= { enterprises 17415 }
rootIT                            OBJECT IDENTIFIER ::= { enterprises 17416 }
portivaCorporation                OBJECT IDENTIFIER ::= { enterprises 17417 }
mahanaxarNetworks                 OBJECT IDENTIFIER ::= { enterprises 17418 }
lincolnInvestmentPlanning         OBJECT IDENTIFIER ::= { enterprises 17419 }
digipowerManufacturing            OBJECT IDENTIFIER ::= { enterprises 17420 }
h4                                OBJECT IDENTIFIER ::= { enterprises 17421 }
realEnterpriseSolutionsDevelopmentBV OBJECT IDENTIFIER ::= { enterprises 17422 }
multidataGesellschaftF            OBJECT IDENTIFIER ::= { enterprises 17423 }
chartPilot                        OBJECT IDENTIFIER ::= { enterprises 17424 }
ilinkKommunikationssysteme        OBJECT IDENTIFIER ::= { enterprises 17425 }
segacom                           OBJECT IDENTIFIER ::= { enterprises 17426 }
abyzInform                        OBJECT IDENTIFIER ::= { enterprises 17427 }
webdesignBK                       OBJECT IDENTIFIER ::= { enterprises 17428 }
michaelTelecomAG                  OBJECT IDENTIFIER ::= { enterprises 17429 }
tclNETWORKEQUIPMENT               OBJECT IDENTIFIER ::= { enterprises 17430 }
shenzhenSDGInformationCo          OBJECT IDENTIFIER ::= { enterprises 17431 }
georgiaPerimeterCollege           OBJECT IDENTIFIER ::= { enterprises 17432 }
pieasEducationalInstitute         OBJECT IDENTIFIER ::= { enterprises 17433 }
theralys                          OBJECT IDENTIFIER ::= { enterprises 17434 }
beac                              OBJECT IDENTIFIER ::= { enterprises 17435 }
worlightInternational             OBJECT IDENTIFIER ::= { enterprises 17436 }
insuranceCorporationOfBritishColumbia OBJECT IDENTIFIER ::= { enterprises 17437 }
novannet                          OBJECT IDENTIFIER ::= { enterprises 17438 }
matsushitaAvionicsSystemsCorporation OBJECT IDENTIFIER ::= { enterprises 17439 }
omnipod                           OBJECT IDENTIFIER ::= { enterprises 17440 }
unholyorg                         OBJECT IDENTIFIER ::= { enterprises 17441 }
iter8                             OBJECT IDENTIFIER ::= { enterprises 17442 }
gerdKoslowski                     OBJECT IDENTIFIER ::= { enterprises 17443 }
wrevaknet                         OBJECT IDENTIFIER ::= { enterprises 17444 }
feasVof                           OBJECT IDENTIFIER ::= { enterprises 17445 }
stefanDrees                       OBJECT IDENTIFIER ::= { enterprises 17446 }
stateMACHINE                      OBJECT IDENTIFIER ::= { enterprises 17447 }
fabriceCo                         OBJECT IDENTIFIER ::= { enterprises 17448 }
klsAirExpress                     OBJECT IDENTIFIER ::= { enterprises 17449 }
wfworg                            OBJECT IDENTIFIER ::= { enterprises 17450 }
ifamily2003                       OBJECT IDENTIFIER ::= { enterprises 17451 }
visyIndustriesHoldingsPty         OBJECT IDENTIFIER ::= { enterprises 17452 }
billionElectricCo                 OBJECT IDENTIFIER ::= { enterprises 17453 }
integuru                          OBJECT IDENTIFIER ::= { enterprises 17454 }
kBESTTECHNOLOGYINC                OBJECT IDENTIFIER ::= { enterprises 17455 }
jigsawSystems                     OBJECT IDENTIFIER ::= { enterprises 17456 }
utiWorldwide                      OBJECT IDENTIFIER ::= { enterprises 17457 }
connectInternetSolutionsPTYLTD    OBJECT IDENTIFIER ::= { enterprises 17458 }
mibtree                           OBJECT IDENTIFIER ::= { enterprises 17459 }
revelantTechnologies              OBJECT IDENTIFIER ::= { enterprises 17460 }
prydeSystemsAndSoftware           OBJECT IDENTIFIER ::= { enterprises 17461 }
akamaiTechnologies                OBJECT IDENTIFIER ::= { enterprises 17462 }
demarcSecurity                    OBJECT IDENTIFIER ::= { enterprises 17463 }
o1Communications                  OBJECT IDENTIFIER ::= { enterprises 17464 }
trusystems                        OBJECT IDENTIFIER ::= { enterprises 17465 }
woojuCommunicationsCO             OBJECT IDENTIFIER ::= { enterprises 17466 }
gamer                             OBJECT IDENTIFIER ::= { enterprises 17467 }
iconagAG                          OBJECT IDENTIFIER ::= { enterprises 17468 }
biowisdom                         OBJECT IDENTIFIER ::= { enterprises 17469 }
str                               OBJECT IDENTIFIER ::= { enterprises 17470 }
actonaTechnologies                OBJECT IDENTIFIER ::= { enterprises 17471 }
tetraplex                         OBJECT IDENTIFIER ::= { enterprises 17472 }
telluceCorporation                OBJECT IDENTIFIER ::= { enterprises 17473 }
crmInformatik                     OBJECT IDENTIFIER ::= { enterprises 17474 }
genetecInformationSystems         OBJECT IDENTIFIER ::= { enterprises 17475 }
vONECorporation                   OBJECT IDENTIFIER ::= { enterprises 17476 }
trailblazerSystems                OBJECT IDENTIFIER ::= { enterprises 17477 }
nexadesic                         OBJECT IDENTIFIER ::= { enterprises 17478 }
oneUnified                        OBJECT IDENTIFIER ::= { enterprises 17479 }
choiceCommunications              OBJECT IDENTIFIER ::= { enterprises 17480 }
logicFusion                       OBJECT IDENTIFIER ::= { enterprises 17481 }
ogmiosca                          OBJECT IDENTIFIER ::= { enterprises 17482 }
hongKongSchoolNet                 OBJECT IDENTIFIER ::= { enterprises 17483 }
adyoronIntelligentSystems         OBJECT IDENTIFIER ::= { enterprises 17484 }
hierweb                           OBJECT IDENTIFIER ::= { enterprises 17485 }
edsDeutschland                    OBJECT IDENTIFIER ::= { enterprises 17486 }
manchesterAirport                 OBJECT IDENTIFIER ::= { enterprises 17487 }
generalTOUCHTECHNOLOGYCO          OBJECT IDENTIFIER ::= { enterprises 17488 }
curtisConsultingLLC               OBJECT IDENTIFIER ::= { enterprises 17489 }
dmTrucking                        OBJECT IDENTIFIER ::= { enterprises 17490 }
barixAG                           OBJECT IDENTIFIER ::= { enterprises 17491 }
northconet                        OBJECT IDENTIFIER ::= { enterprises 17492 }
halliburtonCorporation            OBJECT IDENTIFIER ::= { enterprises 17493 }
matthiasRath                      OBJECT IDENTIFIER ::= { enterprises 17494 }
gardelSoftware                    OBJECT IDENTIFIER ::= { enterprises 17495 }
canadianBroadcastingCorporation   OBJECT IDENTIFIER ::= { enterprises 17496 }
tallinnSchoolNo21                 OBJECT IDENTIFIER ::= { enterprises 17497 }
kommunaleDatenverarbeitungOldenburg OBJECT IDENTIFIER ::= { enterprises 17498 }
packetsurge                       OBJECT IDENTIFIER ::= { enterprises 17499 }
gwinnettUniversityCenter          OBJECT IDENTIFIER ::= { enterprises 17500 }
drakeUniversity                   OBJECT IDENTIFIER ::= { enterprises 17501 }
newfieldAutomation                OBJECT IDENTIFIER ::= { enterprises 17502 }
techforgeSoftware                 OBJECT IDENTIFIER ::= { enterprises 17503 }
securityWizard                    OBJECT IDENTIFIER ::= { enterprises 17504 }
waminOptocommMfgcorporation       OBJECT IDENTIFIER ::= { enterprises 17505 }
eulerianTechnologies              OBJECT IDENTIFIER ::= { enterprises 17506 }
omnidata                          OBJECT IDENTIFIER ::= { enterprises 17507 }
sotrangeTransportesRodovi         OBJECT IDENTIFIER ::= { enterprises 17508 }
versatelNetworks                  OBJECT IDENTIFIER ::= { enterprises 17509 }
goldenhope                        OBJECT IDENTIFIER ::= { enterprises 17510 }
xtremexCorporation                OBJECT IDENTIFIER ::= { enterprises 17511 }
flindersUniversity                OBJECT IDENTIFIER ::= { enterprises 17512 }
rva                               OBJECT IDENTIFIER ::= { enterprises 17513 }
fdf                               OBJECT IDENTIFIER ::= { enterprises 17514 }
bnsfRailway                       OBJECT IDENTIFIER ::= { enterprises 17515 }
nighthawkRadiologyServices        OBJECT IDENTIFIER ::= { enterprises 17516 }
clementiSoftware                  OBJECT IDENTIFIER ::= { enterprises 17517 }
combaTelecomSystem                OBJECT IDENTIFIER ::= { enterprises 17518 }
intelitrac                        OBJECT IDENTIFIER ::= { enterprises 17519 }
eastonTechnologies                OBJECT IDENTIFIER ::= { enterprises 17520 }
realeastNetworks                  OBJECT IDENTIFIER ::= { enterprises 17521 }
ozitem                            OBJECT IDENTIFIER ::= { enterprises 17522 }
fiberlan                          OBJECT IDENTIFIER ::= { enterprises 17523 }
ferrariElectroniAG                OBJECT IDENTIFIER ::= { enterprises 17524 }
amsterdamInternetExchangeBV       OBJECT IDENTIFIER ::= { enterprises 17525 }
symentis                          OBJECT IDENTIFIER ::= { enterprises 17526 }
formware                          OBJECT IDENTIFIER ::= { enterprises 17527 }
kmsInternetSolutionProviders      OBJECT IDENTIFIER ::= { enterprises 17528 }
feldtech                          OBJECT IDENTIFIER ::= { enterprises 17529 }
chernigovStateTechnologicalUniversity OBJECT IDENTIFIER ::= { enterprises 17530 }
henricoCountyPublicSchools        OBJECT IDENTIFIER ::= { enterprises 17531 }
bsiInformatica                    OBJECT IDENTIFIER ::= { enterprises 17532 }
associationKAZAR                  OBJECT IDENTIFIER ::= { enterprises 17533 }
optelecom                         OBJECT IDENTIFIER ::= { enterprises 17534 }
egt                               OBJECT IDENTIFIER ::= { enterprises 17535 }
telenity                          OBJECT IDENTIFIER ::= { enterprises 17536 }
florencePublicSchoolDistrictOne   OBJECT IDENTIFIER ::= { enterprises 17537 }
villageGrilleFamilyDiner          OBJECT IDENTIFIER ::= { enterprises 17538 }
mxcSoftware                       OBJECT IDENTIFIER ::= { enterprises 17539 }
tbSolutionsAdvancedTechnologiesSL OBJECT IDENTIFIER ::= { enterprises 17540 }
lamda                             OBJECT IDENTIFIER ::= { enterprises 17541 }
tfsTechnology                     OBJECT IDENTIFIER ::= { enterprises 17542 }
aduneo                            OBJECT IDENTIFIER ::= { enterprises 17543 }
bspPartners                       OBJECT IDENTIFIER ::= { enterprises 17544 }
wirefreeInnovisionPvt             OBJECT IDENTIFIER ::= { enterprises 17545 }
magnoComunicacoes                 OBJECT IDENTIFIER ::= { enterprises 17546 }
centreForGoodGovernance           OBJECT IDENTIFIER ::= { enterprises 17547 }
air2web                           OBJECT IDENTIFIER ::= { enterprises 17548 }
logiclibrary                      OBJECT IDENTIFIER ::= { enterprises 17549 }
trueBladeSystems                  OBJECT IDENTIFIER ::= { enterprises 17550 }
kmartCorporation                  OBJECT IDENTIFIER ::= { enterprises 17551 }
nkiAvL                            OBJECT IDENTIFIER ::= { enterprises 17552 }
telefonicaDataColombiaSA          OBJECT IDENTIFIER ::= { enterprises 17553 }
podiTheDigitalPrintingInitiative  OBJECT IDENTIFIER ::= { enterprises 17554 }
websterUniversity                 OBJECT IDENTIFIER ::= { enterprises 17555 }
maxina                            OBJECT IDENTIFIER ::= { enterprises 17556 }
tokyoWoman                        OBJECT IDENTIFIER ::= { enterprises 17557 }
moveoSystemyTeleinformatyczne     OBJECT IDENTIFIER ::= { enterprises 17558 }
theArtInstituteOfChicago          OBJECT IDENTIFIER ::= { enterprises 17559 }
netforyouCO                       OBJECT IDENTIFIER ::= { enterprises 17560 }
clink                             OBJECT IDENTIFIER ::= { enterprises 17561 }
expectTechnology                  OBJECT IDENTIFIER ::= { enterprises 17562 }
encodeSA                          OBJECT IDENTIFIER ::= { enterprises 17563 }
wwwportocervocc                   OBJECT IDENTIFIER ::= { enterprises 17564 }
ruralServiciosInform              OBJECT IDENTIFIER ::= { enterprises 17565 }
efgEUROBANKERGASIASAE             OBJECT IDENTIFIER ::= { enterprises 17566 }
certimailSA                       OBJECT IDENTIFIER ::= { enterprises 17567 }
slatSA                            OBJECT IDENTIFIER ::= { enterprises 17568 }
schranzhoferDIAS                  OBJECT IDENTIFIER ::= { enterprises 17569 }
ifsAudiovisuals                   OBJECT IDENTIFIER ::= { enterprises 17570 }
glensoundElectronics              OBJECT IDENTIFIER ::= { enterprises 17571 }
mainframeOy                       OBJECT IDENTIFIER ::= { enterprises 17572 }
secretariaDasFinan                OBJECT IDENTIFIER ::= { enterprises 17573 }
oxfordMicrosystems                OBJECT IDENTIFIER ::= { enterprises 17574 }
lebenshilfeNiederoesterreich      OBJECT IDENTIFIER ::= { enterprises 17575 }
mahalingamAndCo                   OBJECT IDENTIFIER ::= { enterprises 17576 }
ralfBisgesInformationstechnik     OBJECT IDENTIFIER ::= { enterprises 17577 }
berlitzInternational              OBJECT IDENTIFIER ::= { enterprises 17578 }
grooveMedia                       OBJECT IDENTIFIER ::= { enterprises 17579 }
telefonicaDataColombiaSA2         OBJECT IDENTIFIER ::= { enterprises 17580 }
hofmannSoftwareEngineeringInternational OBJECT IDENTIFIER ::= { enterprises 17581 }
loranTechnologie                  OBJECT IDENTIFIER ::= { enterprises 17582 }
informationTechnologiesAustraliaPty OBJECT IDENTIFIER ::= { enterprises 17583 }
unitedNetworkCommunicationCorp    OBJECT IDENTIFIER ::= { enterprises 17584 }
compusys                          OBJECT IDENTIFIER ::= { enterprises 17585 }
bandaiNETWORKSCO                  OBJECT IDENTIFIER ::= { enterprises 17586 }
laserbitCommunicationsCorporation OBJECT IDENTIFIER ::= { enterprises 17587 }
globalELECTRICITYCO               OBJECT IDENTIFIER ::= { enterprises 17588 }
amecSPIECommunications            OBJECT IDENTIFIER ::= { enterprises 17589 }
orbisTerrarumNetworks             OBJECT IDENTIFIER ::= { enterprises 17590 }
theDefenderAssociation            OBJECT IDENTIFIER ::= { enterprises 17591 }
javaciseSoftware                  OBJECT IDENTIFIER ::= { enterprises 17592 }
eathCo                            OBJECT IDENTIFIER ::= { enterprises 17593 }
simitelSDeRLDeCV                  OBJECT IDENTIFIER ::= { enterprises 17594 }
seu                               OBJECT IDENTIFIER ::= { enterprises 17595 }
digionline                        OBJECT IDENTIFIER ::= { enterprises 17596 }
intradataBV                       OBJECT IDENTIFIER ::= { enterprises 17597 }
jouveSI                           OBJECT IDENTIFIER ::= { enterprises 17598 }
northernAlbertaInstituteOfTechnology OBJECT IDENTIFIER ::= { enterprises 17599 }
chuq                              OBJECT IDENTIFIER ::= { enterprises 17600 }
groupOneTrading                   OBJECT IDENTIFIER ::= { enterprises 17601 }
midnightLinux                     OBJECT IDENTIFIER ::= { enterprises 17602 }
surespeed                         OBJECT IDENTIFIER ::= { enterprises 17603 }
scysoftMultimedia                 OBJECT IDENTIFIER ::= { enterprises 17604 }
jensBr                            OBJECT IDENTIFIER ::= { enterprises 17605 }
helloworld                        OBJECT IDENTIFIER ::= { enterprises 17606 }
retia                             OBJECT IDENTIFIER ::= { enterprises 17607 }
gieAGORA                          OBJECT IDENTIFIER ::= { enterprises 17608 }
azMercury                         OBJECT IDENTIFIER ::= { enterprises 17609 }
sadhuSoftwareServicesPvt          OBJECT IDENTIFIER ::= { enterprises 17610 }
excSoftware                       OBJECT IDENTIFIER ::= { enterprises 17611 }
groupeCaisseD                     OBJECT IDENTIFIER ::= { enterprises 17612 }
sAccessGMBH                       OBJECT IDENTIFIER ::= { enterprises 17613 }
queenslandParallelSupercomputingFoundation OBJECT IDENTIFIER ::= { enterprises 17614 }
ashwaySoftware                    OBJECT IDENTIFIER ::= { enterprises 17615 }
exclusiveFlorSales                OBJECT IDENTIFIER ::= { enterprises 17616 }
messagegate                       OBJECT IDENTIFIER ::= { enterprises 17617 }
zinitinet                         OBJECT IDENTIFIER ::= { enterprises 17618 }
jEnterpriseBV                     OBJECT IDENTIFIER ::= { enterprises 17619 }
mouldIndustriaDeMatrizes          OBJECT IDENTIFIER ::= { enterprises 17620 }
lightwaveAccess                   OBJECT IDENTIFIER ::= { enterprises 17621 }
openserve                         OBJECT IDENTIFIER ::= { enterprises 17622 }
millersvilleUniversity            OBJECT IDENTIFIER ::= { enterprises 17623 }
scoutingNederland                 OBJECT IDENTIFIER ::= { enterprises 17624 }
brightlineTechnology              OBJECT IDENTIFIER ::= { enterprises 17625 }
phoenixBusinessTechnologiesGroup  OBJECT IDENTIFIER ::= { enterprises 17626 }
willSystems                       OBJECT IDENTIFIER ::= { enterprises 17627 }
mountHayTechnology                OBJECT IDENTIFIER ::= { enterprises 17628 }
nishimuELECTRONICSINDUSTRIESCO    OBJECT IDENTIFIER ::= { enterprises 17629 }
anana                             OBJECT IDENTIFIER ::= { enterprises 17630 }
oralDiagnosticSystems             OBJECT IDENTIFIER ::= { enterprises 17631 }
tpisacom                          OBJECT IDENTIFIER ::= { enterprises 17632 }
phoenixColorCorporation           OBJECT IDENTIFIER ::= { enterprises 17633 }
agbUKLimited                      OBJECT IDENTIFIER ::= { enterprises 17634 }
dragontailOnlineSecurity          OBJECT IDENTIFIER ::= { enterprises 17635 }
novahead                          OBJECT IDENTIFIER ::= { enterprises 17636 }
fudoorg                           OBJECT IDENTIFIER ::= { enterprises 17637 }
jajok                             OBJECT IDENTIFIER ::= { enterprises 17638 }
abbeynetSrl                       OBJECT IDENTIFIER ::= { enterprises 17639 }
reifenberger                      OBJECT IDENTIFIER ::= { enterprises 17640 }
webPublicationsPty                OBJECT IDENTIFIER ::= { enterprises 17641 }
printsoftCzechRepublic            OBJECT IDENTIFIER ::= { enterprises 17642 }
shanghaiNeotuneInformationTechnologyCo OBJECT IDENTIFIER ::= { enterprises 17643 }
nextGenerationBroadband           OBJECT IDENTIFIER ::= { enterprises 17644 }
cbca                              OBJECT IDENTIFIER ::= { enterprises 17645 }
contactEnergy                     OBJECT IDENTIFIER ::= { enterprises 17646 }
nttMultimediaCommunicationsLaboratories OBJECT IDENTIFIER ::= { enterprises 17647 }
amatSC                            OBJECT IDENTIFIER ::= { enterprises 17648 }
pumaAG                            OBJECT IDENTIFIER ::= { enterprises 17649 }
itsoft                            OBJECT IDENTIFIER ::= { enterprises 17650 }
necronX                           OBJECT IDENTIFIER ::= { enterprises 17651 }
mckessonISFrance                  OBJECT IDENTIFIER ::= { enterprises 17652 }
mootHallHoldingsLimited           OBJECT IDENTIFIER ::= { enterprises 17653 }
sheerNetworks                     OBJECT IDENTIFIER ::= { enterprises 17654 }
epsys                             OBJECT IDENTIFIER ::= { enterprises 17655 }
tohokuRicohCo                     OBJECT IDENTIFIER ::= { enterprises 17656 }
logicalSolutions                  OBJECT IDENTIFIER ::= { enterprises 17658 }
theLutheranUniversityAssociation  OBJECT IDENTIFIER ::= { enterprises 17659 }
astaUniversitaetPotsdam           OBJECT IDENTIFIER ::= { enterprises 17660 }
lincolnNationalCorporation        OBJECT IDENTIFIER ::= { enterprises 17661 }
lucentEBS                         OBJECT IDENTIFIER ::= { enterprises 17662 }
icsIndustrielleAutomatisierungssysteme OBJECT IDENTIFIER ::= { enterprises 17663 }
watkinsContracting                OBJECT IDENTIFIER ::= { enterprises 17664 }
imakeSoftwareAndServices          OBJECT IDENTIFIER ::= { enterprises 17665 }
newJerseyHgiherEducationStudentAssistanceAuthority OBJECT IDENTIFIER ::= { enterprises 17666 }
pctInternational                  OBJECT IDENTIFIER ::= { enterprises 17667 }
americanMedicalSecurity           OBJECT IDENTIFIER ::= { enterprises 17668 }
vslCatena                         OBJECT IDENTIFIER ::= { enterprises 17669 }
cellianceSarl                     OBJECT IDENTIFIER ::= { enterprises 17670 }
ptMugiReksoAbadi                  OBJECT IDENTIFIER ::= { enterprises 17671 }
machSoftware                      OBJECT IDENTIFIER ::= { enterprises 17672 }
certONERA                         OBJECT IDENTIFIER ::= { enterprises 17673 }
vt100                             OBJECT IDENTIFIER ::= { enterprises 17674 }
hillMcGlynnAndAssociates          OBJECT IDENTIFIER ::= { enterprises 17675 }
nextevolutionAG                   OBJECT IDENTIFIER ::= { enterprises 17676 }
traditionFinancialServices        OBJECT IDENTIFIER ::= { enterprises 17677 }
openXTecnologiaDaInformacao       OBJECT IDENTIFIER ::= { enterprises 17678 }
chapterEight                      OBJECT IDENTIFIER ::= { enterprises 17679 }
dialupUSA                         OBJECT IDENTIFIER ::= { enterprises 17680 }
johnsHopkinsBloombergSchoolOfPublicHealthCenterForCommunicationP OBJECT IDENTIFIER ::= { enterprises 17681 }
bnxSystemsCorporation             OBJECT IDENTIFIER ::= { enterprises 17682 }
davisPolkAndWardwell              OBJECT IDENTIFIER ::= { enterprises 17683 }
xiSoftware                        OBJECT IDENTIFIER ::= { enterprises 17684 }
dunesTechnologiesSA               OBJECT IDENTIFIER ::= { enterprises 17685 }
bfAndmInsuranceGroup              OBJECT IDENTIFIER ::= { enterprises 17686 }
teamworkSolutions                 OBJECT IDENTIFIER ::= { enterprises 17687 }
o2                                OBJECT IDENTIFIER ::= { enterprises 17688 }
tjmComputing                      OBJECT IDENTIFIER ::= { enterprises 17689 }
theUniversityOfNewcastle          OBJECT IDENTIFIER ::= { enterprises 17690 }
iNetDeviceCo                      OBJECT IDENTIFIER ::= { enterprises 17691 }
torkildL                          OBJECT IDENTIFIER ::= { enterprises 17692 }
insitutDeRechercheEnCommunicationEtCybern OBJECT IDENTIFIER ::= { enterprises 17693 }
elekta                            OBJECT IDENTIFIER ::= { enterprises 17694 }
comboxWINET                       OBJECT IDENTIFIER ::= { enterprises 17695 }
gadITFuerBankenEG                 OBJECT IDENTIFIER ::= { enterprises 17696 }
sandersonTownendAndGilbert        OBJECT IDENTIFIER ::= { enterprises 17697 }
johnLewisPLC                      OBJECT IDENTIFIER ::= { enterprises 17698 }
japanControlEngineering           OBJECT IDENTIFIER ::= { enterprises 17699 }
powerwallzNetworkSecurity         OBJECT IDENTIFIER ::= { enterprises 17700 }
baeSystems                        OBJECT IDENTIFIER ::= { enterprises 17701 }
smartpantsMedia                   OBJECT IDENTIFIER ::= { enterprises 17702 }
rudjerBoskovicInstitute           OBJECT IDENTIFIER ::= { enterprises 17703 }
criticalTelecomCorp               OBJECT IDENTIFIER ::= { enterprises 17704 }
soveltoOy                         OBJECT IDENTIFIER ::= { enterprises 17705 }
kidery                            OBJECT IDENTIFIER ::= { enterprises 17706 }
theMemeFactory                    OBJECT IDENTIFIER ::= { enterprises 17707 }
sysmangocom                       OBJECT IDENTIFIER ::= { enterprises 17708 }
shanghaiTelecommnunicationsTechnologicalResearchInstitute OBJECT IDENTIFIER ::= { enterprises 17709 }
michaelJVanHam                    OBJECT IDENTIFIER ::= { enterprises 17710 }
aisaiCommunicationTechnologyCO    OBJECT IDENTIFIER ::= { enterprises 17711 }
tbSolutionsTechnologiesSoftwareSL OBJECT IDENTIFIER ::= { enterprises 17712 }
pipinghotNetworksLimited          OBJECT IDENTIFIER ::= { enterprises 17713 }
asmEnterprises                    OBJECT IDENTIFIER ::= { enterprises 17714 }
mitsukoshiInfomationServiceCo     OBJECT IDENTIFIER ::= { enterprises 17715 }
georgiaTechFoundation             OBJECT IDENTIFIER ::= { enterprises 17716 }
escription                        OBJECT IDENTIFIER ::= { enterprises 17717 }
vanu                              OBJECT IDENTIFIER ::= { enterprises 17718 }
noldata                           OBJECT IDENTIFIER ::= { enterprises 17719 }
prompt                            OBJECT IDENTIFIER ::= { enterprises 17720 }
aglResources                      OBJECT IDENTIFIER ::= { enterprises 17721 }
steagAktiengesellschaft           OBJECT IDENTIFIER ::= { enterprises 17722 }
softelSADeCV                      OBJECT IDENTIFIER ::= { enterprises 17723 }
sinocdn                           OBJECT IDENTIFIER ::= { enterprises 17724 }
hwTerminationUnion                OBJECT IDENTIFIER ::= { enterprises 17725 }
advaTechnologies                  OBJECT IDENTIFIER ::= { enterprises 17726 }
wiplug                            OBJECT IDENTIFIER ::= { enterprises 17727 }
abovecable                        OBJECT IDENTIFIER ::= { enterprises 17728 }
spuentrupSoftware                 OBJECT IDENTIFIER ::= { enterprises 17729 }
reddotSolutionsAG                 OBJECT IDENTIFIER ::= { enterprises 17730 }
cqsTechnologyHoldings             OBJECT IDENTIFIER ::= { enterprises 17731 }
snaLab                            OBJECT IDENTIFIER ::= { enterprises 17732 }
delawareStateUniversity           OBJECT IDENTIFIER ::= { enterprises 17733 }
ocSystems                         OBJECT IDENTIFIER ::= { enterprises 17734 }
quarkCommunications               OBJECT IDENTIFIER ::= { enterprises 17735 }
tradingMetrics                    OBJECT IDENTIFIER ::= { enterprises 17736 }
tablus                            OBJECT IDENTIFIER ::= { enterprises 17737 }
traceyBernath                     OBJECT IDENTIFIER ::= { enterprises 17738 }
dfSoft                            OBJECT IDENTIFIER ::= { enterprises 17739 }
isecurityTechnologyLimited        OBJECT IDENTIFIER ::= { enterprises 17740 }
openEnterpriseSystems             OBJECT IDENTIFIER ::= { enterprises 17741 }
rootsr                            OBJECT IDENTIFIER ::= { enterprises 17742 }
mWebBusinessSolutions             OBJECT IDENTIFIER ::= { enterprises 17743 }
dubexAS                           OBJECT IDENTIFIER ::= { enterprises 17744 }
huntekCo                          OBJECT IDENTIFIER ::= { enterprises 17745 }
byIntertrade                      OBJECT IDENTIFIER ::= { enterprises 17746 }
nexagent                          OBJECT IDENTIFIER ::= { enterprises 17747 }
cardSystemsConsultingSRL          OBJECT IDENTIFIER ::= { enterprises 17748 }
tgc                               OBJECT IDENTIFIER ::= { enterprises 17749 }
itechnology                       OBJECT IDENTIFIER ::= { enterprises 17750 }
radioSystems                      OBJECT IDENTIFIER ::= { enterprises 17751 }
institutoAtl                      OBJECT IDENTIFIER ::= { enterprises 17752 }
metrohealthMedicalCenter          OBJECT IDENTIFIER ::= { enterprises 17753 }
alexanderPilgerConsulting         OBJECT IDENTIFIER ::= { enterprises 17754 }
laneDepartmentOfComputerScienceAndElectricalEngineering OBJECT IDENTIFIER ::= { enterprises 17755 }
scienceComputingAg                OBJECT IDENTIFIER ::= { enterprises 17756 }
orthopedicHealthcareNorthwest     OBJECT IDENTIFIER ::= { enterprises 17757 }
trematonUK                        OBJECT IDENTIFIER ::= { enterprises 17758 }
synctomi                          OBJECT IDENTIFIER ::= { enterprises 17759 }
identify                          OBJECT IDENTIFIER ::= { enterprises 17760 }
wiredplace                        OBJECT IDENTIFIER ::= { enterprises 17761 }
covertSecurityServices            OBJECT IDENTIFIER ::= { enterprises 17762 }
teskeNetzwerkberatung             OBJECT IDENTIFIER ::= { enterprises 17763 }
ditelco                           OBJECT IDENTIFIER ::= { enterprises 17764 }
tessnaPrivateLimited              OBJECT IDENTIFIER ::= { enterprises 17765 }
pgpCorporation                    OBJECT IDENTIFIER ::= { enterprises 17766 }
lakesoft                          OBJECT IDENTIFIER ::= { enterprises 17767 }
ecobyteLimited                    OBJECT IDENTIFIER ::= { enterprises 17768 }
werft22AG                         OBJECT IDENTIFIER ::= { enterprises 17769 }
ciaMetropolitanoDeS               OBJECT IDENTIFIER ::= { enterprises 17770 }
lingardKnowledgeSoftwareEngineering OBJECT IDENTIFIER ::= { enterprises 17771 }
ironicoPty                        OBJECT IDENTIFIER ::= { enterprises 17772 }
nexcomInternationalCo             OBJECT IDENTIFIER ::= { enterprises 17773 }
smartComputerSystems              OBJECT IDENTIFIER ::= { enterprises 17774 }
intorel                           OBJECT IDENTIFIER ::= { enterprises 17775 }
sinSolution                       OBJECT IDENTIFIER ::= { enterprises 17776 }
jasernet                          OBJECT IDENTIFIER ::= { enterprises 17777 }
nicatInternetVerwaltungsUndBetriebsgesellschaftMBH OBJECT IDENTIFIER ::= { enterprises 17778 }
econtec                           OBJECT IDENTIFIER ::= { enterprises 17779 }
trumanMedicalCenters              OBJECT IDENTIFIER ::= { enterprises 17780 }
universityOfValeDoItajaiCESSaoJose OBJECT IDENTIFIER ::= { enterprises 17781 }
michaelParker                     OBJECT IDENTIFIER ::= { enterprises 17782 }
setelSpa                          OBJECT IDENTIFIER ::= { enterprises 17783 }
mitsubishiElectricBusinessSystemsCo OBJECT IDENTIFIER ::= { enterprises 17784 }
bonnaSABLASA                      OBJECT IDENTIFIER ::= { enterprises 17785 }
frankendata                       OBJECT IDENTIFIER ::= { enterprises 17786 }
tschaufrei                        OBJECT IDENTIFIER ::= { enterprises 17787 }
edagEngineeringDesignAG           OBJECT IDENTIFIER ::= { enterprises 17788 }

END
