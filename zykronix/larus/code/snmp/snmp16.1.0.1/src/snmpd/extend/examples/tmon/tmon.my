--
--
-- Copyright (C) 1992-2003 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--

--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--
--


   TRAP-MONITOR-MIB DEFINITIONS ::= BEGIN

   IMPORTS
       MODULE-IDENTITY, OBJECT-TYPE, NOTIFICATION-TYPE
           FROM SNMPv2-SMI;

   snmpResearch                OBJECT IDENTIFIER ::= { enterprises 99 }

   snmpResearchMIBs            OBJECT IDENTIFIER ::= { snmpResearch 12 }

   srExamples                  OBJECT IDENTIFIER ::= { snmpResearchMIBs 19 }

   srBasics                    OBJECT IDENTIFIER ::= { srExamples 1 }

   srScalars                   OBJECT IDENTIFIER ::= { srBasics 1 }

   srScalarGet                 OBJECT IDENTIFIER ::= { srScalars 1 }

   srOID                       OBJECT IDENTIFIER ::= { srScalarGet 3 }

   trapMonitor MODULE-IDENTITY
       LAST-UPDATED "9604300000Z"
       ORGANIZATION "SNMP Research"
       CONTACT-INFO
              "         Technical Support

                Postal: SNMP Research
                        3001 Kimberlin Heights Road
                        Knoxville, TN  37920-9716

                   Tel: +1 865 573 1434
                   Fax: +1 865 573 9197

                E-mail: support@snmp.com
                   WWW: http://www.snmp.com"
       DESCRIPTION
               "An example MIB module to demonstrate the SNMP
               Research get method routine and the internal
               representation of Object Identifier MIB objects."
       ::= { srOID 1 }


   tmonLastSentTrap OBJECT-TYPE
       SYNTAX  OBJECT IDENTIFIER
       MAX-ACCESS  read-only
       STATUS  current
       DESCRIPTION
               "The OID of the last enterprise-specific trap which
               was sent by the agent."
       ::= { trapMonitor 1 }


   -- tmon traps

   tmonStartupAlarm NOTIFICATION-TYPE
       STATUS  current
       DESCRIPTION
               "An example trap which is sent when the trap-monitoring
                subsystem is initialized.  The OID of this trap is a
                valid value for tmonLastSentTrap."
       ::= { trapMonitor 2 }

END
