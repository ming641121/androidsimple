--
--
-- Copyright (C) 1992-2003 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--

--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--
--


   VCR-MIB DEFINITIONS ::= BEGIN

   IMPORTS
       MODULE-IDENTITY, OBJECT-TYPE, NOTIFICATION-TYPE,
       ObjectName, Integer32, Counter32
           FROM SNMPv2-SMI
       RowStatus, DateAndTime FROM SNMPv2-TC;

   snmpResearch                OBJECT IDENTIFIER ::= { enterprises 99 }

   snmpResearchMIBs            OBJECT IDENTIFIER ::= { snmpResearch 12 }

   srExamples                  OBJECT IDENTIFIER ::= { snmpResearchMIBs 19 }

   srBasics                    OBJECT IDENTIFIER ::= { srExamples 1 }

   srTables                    OBJECT IDENTIFIER ::= { srBasics 2 }

   srTableRowCreation          OBJECT IDENTIFIER ::= { srTables 3 }

   vcr MODULE-IDENTITY
       LAST-UPDATED "9603050000Z"
       ORGANIZATION "SNMP Research"
       CONTACT-INFO
              "         Technical Support

                Postal: SNMP Research
                        3001 Kimberlin Heights Road
                        Knoxville, TN  37920-9716

                   Tel: +1 865 573 1434
                   Fax: +1 865 573 9197

                E-mail: support@snmp.com
                   WWW: http://www.snmp.com"
       DESCRIPTION
               "An example MIB module to demonstrate the SNMP
               Research method routines for row creation in
	       conceptual tables and MIB tool features for the
	       RowStatus textual convention."
       ::= { srTableRowCreation 1 }

   VcrChannelNumber ::= TEXTUAL-CONVENTION
       STATUS        current
       DESCRIPTION
           "The off-air or on-cable channel number."
       SYNTAX        INTEGER (2..125)


-- The vcrGeneral Group

   vcrGeneral OBJECT IDENTIFIER ::= { vcr 1 }
 
   vcrChannel OBJECT-TYPE
       SYNTAX     VcrChannelNumber 
       MAX-ACCESS read-only
       STATUS     current
       DESCRIPTION
	       "The channel selected for viewing and recording."
       ::= { vcrGeneral 1 }

   vcrPowerState OBJECT-TYPE
       SYNTAX     INTEGER { on(1), off(2) }
       MAX-ACCESS read-only
       STATUS     current
       DESCRIPTION
               "The position of the power control selector."
       ::= { vcrGeneral 2 }


-- The vcrProgram Group

   vcrProgram OBJECT IDENTIFIER ::= { vcr 2 }
    
   vcrProgramTable OBJECT-TYPE
       SYNTAX     SEQUENCE OF VcrProgramEntry
       MAX-ACCESS not-accessible
       STATUS     current
       DESCRIPTION
	       "The table of programs to record."
       ::= { vcrProgram 1 }
   
   vcrProgramEntry OBJECT-TYPE
       SYNTAX     VcrProgramEntry
       MAX-ACCESS not-accessible
       STATUS     current
       DESCRIPTION
	       "The information about one program to record."
       INDEX { vcrProgramTableIndex }
       ::= { vcrProgramTable 1 }
   
   VcrProgramEntry ::= SEQUENCE {
       vcrProgramTableIndex Integer32,
       vcrProgramChannel    VcrChannelNumber,
       vcrProgramStartTime  DateAndTime,
       vcrProgramStopTime   DateAndTime,
       vcrProgramSpeed      INTEGER,
       vcrProgramStatus     RowStatus
   }
   
   vcrProgramTableIndex OBJECT-TYPE
       SYNTAX     Integer32 
       MAX-ACCESS not-accessible
       STATUS     current
       DESCRIPTION
	       "The index of the program entry."
       ::= { vcrProgramEntry 1 }
   
   vcrProgramChannel OBJECT-TYPE
       SYNTAX     VcrChannelNumber
       MAX-ACCESS read-create
       STATUS     current
       DESCRIPTION
	       "The channel to record this program."
       ::= { vcrProgramEntry 2 }
   
   vcrProgramStartTime OBJECT-TYPE
       SYNTAX     DateAndTime
       MAX-ACCESS read-create
       STATUS     current
       DESCRIPTION
	       "The time to start recording this program."
       ::= { vcrProgramEntry 3 }
   
   vcrProgramStopTime OBJECT-TYPE 
       SYNTAX     DateAndTime
       MAX-ACCESS read-create
       STATUS     current
       DESCRIPTION
	       "The time to stop recording this program."
       ::= { vcrProgramEntry 4 }
   
   vcrProgramSpeed OBJECT-TYPE
       SYNTAX     INTEGER {
		sp(1),
		ep(2)
		}
       MAX-ACCESS read-create
       STATUS     current
       DESCRIPTION
	       "The recording speed for this program."
       ::= { vcrProgramEntry 5 }
   
   vcrProgramStatus OBJECT-TYPE
       SYNTAX     RowStatus 
       MAX-ACCESS read-create
       STATUS     current
       DESCRIPTION
	       "The status of this program entry."
       ::= { vcrProgramEntry 6 }
   
   
END
